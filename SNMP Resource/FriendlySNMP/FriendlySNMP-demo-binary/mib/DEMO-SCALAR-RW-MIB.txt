-- 
-- This is FriendlySNMP DEMO-SCALAR-RW-MIB
--

DEMO-SCALAR-RW-MIB DEFINITIONS ::= BEGIN

IMPORTS
    enterprises,
    MODULE-IDENTITY,
    OBJECT-TYPE
        FROM SNMPv2-SMI
    DisplayString,
    TEXTUAL-CONVENTION
        FROM SNMPv2-TC
    MODULE-COMPLIANCE, 
    OBJECT-GROUP
        FROM SNMPv2-CONF
    ;

-- Module Identity
------------------
demoScalarRW MODULE-IDENTITY 
    -- Date Format is "YYYYMMDDhhmmZ"
    LAST-UPDATED "201004010000Z"    
    ORGANIZATION "FriendlySNMP"
    CONTACT-INFO "info@friendlysnmp.org"
    DESCRIPTION  "This is demo MIB to test basic SNMP agent functionality"
    -- Multiple pairs revision/description are allowed
    REVISION     "201004010000Z"
    DESCRIPTION  "FriendlySNMP Demo MIB"
    -- 1.3.6.1.4.1.29091.10.2
    ::= { friendlySNMP demo(10) 2 }

-- Enterprise OIDs
------------------
friendlySNMP OBJECT IDENTIFIER ::= { enterprises 29091 }

-- Textual Conventions
----------------------
DemoImageFormatTC ::= TEXTUAL-CONVENTION
    STATUS  current
    DESCRIPTION "Defines image file format"
    SYNTAX INTEGER { bmp(2), jpg(3), gif(5), png(12) }
    
-- Top-level tree (sections)
----------------------------
demoMIBObjects       OBJECT IDENTIFIER ::= { demoScalarRW 1 }
demoMIBConformance   OBJECT IDENTIFIER ::= { demoScalarRW 3 }

-- Scalar GET values
--------------------
imageFilename OBJECT-TYPE
    SYNTAX      DisplayString
    MAX-ACCESS  read-write
    STATUS      current
    DESCRIPTION "File name defined by MIB browser or user"
    ::= { demoMIBObjects 1 }

imageFormat OBJECT-TYPE
    SYNTAX      DemoImageFormatTC
    MAX-ACCESS  read-write
    STATUS      current
    DESCRIPTION "Image format defined by MIB browser or user"
    ::= { demoMIBObjects 2 }

imageSize OBJECT-TYPE
    SYNTAX      DisplayString
    MAX-ACCESS  read-write
    STATUS      current
    DESCRIPTION "Image size defined by MIB browser. Valid format is NNNxMMM"
    ::= { demoMIBObjects 3 }

--
-- SECTION: Conformance
--
demoCompliance MODULE-COMPLIANCE
    STATUS  current
    DESCRIPTION
        "The compliance statement for SNMP entities which
        implement this MIB."
    MODULE  -- this module
    MANDATORY-GROUPS { 
        demoObjectGroup
    }
    ::= { demoMIBConformance 1 }

demoObjectGroup OBJECT-GROUP
    OBJECTS {
        imageFilename,
        imageFormat,
        imageSize
    }
    STATUS current
    DESCRIPTION "A collection of object nodes in this MIB"
    ::= { demoMIBConformance 2 }

END
