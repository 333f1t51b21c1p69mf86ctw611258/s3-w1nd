-- 
-- This is FriendlySNMP DEMO-TABLE-URL-MIB
--

DEMO-TABLE-URL-MIB DEFINITIONS ::= BEGIN

IMPORTS
    enterprises,
    MODULE-IDENTITY,
    Unsigned32,
    IpAddress,
    OBJECT-TYPE
        FROM SNMPv2-SMI
    DisplayString
        FROM SNMPv2-TC
    MODULE-COMPLIANCE, 
    OBJECT-GROUP
        FROM SNMPv2-CONF
    ;

-- Module Identity
------------------
demoTableURL MODULE-IDENTITY 
    -- Date Format is "YYYYMMDDhhmmZ"
    LAST-UPDATED "201004010000Z"    
    ORGANIZATION "FriendlySNMP"
    CONTACT-INFO "info@friendlysnmp.org"
    DESCRIPTION  "This is demo MIB to test basic SNMP agent functionality"
    -- Multiple pairs revision/description are allowed
    REVISION     "201004010000Z"
    DESCRIPTION  "FriendlySNMP Demo MIB"
    -- 1.3.6.1.4.1.29091.10.3
    ::= { friendlySNMP demo(10) 3 }

-- Enterprise OIDs
------------------
friendlySNMP OBJECT IDENTIFIER ::= { enterprises 29091 }

-- Top-level tree (sections)
----------------------------
demoMIBObjects       OBJECT IDENTIFIER ::= { demoTableURL 1 }
demoMIBConformance   OBJECT IDENTIFIER ::= { demoTableURL 3 }

-- Table
--------------------
urlTable OBJECT-TYPE
    SYNTAX      SEQUENCE OF UrlEntry
    MAX-ACCESS  not-accessible
    STATUS      current
    DESCRIPTION "Table of URLs"
    ::= { demoMIBObjects 13 }

urlEntry OBJECT-TYPE
    SYNTAX      UrlEntry
    MAX-ACCESS  not-accessible
    STATUS      current
    DESCRIPTION "Row with URL info"
    INDEX { urlIndex }
    ::= { urlTable 1 }

UrlEntry ::= SEQUENCE {
    urlIndex        Unsigned32,
    urlHostName     DisplayString,
    urlIpAddress    IpAddress,
    urlResponseTime Unsigned32
}

urlIndex OBJECT-TYPE
    SYNTAX      Unsigned32
    MAX-ACCESS  not-accessible
    STATUS      current
    DESCRIPTION "This is a table column: INDEX"
    ::= { urlEntry 1 }

urlHostName OBJECT-TYPE
    SYNTAX      DisplayString
    MAX-ACCESS  read-only
    STATUS      current
    DESCRIPTION "This is a table column: hostname."
    ::= { urlEntry 2 }

urlIpAddress OBJECT-TYPE
    SYNTAX      IpAddress
    MAX-ACCESS  read-only
    STATUS      current
    DESCRIPTION "This is a table column: IP address."
    ::= { urlEntry 3 }
    
urlResponseTime OBJECT-TYPE
    SYNTAX      Unsigned32
    MAX-ACCESS  read-only
    STATUS      current
    DESCRIPTION "This is a table column: response time."
    ::= { urlEntry 4 }

--
-- SECTION: Conformance
--
demoCompliance MODULE-COMPLIANCE
    STATUS  current
    DESCRIPTION
        "The compliance statement for SNMP entities which
        implement this MIB."
    MODULE  -- this module
    MANDATORY-GROUPS { 
        demoObjectGroup
    }
    ::= { demoMIBConformance 1 }

demoObjectGroup OBJECT-GROUP
    OBJECTS {
        urlHostName,
        urlIpAddress,
        urlResponseTime
    }
    STATUS current
    DESCRIPTION "A collection of object nodes in this MIB"
    ::= { demoMIBConformance 2 }

END
