-- 
-- This is FriendlySNMP DEMO-SCALAR-RO-MIB
--

DEMO-SCALAR-RO-MIB DEFINITIONS ::= BEGIN

IMPORTS
    enterprises,
    MODULE-IDENTITY,
    OBJECT-TYPE,
    Integer32
        FROM SNMPv2-SMI
    DisplayString,
    TEXTUAL-CONVENTION
        FROM SNMPv2-TC
    MODULE-COMPLIANCE, 
    OBJECT-GROUP
        FROM SNMPv2-CONF
    ;

-- Module Identity
------------------
demoScalarRO MODULE-IDENTITY 
    -- Date Format is "YYYYMMDDhhmmZ"
    LAST-UPDATED "201004010000Z"    
    ORGANIZATION "FriendlySNMP"
    CONTACT-INFO "info@friendlysnmp.org"
    DESCRIPTION  "This is demo MIB to test basic SNMP agent functionality"
    -- Multiple pairs revision/description allowed
    REVISION     "201004010000Z"
    DESCRIPTION  "FriendlySNMP Demo MIB"
    -- 1.3.6.1.4.1.29091.10.1
    ::= { friendlySNMP demo(10) 1 }

-- Enterprise OIDs
------------------
friendlySNMP OBJECT IDENTIFIER ::= { enterprises 29091 }

-- Textual Conventions
----------------------
DemoUserLevelTC ::= TEXTUAL-CONVENTION
    STATUS  current
    DESCRIPTION "Defines level"
    SYNTAX INTEGER { beginner(1), intermediate(4), experienced(8), guru(12) }
    
DemoAgeIntTC ::= TEXTUAL-CONVENTION
    DISPLAY-HINT "d"
    STATUS      current
    DESCRIPTION "A positive integer in range 0..100."
    SYNTAX Integer32 (0..100)

-- Top-level tree (sections)
----------------------------
demoMIBObjects       OBJECT IDENTIFIER ::= { demoScalarRO 1 }
demoMIBConformance   OBJECT IDENTIFIER ::= { demoScalarRO 3 }

-- Scalar GET values
--------------------
userDir OBJECT-TYPE
    SYNTAX      DisplayString
    MAX-ACCESS  read-only
    STATUS      current
    DESCRIPTION "Returns user directory"
    ::= { demoMIBObjects 1 }

ticksCount OBJECT-TYPE
    SYNTAX      Integer32
    MAX-ACCESS  read-only
    STATUS      current
    DESCRIPTION "Ticks count (application age in seconds)."
    ::= { demoMIBObjects 2 }

userName OBJECT-TYPE
    SYNTAX      DisplayString
    MAX-ACCESS  read-only
    STATUS      current
    DESCRIPTION "Returns user name"
    ::= { demoMIBObjects 3 }

userLevel OBJECT-TYPE
    SYNTAX      DemoUserLevelTC
    MAX-ACCESS  read-only
    STATUS      current
    DESCRIPTION "Returns user's level"
    ::= { demoMIBObjects 4 }
    
userAge OBJECT-TYPE
    SYNTAX      DemoAgeIntTC
    MAX-ACCESS  read-only
    STATUS      current
    DESCRIPTION "Returns user's age (years)"
    ::= { demoMIBObjects 5 }
    
--
-- SECTION: Conformance
--
demoCompliance MODULE-COMPLIANCE
    STATUS  current
    DESCRIPTION
        "The compliance statement for SNMP entities which
        implement this MIB."
    MODULE  -- this module
    MANDATORY-GROUPS { 
        demoObjectGroup
    }
    ::= { demoMIBConformance 1 }

demoObjectGroup OBJECT-GROUP
    OBJECTS {
        ticksCount,
        userDir,
        userName,
        userLevel,
        userAge
    }
    STATUS current
    DESCRIPTION "A collection of object nodes in this MIB"
    ::= { demoMIBConformance 2 }

END
