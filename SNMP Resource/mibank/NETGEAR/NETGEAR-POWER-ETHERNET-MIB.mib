NETGEAR-POWER-ETHERNET-MIB DEFINITIONS ::= BEGIN

-- Copyright LVL7 Systems (2003-2005)  All rights reserved.

-- This SNMP Management Information Specification
-- embodies LVL7 System's confidential and proprietary
-- intellectual property.  LVL7 Systems retains all title
-- and ownership in the Specification including any revisions.

-- This Specification is supplied "AS IS", LVL7 Systems
-- makes no warranty, either expressed or implied,
-- as to the use, operation, condition, or performance of the
-- Specification.
    
    IMPORTS
      MODULE-IDENTITY, OBJECT-TYPE, Gauge32                  FROM SNMPv2-SMI
      ng7000Switch                                           FROM NETGEAR-REF-MIB
      pethPsePortEntry                                       FROM POWER-ETHERNET-MIB;
    

    agentPowerEthernetMIB MODULE-IDENTITY
    LAST-UPDATED "200311101200Z" -- 10 Nov 2003 12:00:00 GMT
    ORGANIZATION "Netgear"
    CONTACT-INFO
        ""
    DESCRIPTION
        "This MIB Augments the POWER-ETHERNET-MIB created by the IETF Ethernet 
         Interfaces and Hub MIB Working Group for managing Power Source 
         Equipment (PSE).  The objects in this MIB are intended to provide 
         additional objects for reporting information available to the hardware 
         on this platform which are not represented in the draft MIB."
         
-- revision history
    REVISION
	    "200311101200Z" -- 10 Nov 2003 12:00:00 GMT

	DESCRIPTION
	    "Initial revision."
    ::= { ng7000Switch 15 }

    agentPethObjects       OBJECT IDENTIFIER ::= { agentPowerEthernetMIB 1 }

    agentPethPsePortTable OBJECT-TYPE
          SYNTAX      SEQUENCE OF AgentPethPsePortEntry
          MAX-ACCESS  not-accessible
          STATUS      current
          DESCRIPTION
              "A table of per-port information and configuration objects relating 
              to the power status of each port."
          ::= { agentPethObjects 1 }

    agentPethPsePortEntry OBJECT-TYPE
          SYNTAX      AgentPethPsePortEntry
          MAX-ACCESS  not-accessible
          STATUS      current
          DESCRIPTION
              "A collection of objects providing additional power information 
              and control parameters for the specified port."
          AUGMENTS    { pethPsePortEntry }
          ::= { agentPethPsePortTable 1 }

    AgentPethPsePortEntry ::= SEQUENCE {
          agentPethPowerLimit
             Gauge32,
          agentPethOutputPower
             Gauge32,
          agentPethOutputCurrent
             Gauge32,
          agentPethOutputVolts
             Gauge32
          }
             
    agentPethPowerLimit OBJECT-TYPE
          SYNTAX      Gauge32 (3..16)
          UNITS       "Watts"
          MAX-ACCESS  read-write
          STATUS      current
          DESCRIPTION
             "The configured maximum power this port can provide to an 
             attached device measured in Watts."
          ::= { agentPethPsePortEntry 1 }
    
    agentPethOutputPower OBJECT-TYPE
          SYNTAX      Gauge32
          UNITS       "Milliwatts"
          MAX-ACCESS  read-only
          STATUS      current
          DESCRIPTION
             "The power this port is supplying to an attached device measured 
             in Milliwatts."
          ::= { agentPethPsePortEntry 2 }
    
    agentPethOutputCurrent OBJECT-TYPE
          SYNTAX      Gauge32
          UNITS       "Milliamps"
          MAX-ACCESS  read-only
          STATUS      current
          DESCRIPTION
             "The current this port is supplying to an attached device measured 
             in Milliamps."
          ::= { agentPethPsePortEntry 3 }
    
    agentPethOutputVolts OBJECT-TYPE
          SYNTAX      Gauge32
          UNITS       "Volts"
          MAX-ACCESS  read-only
          STATUS      current
          DESCRIPTION
             "The voltage this port is supplying to an attached device measured 
             in Volts."
          ::= { agentPethPsePortEntry 4 }
          
END
