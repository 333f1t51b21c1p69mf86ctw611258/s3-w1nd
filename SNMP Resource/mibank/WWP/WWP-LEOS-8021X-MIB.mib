--
-- WWP-LEOS-8021X-MIB.my
-- MIB generated by MG-SOFT Visual MIB Builder Version 6.0  Build 88
-- Sunday, August 28, 2005 at 19:49:14
--

	WWP-LEOS-8021X-MIB DEFINITIONS ::= BEGIN
 
		IMPORTS
			OBJECT-GROUP, NOTIFICATION-GROUP			
				FROM SNMPv2-CONF			
			OBJECT-TYPE, MODULE-IDENTITY			
				FROM SNMPv2-SMI			
			wwpModulesLeos			
				FROM WWP-SMI;
	
	
		-- 1.3.6.1.4.1.6141.2.60.401
		wwpLeos8021xMibModule MODULE-IDENTITY 
			LAST-UPDATED "200508281935Z"		-- August 28, 2005 at 19:35 GMT
			ORGANIZATION 
				"World Wide Packets, Inc"
			CONTACT-INFO
				"   Mib Meister
		  		Postal: World Wide Packets
				P.O. Box 950
				Veradale, WA 99037
				USA
		 		Phone:  +1 509 242 9000
				Email:  mib.meister@worldwidepackets.com"
			DESCRIPTION 
				"Description."
			::= { wwpModulesLeos 401 }

		
	
--
-- Node definitions
--
	
		-- 1.3.6.1.4.1.6141.2.60.401.1
		wwpLeos8021xMIB OBJECT IDENTIFIER ::= { wwpLeos8021xMibModule 1 }

		
		-- 1.3.6.1.4.1.6141.2.60.401.1.1
		wwpLeos8021xConf OBJECT IDENTIFIER ::= { wwpLeos8021xMIB 1 }

		
		-- 1.3.6.1.4.1.6141.2.60.401.1.1.1
		wwpLeos8021xGroups OBJECT IDENTIFIER ::= { wwpLeos8021xConf 1 }

		
		-- 1.3.6.1.4.1.6141.2.60.401.1.1.1.1
		wwpLeos8021xObjectGroup OBJECT-GROUP
			OBJECTS { object1 }
			STATUS current
			DESCRIPTION 
				"Description."
			::= { wwpLeos8021xGroups 1 }

		
		-- 1.3.6.1.4.1.6141.2.60.401.1.1.1.2
		wwpLeos8021xNotificationGroup NOTIFICATION-GROUP
			NOTIFICATIONS { notification1 }
			STATUS current
			DESCRIPTION 
				"Description."
			::= { wwpLeos8021xGroups 2 }

		
		-- 1.3.6.1.4.1.6141.2.60.401.1.1.2
		wwpLeos8021xCompls OBJECT IDENTIFIER ::= { wwpLeos8021xConf 2 }

		
		-- 1.3.6.1.4.1.6141.2.60.401.1.2
		wwpLeos8021xObjs OBJECT IDENTIFIER ::= { wwpLeos8021xMIB 2 }

		
		-- 1.3.6.1.4.1.6141.2.60.401.1.2.1
		wwpLeos8021xPortTable OBJECT-TYPE
			SYNTAX SEQUENCE OF WwpLeos8021xPortEntry
			MAX-ACCESS not-accessible
			STATUS current
			DESCRIPTION
				"Table with an entry for every port on the switch"
			::= { wwpLeos8021xObjs 1 }

		
		-- 1.3.6.1.4.1.6141.2.60.401.1.2.1.1
		wwpLeos8021xPortEntry OBJECT-TYPE
			SYNTAX WwpLeos8021xPortEntry
			MAX-ACCESS not-accessible
			STATUS current
			DESCRIPTION
				"Description."
			INDEX { wwpLeos8021xPort }
			::= { wwpLeos8021xPortTable 1 }

		
		WwpLeos8021xPortEntry ::=
			SEQUENCE { 
				wwpLeos8021xPort
					INTEGER,
				wwpLeos8021xRole
					INTEGER
			 }

		-- 1.3.6.1.4.1.6141.2.60.401.1.2.1.1.1
		wwpLeos8021xPort OBJECT-TYPE
			SYNTAX INTEGER (1..1000)
			MAX-ACCESS read-only
			STATUS current
			DESCRIPTION
				"Switch Ethernet Port"
			::= { wwpLeos8021xPortEntry 1 }

		
		-- 1.3.6.1.4.1.6141.2.60.401.1.2.1.1.2
		wwpLeos8021xRole OBJECT-TYPE
			SYNTAX INTEGER
				{
				none(1),
				supplicant(2),
				authenticator(3),
				both(4)
				}
			MAX-ACCESS read-write
			STATUS current
			DESCRIPTION
				"802.1x role of the Port."
			::= { wwpLeos8021xPortEntry 2 }

		
		-- 1.3.6.1.4.1.6141.2.60.401.1.3
		wwpLeos8021xEvents OBJECT IDENTIFIER ::= { wwpLeos8021xMIB 3 }

		
		-- 1.3.6.1.4.1.6141.2.60.401.1.3.0
		wwpLeos8021xEventsV2 OBJECT IDENTIFIER ::= { wwpLeos8021xEvents 0 }

		
	
	END

--
-- WWP-LEOS-8021X-MIB.my
--
