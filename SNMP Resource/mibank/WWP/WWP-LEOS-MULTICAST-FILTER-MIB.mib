--
 -- WWP-LEOS-MULTICAST-FILTER-MIB.my
 --
 --

 WWP-LEOS-MULTICAST-FILTER-MIB DEFINITIONS ::= BEGIN

 IMPORTS 		
	TEXTUAL-CONVENTION FROM SNMPv2-TC
   NOTIFICATION-TYPE, Counter32, IpAddress, Integer32, Unsigned32, OBJECT-TYPE, MODULE-IDENTITY			
	    FROM SNMPv2-SMI		
   DisplayString, MacAddress, DateAndTime, RowStatus, TruthValue			
	    FROM SNMPv2-TC						
   wwpModules, wwpModulesLeos	
	    FROM WWP-SMI;
	
	
 wwpLeosMcastFilterMIB MODULE-IDENTITY
	    LAST-UPDATED "200302101700Z"
	    ORGANIZATION "World Wide Packets, Inc"
	    CONTACT-INFO
		    "   Mib Meister
		  	Postal: World Wide Packets
		        P.O. Box 950
		        Veradale, WA 99037
		        USA
		 	Phone:  +1 509 242 9000
			Email:  mib.meister@worldwidepackets.com"
	    DESCRIPTION
		    "This MIB specifies the managed objects for Multicast filter 
		    specific to the WWP Products."
	    REVISION    "200302101700Z"
	    DESCRIPTION
		    "Initial creation."
	    ::= { wwpModulesLeos 7 }
						

 --
 -- Textual conventions
 --

 VlanId ::= TEXTUAL-CONVENTION
    STATUS      current
    DESCRIPTION
        "A Vlan Id represents a Broadcast Domain."
    SYNTAX      INTEGER (1..24576)

 
 --
 -- Node definitions
 --
	
 wwpLeosMcastFilterMIBObjects OBJECT IDENTIFIER ::= { wwpLeosMcastFilterMIB 1 }
 
 --
 -- multicast filter group
 --
 wwpLeosMcastFilterConfig OBJECT IDENTIFIER ::= { wwpLeosMcastFilterMIBObjects 1 }
 
 --
 -- multicast filter status
 --
 wwpLeosMcastFilterStatus OBJECT IDENTIFIER ::= { wwpLeosMcastFilterMIBObjects 2 }

 --
 -- multicast filter stats
 --
 wwpLeosMcastFilterStats OBJECT IDENTIFIER ::= { wwpLeosMcastFilterMIBObjects 3 }
   

 -- Notifications 
  
 wwpLeosMcastFilterMIBNotificationPrefix  OBJECT IDENTIFIER ::= { wwpLeosMcastFilterMIB 2 } 
 wwpLeosMcastFilterMIBNotifications       OBJECT IDENTIFIER ::=  
                       { wwpLeosMcastFilterMIBNotificationPrefix 0 }

 -- Conformance information 
 
 wwpLeosMcastFilterMIBConformance OBJECT IDENTIFIER ::= { wwpLeosMcastFilterMIB 3 } 
 wwpLeosMcastFilterMIBCompliances OBJECT IDENTIFIER ::= { wwpLeosMcastFilterMIBConformance 1 } 		
 wwpLeosMcastFilterMIBGroups      OBJECT IDENTIFIER ::= { wwpLeosMcastFilterMIBConformance 2 }

 wwpLeosMcastConfigState OBJECT-TYPE
     SYNTAX     INTEGER {
			enabled(1),
			disabled(2)
                }
     MAX-ACCESS read-write
     STATUS     current
     DESCRIPTION
            "Setting this object will enable or disable multicast globally."
     ::= { wwpLeosMcastFilterConfig 1 }
 
 --
 --  The Multicast filter Activation Table
 --

 wwpLeosMcastFilterActivationTable OBJECT-TYPE
     SYNTAX     SEQUENCE OF WwpLeosMcastFilterActivationEntry
     MAX-ACCESS not-accessible
     STATUS     current
     DESCRIPTION
            "The (conceptual) table listing the vlans on which the
             multicast filter can be applied. This table is used to create
	     delete entries in the multicast table and also to administratively
	     enable/disable. To configure the Igmp Snooping on this vlan
	     use table wwpLeosMcastIgmpSnoopTable after creating entry in
	     this (wwpLeosMcastFilterActivationTable) table."
    ::= { wwpLeosMcastFilterConfig 2 }

 wwpLeosMcastFilterActivationEntry OBJECT-TYPE
     SYNTAX     WwpLeosMcastFilterActivationEntry
     MAX-ACCESS not-accessible
     STATUS     current
     DESCRIPTION
            "An entry (conceptual row) in the wwpLeosMcastFilterActivationTable."
     INDEX      { wwpLeosMcastVlanId }
     ::= { wwpLeosMcastFilterActivationTable 1 }

 WwpLeosMcastFilterActivationEntry ::= SEQUENCE {   
     wwpLeosMcastVlanId			VlanId,
     wwpLeosMcastFilterAdminState	INTEGER,
     wwpLeosMcastFilterOperState	INTEGER,
     wwpLeosMcastFilterState		RowStatus
 }

 wwpLeosMcastVlanId OBJECT-TYPE
     SYNTAX     VlanId
     MAX-ACCESS read-only
     STATUS     current
     DESCRIPTION
            "The vlan for which this multicast filter can be 
	     enabled/disabled."
     ::= { wwpLeosMcastFilterActivationEntry 1 }
 
 wwpLeosMcastFilterAdminState OBJECT-TYPE
     SYNTAX     INTEGER {
		enabled(1),
		disabled(2)   
		}
     MAX-ACCESS read-write
     STATUS     current
     DESCRIPTION
            "Setting this object to enable will enable multicast on 
	     then given vlan."
     ::= { wwpLeosMcastFilterActivationEntry 2 }

 wwpLeosMcastFilterOperState OBJECT-TYPE
     SYNTAX     INTEGER {
		enabled(1),
		disabled(2)
		}
     MAX-ACCESS read-only
     STATUS     current
     DESCRIPTION
            "The object represents the operational state of multicast
	     on the given vlan."
     ::= { wwpLeosMcastFilterActivationEntry 3 }

 wwpLeosMcastFilterState  OBJECT-TYPE
     SYNTAX          RowStatus
     MAX-ACCESS      read-create
     STATUS          current
     DESCRIPTION
    	    "Setting this object to createandgo(4) will create 
	     entry in multicast table for given vlan and will enable
	     multicast on that vlan.
	     Setting this object to destory will delete the entry from
	     multicast table."
     ::= { wwpLeosMcastFilterActivationEntry 4 }
  
 --
 --  The Multicast filter Server Port Table
 --

 wwpLeosMcastFilterServerPortTable OBJECT-TYPE
     SYNTAX     SEQUENCE OF WwpLeosMcastFilterServerPortEntry
     MAX-ACCESS not-accessible
     STATUS     current
     DESCRIPTION
            "The (conceptual) table listing the 
	    authorized server ports."
    ::= { wwpLeosMcastFilterConfig 3 }

 wwpLeosMcastFilterServerPortEntry OBJECT-TYPE
     SYNTAX     WwpLeosMcastFilterServerPortEntry
     MAX-ACCESS not-accessible
     STATUS     current
     DESCRIPTION
            "An entry (conceptual row) in the wwpLeosMcastFilterServerPortTable."
     INDEX      { wwpLeosMcastVlanId, wwpLeosMcastServerPortId }
     ::= { wwpLeosMcastFilterServerPortTable 1 }

 WwpLeosMcastFilterServerPortEntry ::= SEQUENCE {
     wwpLeosMcastServerPortId         Integer32,
     wwpLeosMcastServerPortStatus     RowStatus
 }

 wwpLeosMcastServerPortId OBJECT-TYPE
     SYNTAX      Integer32 (0..65535)
     MAX-ACCESS  read-only
     STATUS      current
     DESCRIPTION
	    "The server port from which the igmp 
	     query messages can be received, and joins/leaves 
	     messages can be sent."  
     ::= { wwpLeosMcastFilterServerPortEntry 1 }
     
 wwpLeosMcastServerPortStatus OBJECT-TYPE
     SYNTAX      RowStatus
     MAX-ACCESS  read-create
     STATUS      current
     DESCRIPTION
	    "This object is used to add/delete server ports from
	    the list of authorized server ports. To add a port to 
	    the authorized server port list, a user must set this
	    object to 'createAndGo'."  
     ::= { wwpLeosMcastFilterServerPortEntry 2 }

 --
 --  The Mcast IGMP Snoop Config Table
 --

 wwpLeosMcastIgmpSnoopTable OBJECT-TYPE
     SYNTAX     SEQUENCE OF WwpLeosMcastIgmpSnoopEntry
     MAX-ACCESS not-accessible
     STATUS     current
     DESCRIPTION
            "The (conceptual) table listing the config parameters
            for the igmp snooping."
    ::= { wwpLeosMcastFilterConfig 4 }

 wwpLeosMcastIgmpSnoopEntry OBJECT-TYPE
    SYNTAX     WwpLeosMcastIgmpSnoopEntry
    MAX-ACCESS not-accessible
    STATUS     current
    DESCRIPTION
            "An entry (conceptual row) in the wwpLeosMcastIgmpSnoopTable."
    INDEX      { wwpLeosMcastVlanId }
    ::= { wwpLeosMcastIgmpSnoopTable 1 }


 WwpLeosMcastIgmpSnoopEntry ::= SEQUENCE {   
    wwpLeosMcastIgmpSnoopEnable                  TruthValue,    
    wwpLeosMcastIgmpSnoopRobustness              Integer32,
    wwpLeosMcastIgmpSnoopProxyQueryInterval      Integer32,
    wwpLeosMcastIgmpSnoopProxyQueryReplyTmo      Integer32,
    wwpLeosMcastIgmpSnoopProxyQueryDelay         Integer32,
    wwpLeosMcastIgmpSnoopLingerTmo               Integer32,
    wwpLeosMcastIgmpQueryEngineState	     INTEGER,
    wwpLeosMcastIgmpProxyQuerySrcIp		     IpAddress,
    wwpLeosMcastIgmpRouterQueryInterval	     INTEGER,
    wwpLeosMcastIgmpMinResponseTime		     INTEGER,
    wwpLeosMcastIgmpDefaultRouterPort	     INTEGER,
    wwpLeosMcastIgmpInquisitiveLeaveState	     INTEGER,	
    wwpLeosMcastIgmpLastMemberQueryInterval      INTEGER,
    wwpLeosMcastIgmpPriority	             INTEGER,
    wwpLeosMcastIgmpSnoopRouterRangeStartIpAddr  IpAddress,
    wwpLeosMcastIgmpSnoopRouterRangeEndIpAddr    IpAddress,
    wwpLeosMcastIgmpSnoopActiveLingerTimeout     INTEGER,
    wwpLeosMcastIgmpSnoopServerTopology		INTEGER
 }

  
 wwpLeosMcastIgmpSnoopEnable  OBJECT-TYPE
     SYNTAX          TruthValue
     MAX-ACCESS      read-write
     STATUS          current
     DESCRIPTION
    	    "The igmp snooping can be enabled on this vlan
	     by setting this object to 'true'. The Management
	     station should define the router IP address range 
	     and the list of server ports before snooping 
	     is enabled."
       DEFVAL { false }                
     ::= { wwpLeosMcastIgmpSnoopEntry 1 }      
     
 wwpLeosMcastIgmpSnoopRobustness  OBJECT-TYPE
     SYNTAX          Integer32(1..2)
     MAX-ACCESS      read-write
     STATUS          current
     DESCRIPTION
    	    "The number of replies to send for 
	    each multicast group."
     DEFVAL { 1 }              
     ::= { wwpLeosMcastIgmpSnoopEntry 2 }
 
 wwpLeosMcastIgmpSnoopProxyQueryInterval  OBJECT-TYPE
     SYNTAX          Integer32(10..999999)
     UNITS           "seconds"
     MAX-ACCESS      read-write
     STATUS          current
     DESCRIPTION
    	    "The interval period between each general query
	     sent to the router. This parameter specifies how 
	     often to repeat the group specific query.  
	     Default will be 125 seconds.  Note that the actual 
	     rate may be slower when the switch becomes busy, 
	     so this parameter should be thought of as a 
	     minimum time interval."
     DEFVAL { 125 }              
     ::= { wwpLeosMcastIgmpSnoopEntry 3 }
     
 wwpLeosMcastIgmpSnoopProxyQueryReplyTmo  OBJECT-TYPE
     SYNTAX          Integer32(10..255)     
     UNITS           "seconds"
     MAX-ACCESS      read-write
     STATUS          current
     DESCRIPTION
    	    "The amount of time to to receive a membership 
	     report after a query message was sent.
	     This value goes directly into the query packet."     
     ::= { wwpLeosMcastIgmpSnoopEntry 4 }
     
 wwpLeosMcastIgmpSnoopProxyQueryDelay  OBJECT-TYPE
     SYNTAX          Integer32(1..100)
     UNITS           "seconds"
     MAX-ACCESS      read-write
     STATUS          current
     DESCRIPTION
    	    "The amount of time to wait before sending the next 
	     group specific query downstream.  
	     General queries are sent one port at a time." 
     DEFVAL { 50 }              
     ::= { wwpLeosMcastIgmpSnoopEntry 5 }
        
 wwpLeosMcastIgmpSnoopLingerTmo  OBJECT-TYPE
     SYNTAX          Integer32(10..300)
     UNITS           "seconds"
     MAX-ACCESS      read-write
     STATUS          current
     DESCRIPTION
    	    "This value specifies the amount of time that a 
	     multicast filter will be in place after the last 
	     host has left. In essence it configures how long 
	     to filter the stream after all the hosts have left 
             the group. This can tune the system as to how long 
	     the router has to remove the stream from the subnet. 
	     The minimum value is 1 second, with no maximum value."
       DEFVAL { 125 }                
       ::= { wwpLeosMcastIgmpSnoopEntry 6 }
 
  wwpLeosMcastIgmpQueryEngineState  OBJECT-TYPE
     SYNTAX          INTEGER {
			disable(1),
			enable(2)
                     }     
     MAX-ACCESS      read-write
     STATUS          current
     DESCRIPTION
    	    "Setting this object to disable will enable query engine on 
	     a given vlan. Setting it to enable will enable it."       
       ::= { wwpLeosMcastIgmpSnoopEntry 7 }

 wwpLeosMcastIgmpProxyQuerySrcIp  OBJECT-TYPE
     SYNTAX          IpAddress 
     MAX-ACCESS      read-write
     STATUS          current
     DESCRIPTION
    	    "Setting this object will set the source ip address for the vlan."       
       ::= { wwpLeosMcastIgmpSnoopEntry 8 }

 wwpLeosMcastIgmpRouterQueryInterval  OBJECT-TYPE
     SYNTAX          INTEGER (10..999999)
     MAX-ACCESS      read-write
     STATUS          current
     DESCRIPTION
    	    "Setting this object will set the router query interval for given vlan."       
       ::= { wwpLeosMcastIgmpSnoopEntry 9 }

 wwpLeosMcastIgmpMinResponseTime  OBJECT-TYPE
     SYNTAX          INTEGER (50..600)
     MAX-ACCESS      read-write
     STATUS          current
     DESCRIPTION
    	    "Setting this object will set the minimum response time for given vlan."       
       ::= { wwpLeosMcastIgmpSnoopEntry 10 }

 wwpLeosMcastIgmpDefaultRouterPort  OBJECT-TYPE
     SYNTAX          INTEGER (0..65535)
     MAX-ACCESS      read-write
     STATUS          current
     DESCRIPTION
    	    "Setting this object will set the default router port for given vlan."
       ::= { wwpLeosMcastIgmpSnoopEntry 11 }

 wwpLeosMcastIgmpInquisitiveLeaveState  OBJECT-TYPE
     SYNTAX          INTEGER {
			disable(1),
			enable(2)
		     }
     MAX-ACCESS      read-write
     STATUS          current
     DESCRIPTION
    	    "Setting this object will set the igmp inquisitive leave state for given vlan."       
       ::= { wwpLeosMcastIgmpSnoopEntry 12 }
  
  wwpLeosMcastIgmpLastMemberQueryInterval  OBJECT-TYPE
     SYNTAX          INTEGER (10..100)
     MAX-ACCESS      read-write
     STATUS          current
     DESCRIPTION
    	    "Setting this object will set the last membsershil query interval for given vlan."       
       ::= { wwpLeosMcastIgmpSnoopEntry 13 }

   wwpLeosMcastIgmpPriority  OBJECT-TYPE
     SYNTAX          INTEGER (0..7)
     MAX-ACCESS      read-write
     STATUS          current
     DESCRIPTION
    	    "Setting this object will set the priority if IGMP packets  
	     for this vlan."                
     ::= { wwpLeosMcastIgmpSnoopEntry 14 }

   wwpLeosMcastIgmpSnoopRouterRangeStartIpAddr  OBJECT-TYPE
     SYNTAX          IpAddress
     MAX-ACCESS      read-write
     STATUS          current
     DESCRIPTION
    	    "The first IP Address of the router Ip Address range."                
     ::= { wwpLeosMcastIgmpSnoopEntry 15 }  
     
  wwpLeosMcastIgmpSnoopRouterRangeEndIpAddr  OBJECT-TYPE
     SYNTAX          IpAddress
     MAX-ACCESS      read-write
     STATUS          current
     DESCRIPTION
    	    "The last IP Address of the router Ip Address range.
	     When range is undefined, all leave/join 
	     messages will be forwarded to the router even when the 
	     multicast stream does not originate from the router.  
	     If the range is defined, leave/join messages will 
	     be filtered.
	     The default value for this object should be equal 
	     to the value of wwpLeosMcastIgmpSnoopRouterRangeStartIpAddr."                
     ::= { wwpLeosMcastIgmpSnoopEntry 16 }   
  
  wwpLeosMcastIgmpSnoopActiveLingerTimeout  OBJECT-TYPE     
     SYNTAX          INTEGER (0..300)
     UNITS           "seconds"
     MAX-ACCESS      read-write
     STATUS          current
     DESCRIPTION
    	    "The object specifies the active linger timeout in seconds."                
     ::= { wwpLeosMcastIgmpSnoopEntry 17 } 
 
 wwpLeosMcastIgmpSnoopServerTopology  OBJECT-TYPE     
     SYNTAX          INTEGER {
			centralized(1),
			distributed(2)
			}
     MAX-ACCESS      read-write
     STATUS          current
     DESCRIPTION
    	    "The object specifies the server topology."                
     ::= { wwpLeosMcastIgmpSnoopEntry 18 }
 --
 --  The Mcast Channel Stream Config Table
 --

 wwpLeosMcastChannelStreamTable OBJECT-TYPE
     SYNTAX     SEQUENCE OF WwpLeosMcastChannelStreamEntry
     MAX-ACCESS not-accessible
     STATUS     current
     DESCRIPTION
            "The (conceptual) table listing the config parameters
            for the multicast channel stream."
    ::= { wwpLeosMcastFilterConfig 5 }

 wwpLeosMcastChannelStreamEntry OBJECT-TYPE
    SYNTAX     WwpLeosMcastChannelStreamEntry
    MAX-ACCESS not-accessible
    STATUS     current
    DESCRIPTION
            "An entry (conceptual row) in the wwpLeosMcastChannelStreamTable."
    INDEX      { wwpLeosMcastVlanId, wwpLeosMcastChanelStreamStartGroupAddr }
    ::= { wwpLeosMcastChannelStreamTable 1 }

 WwpLeosMcastChannelStreamEntry ::= SEQUENCE { 
    wwpLeosMcastChanelStreamStartGroupAddr       IpAddress,
    wwpLeosMcastChanelStreamEndGroupAddr         IpAddress,
    wwpLeosMcastChannelStreamStatus              RowStatus
 }
 
 wwpLeosMcastChanelStreamStartGroupAddr  OBJECT-TYPE
     SYNTAX          IpAddress
     MAX-ACCESS      read-only
     STATUS          current
     DESCRIPTION
    	    "The first IP Address of the multicast Ip Address range. "                
     ::= { wwpLeosMcastChannelStreamEntry 1 }  
     
 wwpLeosMcastChanelStreamEndGroupAddr  OBJECT-TYPE
     SYNTAX          IpAddress
     MAX-ACCESS      read-write
     STATUS          current
     DESCRIPTION
    	    "The last IP Address of the multicast Ip address range.
	     if range doesnot need to be specifed then don;t set 
	     this value." 
     ::= { wwpLeosMcastChannelStreamEntry 2 }  
       
 wwpLeosMcastChannelStreamStatus OBJECT-TYPE
     SYNTAX      RowStatus
     MAX-ACCESS  read-create
     STATUS      current
     DESCRIPTION
	    "This object is used to add/delete multicast
	     groups to the channel stream. To add a multicast group to 
	     the channel stream, a user must set this object to 'createAndGo'.
	    
	    Device will not allow to create entry unless 'wwpLeosMcastChanelStreamStartGroupAddr'
	    is specfied. If range needs to be specifed then set 'wwpLeosMcastChanelStreamEndGroupAddr'
	    with the desired group address. if device cannot create entry for any of the IP address
	    within the range then no entry will be created and error will be retruned."  
     ::= { wwpLeosMcastChannelStreamEntry 3 }   
  
 --
 --  The Multicast Group Table
 --

 wwpLeosMcastGroupTable OBJECT-TYPE
     SYNTAX     SEQUENCE OF WwpLeosMcastGroupEntry
     MAX-ACCESS not-accessible
     STATUS     current
     DESCRIPTION
            "The (conceptual) table listing all the 
	     multicast groups."
     ::= { wwpLeosMcastFilterStatus 1 }

 wwpLeosMcastGroupEntry OBJECT-TYPE
     SYNTAX     WwpLeosMcastGroupEntry
     MAX-ACCESS not-accessible
     STATUS     current
     DESCRIPTION
            "An entry (conceptual row) in the wwpLeosMcastGroupTable."
     INDEX      { wwpLeosMcastVlanId, wwpLeosMcastGroupAddr }
     ::= { wwpLeosMcastGroupTable 1 }

 WwpLeosMcastGroupEntry ::= SEQUENCE {   
     wwpLeosMcastGroupAddr            IpAddress,
     wwpLeosMcastState                INTEGER,
     wwpLeosMcastType                 INTEGER,
     wwpLeosMcastSource               INTEGER,
     wwpLeosMcastMemberCount          Counter32                              
 }

 wwpLeosMcastGroupAddr   OBJECT-TYPE
     SYNTAX          IpAddress
     MAX-ACCESS      read-only
     STATUS          current
     DESCRIPTION
    	    "The multicast group IP address."                
     ::= { wwpLeosMcastGroupEntry 1 } 
     
 wwpLeosMcastState   OBJECT-TYPE
     SYNTAX          INTEGER {                        
			active(1),
			query(2),
			linger(3)
		     } 
     MAX-ACCESS      read-only
     STATUS          current
     DESCRIPTION
    	    "The current state of the multicast stream."                
     ::= { wwpLeosMcastGroupEntry 2 } 

 wwpLeosMcastType   OBJECT-TYPE
     SYNTAX          INTEGER {
                        static(1),
			dynamic(2)      
		     } 
     MAX-ACCESS      read-only
     STATUS          current
     DESCRIPTION
    	    "The type of the multicast stream."                
     ::= { wwpLeosMcastGroupEntry 3 } 
     
 wwpLeosMcastSource   OBJECT-TYPE
     SYNTAX          INTEGER {
                        router(1),
			server(2)      
		     } 
     MAX-ACCESS      read-only
     STATUS          current
     DESCRIPTION
    	    "The source for this multicast stream."                
     ::= { wwpLeosMcastGroupEntry 4 }
     
 wwpLeosMcastMemberCount  OBJECT-TYPE
     SYNTAX          Counter32
     MAX-ACCESS      read-only
     STATUS          current
     DESCRIPTION
    	    "The number of ports that joined the group." 
     ::= { wwpLeosMcastGroupEntry 5 } 
 
 --
 --  The Multicast Group Port Membership Table
 --

 wwpLeosMcastGroupMemberTable OBJECT-TYPE
     SYNTAX     SEQUENCE OF WwpLeosMcastGroupMemberEntry
     MAX-ACCESS not-accessible
     STATUS     current
     DESCRIPTION
            "The (conceptual) table listing all the 
	     port members of the multicast groups."
     ::= { wwpLeosMcastFilterStatus 2 }

 wwpLeosMcastGroupMemberEntry OBJECT-TYPE
     SYNTAX     WwpLeosMcastGroupMemberEntry
     MAX-ACCESS not-accessible
     STATUS     current
     DESCRIPTION
            "An entry (conceptual row) in the wwpLeosMcastGroupMemberTable."
     INDEX      { wwpLeosMcastVlanId, wwpLeosMcastGroupAddr, wwpLeosMcastPortId }
     ::= { wwpLeosMcastGroupMemberTable 1 }
 
 WwpLeosMcastGroupMemberEntry ::= SEQUENCE {
     wwpLeosMcastPortId               Integer32,
     wwpLeosMcastPortTagId            Integer32
 }
     
 wwpLeosMcastPortId OBJECT-TYPE
     SYNTAX      Integer32 (1..65535)
     MAX-ACCESS  read-only
     STATUS      current
     DESCRIPTION
	    "The router port from which the igmp 
	     query messages are received, and joins/leaves 
	     messages are sent."  
     ::= { wwpLeosMcastGroupMemberEntry 1 }
 
 wwpLeosMcastPortTagId   OBJECT-TYPE
     SYNTAX      Integer32(1..4094)
     MAX-ACCESS  read-only
     STATUS      current
     DESCRIPTION
	    "The Virtual Lan Tag Id used by the port on this
             Virtual Lan. If the switch is being used as a traditional 
	     Layer 2 device, then the value of this object
	     should be same as wwpLeosMcastVlanId."
     ::= { wwpLeosMcastGroupMemberEntry 2 }
     
     
 --
 --  stats group 
 --
 
 --
 --  The Multicast filter Stats Table
 --

 wwpLeosMcastFilterStatsTable OBJECT-TYPE
     SYNTAX     SEQUENCE OF WwpLeosMcastFilterStatsEntry
     MAX-ACCESS not-accessible
     STATUS     current
     DESCRIPTION
            "The (conceptual) table listing the multicast stats."
     ::= { wwpLeosMcastFilterStats 1 }

 wwpLeosMcastFilterStatsEntry OBJECT-TYPE
     SYNTAX     WwpLeosMcastFilterStatsEntry
     MAX-ACCESS not-accessible
     STATUS     current
     DESCRIPTION
            "An entry (conceptual row) in the wwpLeosMcastFilterServerTable."
     INDEX      { wwpLeosMcastVlanId }
     ::= { wwpLeosMcastFilterStatsTable 1 }

 WwpLeosMcastFilterStatsEntry ::= SEQUENCE {   
    wwpLeosMcastStaticGrpCount        INTEGER,
    wwpLeosMcastDynamicGrpCount       INTEGER,
    wwpLeosMcastJoinMessages          Counter32,
    wwpLeosMcastLeaveMessages         Counter32,
    wwpLeosMcastQueryMessages         Counter32,
    wwpLeosMcastQueryDiscards         Counter32,
    wwpLeosMcastQueryTimeouts         Counter32,
    wwpLeosMcastUnknownPktType        Counter32,
    wwpLeosMcastRouterDiscards        Counter32,
    wwpLeosMcastHostDiscards          Counter32,
    wwpLeosMcastBadChecksum           Counter32,
    wwpLeosMcastL2L3Mismatch          Counter32,
    wwpLeosMcastTotalMembers          Counter32,
    wwpLeosMcastLingerCount           Counter32,
    wwpLeosMcastRouterSrcMacAddr      MacAddress,
    wwpLeosMcastRouterSrcIpAddr       IpAddress,
    wwpLeosMcastRouterPortId          INTEGER,
    wwpLeosMcastReportSendPortId      INTEGER
 }

 wwpLeosMcastStaticGrpCount  OBJECT-TYPE
     SYNTAX          INTEGER (0..65535)
     MAX-ACCESS      read-only
     STATUS          current
     DESCRIPTION
    	     "The total number of static mcast group."                              
       ::= { wwpLeosMcastFilterStatsEntry 1 } 

 wwpLeosMcastDynamicGrpCount  OBJECT-TYPE
     SYNTAX          INTEGER(0..65535)
     MAX-ACCESS      read-only
     STATUS          current
     DESCRIPTION
    	     "The total number of dynamic mcast group."                              
       ::= { wwpLeosMcastFilterStatsEntry 2 } 

 wwpLeosMcastJoinMessages  OBJECT-TYPE
     SYNTAX          Counter32
     MAX-ACCESS      read-only
     STATUS          current
     DESCRIPTION
    	     "The total number of join messages received."                              
       ::= { wwpLeosMcastFilterStatsEntry 3 }
       
 wwpLeosMcastLeaveMessages  OBJECT-TYPE
     SYNTAX          Counter32
     MAX-ACCESS      read-only
     STATUS          current
     DESCRIPTION
    	     "The total number of leave messages received."                              
       ::= { wwpLeosMcastFilterStatsEntry 4 }
       
 wwpLeosMcastQueryMessages  OBJECT-TYPE
     SYNTAX          Counter32
     MAX-ACCESS      read-only
     STATUS          current
     DESCRIPTION
    	     "The total number of queries received."                              
       ::= { wwpLeosMcastFilterStatsEntry 5 }
       
 wwpLeosMcastQueryDiscards  OBJECT-TYPE
     SYNTAX          Counter32
     MAX-ACCESS      read-only
     STATUS          current
     DESCRIPTION
    	     "The total number of queries discarded."                              
       ::= { wwpLeosMcastFilterStatsEntry 6 }
       
 wwpLeosMcastQueryTimeouts  OBJECT-TYPE
     SYNTAX          Counter32
     MAX-ACCESS      read-only
     STATUS          current
     DESCRIPTION
    	     "The total number of timeouts waiting for the
	      router to send query."                              
       ::= { wwpLeosMcastFilterStatsEntry 7 }
       
 wwpLeosMcastUnknownPktType  OBJECT-TYPE
     SYNTAX          Counter32
     MAX-ACCESS      read-only
     STATUS          current
     DESCRIPTION
    	     "The total number of unknown (unknown type ) IGMP 
	      packets received."                              
       ::= { wwpLeosMcastFilterStatsEntry 8 }
       
 wwpLeosMcastRouterDiscards  OBJECT-TYPE
     SYNTAX          Counter32
     MAX-ACCESS      read-only
     STATUS          current
     DESCRIPTION
    	     "The total number of messages discraded by the
	      router. This happens when join comes in from 
	      a router port."                              
       ::= { wwpLeosMcastFilterStatsEntry 9 }
       
 wwpLeosMcastHostDiscards  OBJECT-TYPE
     SYNTAX          Counter32
     MAX-ACCESS      read-only
     STATUS          current
     DESCRIPTION
    	     "The total number of messages discraded by the
	      host. This happens when when a join/leave comes 
	      in a port, but no router port is established."                              
       ::= { wwpLeosMcastFilterStatsEntry 10 }
       
 wwpLeosMcastBadChecksum  OBJECT-TYPE
     SYNTAX          Counter32
     MAX-ACCESS      read-only
     STATUS          current
     DESCRIPTION
    	     "The total number of packets received with bad 
	      IP checksum."                              
       ::= { wwpLeosMcastFilterStatsEntry 11 }  
       
 wwpLeosMcastL2L3Mismatch  OBJECT-TYPE
     SYNTAX          Counter32
     MAX-ACCESS      read-only
     STATUS          current
     DESCRIPTION
    	     "The total number of IGMP Layer2 / Layer 3 mismatch packets
	      received."                              
       ::= { wwpLeosMcastFilterStatsEntry 12 }

 wwpLeosMcastTotalMembers OBJECT-TYPE
     SYNTAX          Counter32
     MAX-ACCESS      read-only
     STATUS          current
     DESCRIPTION
    	     "The total number of group members for all groups in the given vlan."                              
       ::= { wwpLeosMcastFilterStatsEntry 13 }

 wwpLeosMcastLingerCount OBJECT-TYPE
     SYNTAX          Counter32
     MAX-ACCESS      read-only
     STATUS          current
     DESCRIPTION
    	     "The total number of groups in linger state."                              
       ::= { wwpLeosMcastFilterStatsEntry 14 }

 wwpLeosMcastRouterSrcMacAddr  OBJECT-TYPE
     SYNTAX          MacAddress
     MAX-ACCESS      read-only
     STATUS          current
     DESCRIPTION
    	     "Specfies the router's mac address."                              
       ::= { wwpLeosMcastFilterStatsEntry 15 }

 wwpLeosMcastRouterSrcIpAddr  OBJECT-TYPE
     SYNTAX          IpAddress
     MAX-ACCESS      read-only
     STATUS          current
     DESCRIPTION
    	     "Specfies the router's Ip address."                              
       ::= { wwpLeosMcastFilterStatsEntry 16 }

 wwpLeosMcastRouterPortId  OBJECT-TYPE
     SYNTAX          INTEGER (0..65535)
     MAX-ACCESS      read-only
     STATUS          current
     DESCRIPTION
    	     "Specfies the port from where router queries are coming."
       ::= { wwpLeosMcastFilterStatsEntry 17 }
       
 wwpLeosMcastReportSendPortId  OBJECT-TYPE
     SYNTAX          INTEGER (0..65535)
     MAX-ACCESS      read-only
     STATUS          current
     DESCRIPTION
    	     "The new value is the port number of the port where igmp 
	      reports will be sent.  Not always the same as the router port."
       ::= { wwpLeosMcastFilterStatsEntry 18 }

 --
 --  The Multicast UPF filter Activation Table
 --

 wwpLeosMcastFilterConfigTable OBJECT-TYPE
     SYNTAX     SEQUENCE OF WwpLeosMcastFilterConfigEntry
     MAX-ACCESS not-accessible
     STATUS     current
     DESCRIPTION
            "The (conceptual) table listing the vlans on which the
             UPF can be applied."
    ::= { wwpLeosMcastFilterConfig 6 }

 wwpLeosMcastFilterConfigEntry OBJECT-TYPE
     SYNTAX     WwpLeosMcastFilterConfigEntry
     MAX-ACCESS not-accessible
     STATUS     current
     DESCRIPTION
            "An entry (conceptual row) in the wwpLeosMcastFilterConfigTable."
     INDEX      { wwpLeosMcastVlanId }
     ::= { wwpLeosMcastFilterConfigTable 1 }

 WwpLeosMcastFilterConfigEntry ::= SEQUENCE {     
     wwpLeosMcastFilterUPFActivate       TruthValue,     
     wwpLeosMcastUnresolvedAction        INTEGER,
     wwpLeosMcastFilterWKMFLocalActivate INTEGER,
     wwpLeosMcastFilterWKMFInternetActivate INTEGER,
     wwpLeosMcastFilterWKMFAdhocActivate INTEGER,
     wwpLeosMcastFilterWKMFStMulticastActivate INTEGER,
     wwpLeosMcastFilterWKMFSdpSapActivate INTEGER
 }
      
 wwpLeosMcastFilterUPFActivate  OBJECT-TYPE
     SYNTAX          TruthValue
     MAX-ACCESS      read-write
     STATUS          current
     DESCRIPTION
    	    "UPF can be enabled on this vlan
	     by setting this object to 'true'."
     DEFVAL { false }      
     ::= { wwpLeosMcastFilterConfigEntry 1 } 

 wwpLeosMcastUnresolvedAction  OBJECT-TYPE
     SYNTAX          INTEGER {
                        flood(1),
			drop(2)
		     }
     MAX-ACCESS      read-write
     STATUS          current
     DESCRIPTION
    	    "Setting this object to 'flood' will cause the 
	     device to flood all the unresolved messages to 
	     all the ports in the vlan.
	     
	     Setting this object to 'drop' will cause the 
	     device to drop all the unresolved messages. 
	     If an IGMP join is received with a matching multicast 
	     group address, the multicast stream will forward to the 
	     corresponding port."                
     ::= { wwpLeosMcastFilterConfigEntry 2 }  

 wwpLeosMcastFilterWKMFLocalActivate  OBJECT-TYPE
     SYNTAX          INTEGER {
                        flood(1),
			drop(2)
		     }
     MAX-ACCESS      read-write
     STATUS          current
     DESCRIPTION
    	    "Setting the object to flood will enable flooding of local wkmf 
	     on a vlan. 
	     Setting the object to drop will enable droping of local wkmf 
	     on a vlan.
	     Multicast address belonging to this object is 224.0.0.x."     
     ::= { wwpLeosMcastFilterConfigEntry 3 }

 wwpLeosMcastFilterWKMFInternetActivate  OBJECT-TYPE
     SYNTAX          INTEGER {
                        flood(1),
			drop(2)
		     }
     MAX-ACCESS      read-write
     STATUS          current
     DESCRIPTION
    	    "Setting the object to flood will enable flooding of internet wkmf 
	     on a vlan. 
	     Setting the object to drop will enable droping of internet wkmf 
	     on a vlan.
	     Multicast address belonging to this object is 224.0.1.x."     
     ::= { wwpLeosMcastFilterConfigEntry 4 }
 
 wwpLeosMcastFilterWKMFAdhocActivate  OBJECT-TYPE
     SYNTAX          INTEGER {
                        flood(1),
			drop(2)
		     }
     MAX-ACCESS      read-write
     STATUS          current
     DESCRIPTION
    	    "Setting the object to flood will enable flooding of adhoc wkmf 
	     on a vlan.
	     Setting the object to drop will enable droping of adhoc wkmf 
	     on a vlan.
	     Multicast address belonging to this object is 
	     224.0.2.x to 224.0.255.x."     
     ::= { wwpLeosMcastFilterConfigEntry 5 }
 
 wwpLeosMcastFilterWKMFStMulticastActivate  OBJECT-TYPE
     SYNTAX          INTEGER {
                        flood(1),
			drop(2)
		     }
     MAX-ACCESS      read-write
     STATUS          current
     DESCRIPTION
    	    "Setting the object to flood will enable flooding of st-multicast
	     wkmf on a vlan. 
	     Setting the object to drop will enable droping of st-multicast wkmf 
	     on a vlan.
	     Multicast address belonging to this object is 224.1.x.x."     
     ::= { wwpLeosMcastFilterConfigEntry 6 }

 wwpLeosMcastFilterWKMFSdpSapActivate  OBJECT-TYPE
     SYNTAX          INTEGER {
                        flood(1),
			drop(2)
		     }
     MAX-ACCESS      read-write
     STATUS          current
     DESCRIPTION
    	    "Setting the object to flood will enable flooding of sdp-sap wkmf 
	     on a vlan. 
	     Setting the object to drop will enable droping of sdp-sap wkmf 
	     on a vlan.
	     Multicast address belonging to this object is 224.2.x.x."     
     ::= { wwpLeosMcastFilterConfigEntry 7 }

 --
 --  The Multicast Channel Stream Exclude Port List
 --

 wwpLeosMcastChannelStreamExPortMemTable OBJECT-TYPE
     SYNTAX     SEQUENCE OF WwpLeosMcastChannelStreamExPortMemEntry
     MAX-ACCESS not-accessible
     STATUS     current
     DESCRIPTION
            "The (conceptual) table listing the excluded port list
             per vlan for channel stream."
    ::= { wwpLeosMcastFilterConfig 7 }

 wwpLeosMcastChannelStreamExPortMemEntry OBJECT-TYPE
     SYNTAX     WwpLeosMcastChannelStreamExPortMemEntry
     MAX-ACCESS not-accessible
     STATUS     current
     DESCRIPTION
            "An entry (conceptual row) in the wwpLeosMcastChannelStreamExPortMemTable."
     INDEX      { wwpLeosMcastVlanId, wwpLeosMcastChannelStreamExPortId}
     ::= { wwpLeosMcastChannelStreamExPortMemTable 1 }

 WwpLeosMcastChannelStreamExPortMemEntry ::= SEQUENCE {     
     wwpLeosMcastChannelStreamExPortId		INTEGER,
     wwpLeosMcastChannelStreamExPortMemStatus	RowStatus
 }
 
 wwpLeosMcastChannelStreamExPortId  OBJECT-TYPE
     SYNTAX          INTEGER (1..65535)
     MAX-ACCESS      read-only
     STATUS          current
     DESCRIPTION
    	    "The port num to be excluded from channel stream."     
     ::= { wwpLeosMcastChannelStreamExPortMemEntry 1 }

 wwpLeosMcastChannelStreamExPortMemStatus  OBJECT-TYPE
     SYNTAX          RowStatus
     MAX-ACCESS      read-create
     STATUS          current
     DESCRIPTION
    	    "Setting this object to createAndGo will add wwpLeosMcastVlanId and 
	     wwpLeosMcastChannelStreamExPortId in the excluded port list of 
	     channel stream. Setting this to destory will remove the 
	     wwpLeosMcastVlanId, wwpLeosMcastChannelStreamExPortId membership
	     from excluded port list."
     ::= { wwpLeosMcastChannelStreamExPortMemEntry 2 }  

 -- 
 -- Notifications
 --
 wwpLeosMcastAddrOverlapNotification NOTIFICATION-TYPE	
	STATUS	current
	DESCRIPTION
		"A wwpLeosMcastAddrOverlapNotification is sent whenever 
		 several multicast Ip addresses overlap (matches the 
		 same L2 address)."
	::= { wwpLeosMcastFilterMIBNotifications 1 }
 END
 
 -- 
 -- WWP-MULTICAST-FILTER-MIB
 --
