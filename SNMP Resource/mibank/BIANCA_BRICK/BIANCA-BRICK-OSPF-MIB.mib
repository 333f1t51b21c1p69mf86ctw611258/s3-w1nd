-- This file is corresponding to Release 5.2.1.100 from 2000/11/08 00:00:00
-- (C)opyright 1991-1999 BinTec Communications AG, All Rights Reserved
--  $RCSfile: mibbospf,v $ 
-- $Revision: 1.4 $ 

BIANCA-BRICK-OSPF-MIB DEFINITIONS ::= BEGIN
 
        IMPORTS
            IpAddress, Counter, enterprises
                FROM RFC1155-SMI
 
            OBJECT-TYPE
                FROM RFC-1212;

  --  org		OBJECT IDENTIFIER ::= { iso 3 }
  --  dod		OBJECT IDENTIFIER ::= { org 6 }
  --  internet	OBJECT IDENTIFIER ::= { dod 1 }
  --  private	OBJECT IDENTIFIER ::= { internet 4 }
  --  enterprises	OBJECT IDENTIFIER ::= { private 1 }

    bintec 	OBJECT IDENTIFIER ::= { enterprises 272 }
    bibo	OBJECT IDENTIFIER ::= { bintec 4 }
    biboip      OBJECT IDENTIFIER ::= { bibo 5 }
    ospfStat	OBJECT IDENTIFIER ::= { biboip 10 }

-- OSPF MIB

	ospfStatHelloRecv OBJECT-TYPE
	    SYNTAX Counter
	    ACCESS read-only
	    STATUS mandatory
	    DESCRIPTION
		"Counts the number of Hello packets received."
	::= { ospfStat 1 }

	ospfStatHelloSent OBJECT-TYPE
	    SYNTAX Counter
	    ACCESS read-only
	    STATUS mandatory
	    DESCRIPTION
		"Counts the number of Hello packets sent."
	::= { ospfStat 2 }

	ospfStatDdRecv OBJECT-TYPE
	    SYNTAX Counter
	    ACCESS read-only
	    STATUS mandatory
	    DESCRIPTION
		"Counts the number of Database Description packets received."
	::= { ospfStat 3 }

	ospfStatDdSent OBJECT-TYPE
	    SYNTAX Counter
	    ACCESS read-only
	    STATUS mandatory
	    DESCRIPTION
		"Counts the number of Database Description packets sent."
	::= { ospfStat 4 }

	ospfStatLsackRecv OBJECT-TYPE
	    SYNTAX Counter
	    ACCESS read-only
	    STATUS mandatory
	    DESCRIPTION
		"Counts the number of Link State Acknowledge packets received."
	::= { ospfStat 5 }

	ospfStatLsackSent OBJECT-TYPE
	    SYNTAX Counter
	    ACCESS read-only
	    STATUS mandatory
	    DESCRIPTION
		"Counts the number of Link State Acknowledge packets sent."
	::= { ospfStat 6 }

	ospfStatLsreqRecv OBJECT-TYPE
	    SYNTAX Counter
	    ACCESS read-only
	    STATUS mandatory
	    DESCRIPTION
		"Counts the number of Link State Request packets received."
	::= { ospfStat 7 }

	ospfStatLsreqSent OBJECT-TYPE
	    SYNTAX Counter
	    ACCESS read-only
	    STATUS mandatory
	    DESCRIPTION
		"Counts the number of Link State Request packets sent"
	::= { ospfStat 8 }

	ospfStatLsupdRecv OBJECT-TYPE
	    SYNTAX Counter
	    ACCESS read-only
	    STATUS mandatory
	    DESCRIPTION
		"Counts the number of Link State Update packets received."
	::= { ospfStat 9 }

	ospfStatLsupdSent OBJECT-TYPE
	    SYNTAX Counter
	    ACCESS read-only
	    STATUS mandatory
	    DESCRIPTION
		"Counts the number of Link State Update packets sent."
	::= { ospfStat 10 }

	ospfStatSummaryIncUpd OBJECT-TYPE
	    SYNTAX Counter
	    ACCESS read-only
	    STATUS mandatory
	    DESCRIPTION
		"Counts the number of incremental routing table updates 
		 performed due to reception of new Summary Links Advertisments."
	::= { ospfStat 11 }

	ospfStatExternalIncUpd OBJECT-TYPE
	    SYNTAX Counter
	    ACCESS read-only
	    STATUS mandatory
	    DESCRIPTION
		"Counts the number of incremental routing table updates 
		 performed due to reception of new External Advertisments."
	::= { ospfStat 12 }
END
