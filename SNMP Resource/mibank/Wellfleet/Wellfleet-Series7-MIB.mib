Wellfleet-Series7-MIB

-- Creation date            : Mon Apr 12 14:07:33 PDT 1993
-- Series 7 Software Release: 7.55

-- Copyright 1993 Wellfleet Communications, Inc.  All Rights
-- Reserved.  Reproduction of this document is authorized on
-- condition that the foregoing copyright notice is included.
-- This Wellfleet SNMP Management Information Base Specification
-- (Specification) embodies Wellfleet's confidential and
-- proprietary intellectual property.  Wellfleet retains all
-- title and ownership in the Specification, including any
-- revisions.
--
-- It is Wellfleet's intent to encourage the widespread use of
-- this Specification in connection with the management of
-- Wellfleet products. Wellfleet grants vendors, end-users,
-- and other interested parties a non-exclusive license to
-- use this Specification in connection with the management
-- of Wellfleet products utilizing series 7.xx system software.
--
-- This Specification is supplied "AS IS", and Wellfleet makes
-- no warranty, either expressed or implied, as to the use,
-- operation, condition, or performance of the Specification.

-- Copyright text courtesy of D. Perkins.


DEFINITIONS ::= BEGIN

IMPORTS

  IpAddress, Counter, Gauge, TimeTicks, Opaque, enterprises
    FROM RFC1155-SMI
  OBJECT-TYPE
    FROM RFC-1212
  DisplayString
    FROM RFC1213-MIB;

wellfleet	OBJECT IDENTIFIER ::= { enterprises 18 }
wfSwSeries7	OBJECT IDENTIFIER ::= { wellfleet 3 }

wfHardwareConfig	OBJECT IDENTIFIER ::= { wfSwSeries7 1 }
wfSoftwareConfig	OBJECT IDENTIFIER ::= { wfSwSeries7 2 }
wfSystem	OBJECT IDENTIFIER ::= { wfSwSeries7 3 }
wfServices	OBJECT IDENTIFIER ::= { wfSystem 2 }
wfGameGroup	OBJECT IDENTIFIER ::= { wfServices 5 }
wfLine		OBJECT IDENTIFIER ::= { wfSwSeries7 4 }
wfHwFGroup	OBJECT IDENTIFIER ::= { wfLine 6 }
wfDs1Group	OBJECT IDENTIFIER ::= { wfLine 12 }
wfDs3Group	OBJECT IDENTIFIER ::= { wfLine 13 }
wfSipGroup	OBJECT IDENTIFIER ::= { wfLine 14 }
wfSipPlcpGroup	OBJECT IDENTIFIER ::= { wfSipGroup 2 }
wfFddiGroup	OBJECT IDENTIFIER ::= { wfLine 15 }
wfFddiSmtGroup	OBJECT IDENTIFIER ::= { wfFddiGroup 1 }
wfFddiMacGroup	OBJECT IDENTIFIER ::= { wfFddiGroup 2 }
wfFddiPathGroup	OBJECT IDENTIFIER ::= { wfFddiGroup 3 }
wfFddiPortGroup	OBJECT IDENTIFIER ::= { wfFddiGroup 4 }
wfApplication	OBJECT IDENTIFIER ::= { wfSwSeries7 5 }
wfDataLink	OBJECT IDENTIFIER ::= { wfApplication 1 }
wfBridgeGroup	OBJECT IDENTIFIER ::= { wfDataLink 1 }
wfBrLearning	OBJECT IDENTIFIER ::= { wfBridgeGroup 1 }
wfBrSourceRouting	OBJECT IDENTIFIER ::= { wfBridgeGroup 2 }
wfSpanningTree	OBJECT IDENTIFIER ::= { wfDataLink 2 }
wfIfGroup	OBJECT IDENTIFIER ::= { wfDataLink 3 }
wfCircuitOptsGroup	OBJECT IDENTIFIER ::= { wfDataLink 4 }
wfDecGroup	OBJECT IDENTIFIER ::= { wfApplication 2 }
wfInternet	OBJECT IDENTIFIER ::= { wfApplication 3 }
wfArpGroup	OBJECT IDENTIFIER ::= { wfInternet 1 }
wfIpRouting	OBJECT IDENTIFIER ::= { wfInternet 2 }
wfIpGroup	OBJECT IDENTIFIER ::= { wfIpRouting 1 }
wfRipGroup	OBJECT IDENTIFIER ::= { wfIpRouting 2 }
wfOspfGroup	OBJECT IDENTIFIER ::= { wfIpRouting 3 }
wfEgpGroup	OBJECT IDENTIFIER ::= { wfIpRouting 4 }
wfBgpGroup	OBJECT IDENTIFIER ::= { wfIpRouting 5 }
wfTcpGroup	OBJECT IDENTIFIER ::= { wfInternet 3 }
wfUdpGroup	OBJECT IDENTIFIER ::= { wfInternet 4 }
wfSnmpGroup	OBJECT IDENTIFIER ::= { wfInternet 5 }
wfTelnetGroup	OBJECT IDENTIFIER ::= { wfInternet 7 }
wfBootpGroup	OBJECT IDENTIFIER ::= { wfInternet 8 }
wfAppletalkGroup	OBJECT IDENTIFIER ::= { wfApplication 4 }
wfIpxGroup	OBJECT IDENTIFIER ::= { wfApplication 5 }
wfOsiGroup	OBJECT IDENTIFIER ::= { wfApplication 6 }
wfVinesGroup	OBJECT IDENTIFIER ::= { wfApplication 8 }
wfWanGroup	OBJECT IDENTIFIER ::= { wfApplication 9 }
wfFrameRelayGroup	OBJECT IDENTIFIER ::= { wfWanGroup 1 }
wfPppGroup	OBJECT IDENTIFIER ::= { wfWanGroup 2 }
wfX25Group	OBJECT IDENTIFIER ::= { wfWanGroup 4 }
wfAtmGroup	OBJECT IDENTIFIER ::= { wfWanGroup 5 }
wfXnsGroup	OBJECT IDENTIFIER ::= { wfApplication 10 }
wfTestGroup	OBJECT IDENTIFIER ::= { wfApplication 11 }

--
-- Definitions (in alphabetical order)
--

wfAppleBase	OBJECT IDENTIFIER ::= { wfAppletalkGroup 1 }

wfAppleBaseDelete OBJECT-TYPE
	SYNTAX	INTEGER {
		created(1),
		deleted(2)
	}
	ACCESS	read-write
	STATUS	mandatory
	DESCRIPTION
		" Create/Delete parameter for determining whether
		  or not AppleTalk is configured on this slot.
		     "
	DEFVAL	{ created }
	::= { wfAppleBase 1 }

wfAppleBaseDisable OBJECT-TYPE
	SYNTAX	INTEGER {
		enabled(1),
		disabled(2)
	}
	ACCESS	read-write
	STATUS	mandatory
	DESCRIPTION
		" Enable/Disable parameter for determining whether
		  or not to startup AppleTalk.
		     "
	DEFVAL	{ enabled }
	::= { wfAppleBase 2 }

wfAppleBaseState OBJECT-TYPE
	SYNTAX	INTEGER {
		up(1),
		down(2),
		init(3),
		notpres(4)
	}
	ACCESS	read-only
	STATUS	mandatory
	DESCRIPTION
		" This parameter relfects the current state of AppleTalk. "
	DEFVAL	{ down }
	::= { wfAppleBase 3 }

wfAppleBaseDebugLevel OBJECT-TYPE
	SYNTAX	INTEGER
	ACCESS	read-write
	STATUS	mandatory
	DESCRIPTION
		" Appletalk has control of what debug and info messages
		  are printed.
		     "
	::= { wfAppleBase 4 }

wfAppleBaseDdpQueLen OBJECT-TYPE
	SYNTAX	INTEGER {
		default(20)
	}
	ACCESS	read-write
	STATUS	mandatory
	DESCRIPTION
		" Queue clipping is done on all packets destined for the port.
		  This is the length of the queue.
		     "
	DEFVAL	{ default }
	::= { wfAppleBase 5 }

wfAppleBaseHomedPort OBJECT-TYPE
	SYNTAX	INTEGER
	ACCESS	read-write
	STATUS	mandatory
	DESCRIPTION
		" The circuit number of the port on which NBP will register this
		  router.
		     "
	::= { wfAppleBase 6 }

wfAppleBaseTotalNets OBJECT-TYPE
	SYNTAX	INTEGER
	ACCESS	read-only
	STATUS	mandatory
	DESCRIPTION
		" The circuit number of the port on which NBP will register this
		  router.
		     "
	::= { wfAppleBase 7 }

wfAppleBaseTotalZones OBJECT-TYPE
	SYNTAX	INTEGER
	ACCESS	read-only
	STATUS	mandatory
	DESCRIPTION
		" The circuit number of the port on which NBP will register this
		  router.
		     "
	::= { wfAppleBase 8 }

wfAppleRtmpTable OBJECT-TYPE
	SYNTAX	SEQUENCE OF WfAppleRtmpEntry
	ACCESS	not-accessible
	STATUS	mandatory
	DESCRIPTION
		" The table of elements of AppleTalk's routing RTMP table "
	::= { wfAppletalkGroup 2 }

wfAppleRtmpEntry OBJECT-TYPE
	SYNTAX	WfAppleRtmpEntry
	ACCESS	not-accessible
	STATUS	mandatory
	DESCRIPTION
		" An entry in the Routing table "
	INDEX	{ wfAppleRtmpNetStart,
		wfAppleRtmpNetEnd }
	::= { wfAppleRtmpTable 1 }

WfAppleRtmpEntry ::= SEQUENCE {
	wfAppleRtmpNetStart
		INTEGER,
	wfAppleRtmpNetEnd
		INTEGER,
	wfAppleRtmpPort
		INTEGER,
	wfAppleRtmpHops
		INTEGER,
	wfAppleRtmpNextHopNet
		INTEGER,
	wfAppleRtmpNextHopNode
		INTEGER,
	wfAppleRtmpState
		INTEGER
}

wfAppleRtmpNetStart OBJECT-TYPE
	SYNTAX	INTEGER
	ACCESS	read-only
	STATUS	mandatory
	DESCRIPTION
		" The destinatination network range of this
		  route to which this entry pertains.  The route 
		  is considered the best route to that network. 
		  There wil only be one route to a single destination.  
		  The address will be in the form of 
		  [network min - network max].
		      "
	::= { wfAppleRtmpEntry 1 }

wfAppleRtmpNetEnd OBJECT-TYPE
	SYNTAX	INTEGER
	ACCESS	read-only
	STATUS	mandatory
	DESCRIPTION
		" The network max in the destination network range
		  to which the routing entry pertains.
		      "
	::= { wfAppleRtmpEntry 2 }

wfAppleRtmpPort OBJECT-TYPE
	SYNTAX	INTEGER
	ACCESS	read-only
	STATUS	mandatory
	DESCRIPTION
		" The index value which uniquely identifies the
		  local interface through which the next hop of 
		  this route should be reached.  The interface 
		  identified by a particular value of this index 
		  is the same interface as identified by the same 
		  value of ifIndex.
		      "
	::= { wfAppleRtmpEntry 3 }

wfAppleRtmpHops OBJECT-TYPE
	SYNTAX	INTEGER
	ACCESS	read-only
	STATUS	mandatory
	DESCRIPTION
		" The routing metric to get to this destination
		  network.  The measurement is in terms of hops.
		      "
	::= { wfAppleRtmpEntry 4 }

wfAppleRtmpNextHopNet OBJECT-TYPE
	SYNTAX	INTEGER
	ACCESS	read-only
	STATUS	mandatory
	DESCRIPTION
		" The AppleTalk net of the next hop router for this route.
		      "
	::= { wfAppleRtmpEntry 5 }

wfAppleRtmpNextHopNode OBJECT-TYPE
	SYNTAX	INTEGER
	ACCESS	read-only
	STATUS	mandatory
	DESCRIPTION
		" The AppleTalk node of the next hop router for this route.
		      "
	::= { wfAppleRtmpEntry 6 }

wfAppleRtmpState OBJECT-TYPE
	SYNTAX	INTEGER {
		good(1),
		suspect(2),
		goingbad(3),
		bad(4)
	}
	ACCESS	read-write
	STATUS	mandatory
	DESCRIPTION
		" The state of this routing entry: (G)ood,
		  (S)uspect, (GB) GoingBad, or (B)ad. Setting
		  this object to the value bad(4) has the effect
		  of invalidating the corresponding entry in 
		  the RTMP table.
		      "
	::= { wfAppleRtmpEntry 7 }

wfApplePortTable OBJECT-TYPE
	SYNTAX	SEQUENCE OF WfApplePortEntry
	ACCESS	not-accessible
	STATUS	mandatory
	DESCRIPTION
		" The port descriptor table that describes the
		  configuration parameters for this port of 
		  the AppleTalk Router.
		  "
	::= { wfAppletalkGroup 3 }

wfApplePortEntry OBJECT-TYPE
	SYNTAX	WfApplePortEntry
	ACCESS	not-accessible
	STATUS	mandatory
	DESCRIPTION
		" An entry in the Port Descriptor table "
	INDEX	{ wfApplePortCircuit }
	::= { wfApplePortTable 1 }

WfApplePortEntry ::= SEQUENCE {
	wfApplePortDelete
		INTEGER,
	wfApplePortDisable
		INTEGER,
	wfApplePortCircuit
		INTEGER,
	wfApplePortState
		INTEGER,
	wfApplePortType
		INTEGER,
	wfApplePortCksumDisable
		INTEGER,
	wfApplePortTrEndStation
		INTEGER,
	wfApplePortGniForever
		INTEGER,
	wfApplePortAarpFlush
		INTEGER,
	wfApplePortMacAddress
		OCTET STRING,
	wfApplePortNodeId
		INTEGER,
	wfApplePortNetwork
		INTEGER,
	wfApplePortNetStart
		INTEGER,
	wfApplePortNetEnd
		INTEGER,
	wfApplePortDfltZone
		DisplayString,
	wfApplePortCurMacAddress
		OCTET STRING,
	wfApplePortCurNodeId
		INTEGER,
	wfApplePortCurNetwork
		INTEGER,
	wfApplePortCurNetStart
		INTEGER,
	wfApplePortCurNetEnd
		INTEGER,
	wfApplePortCurDfltZone
		DisplayString,
	wfApplePortAarpProbeRxs
		Counter,
	wfApplePortAarpProbeTxs
		Counter,
	wfApplePortAarpReqRxs
		Counter,
	wfApplePortAarpReqTxs
		Counter,
	wfApplePortAarpRspRxs
		Counter,
	wfApplePortAarpRspTxs
		Counter,
	wfApplePortDdpOutRequests
		Counter,
	wfApplePortDdpInReceives
		Counter,
	wfApplePortDdpInLocalDatagrams
		Counter,
	wfApplePortDdpNoProtocolHandlers
		Counter,
	wfApplePortDdpTooShortErrors
		Counter,
	wfApplePortDdpTooLongErrors
		Counter,
	wfApplePortDdpChecksumErrors
		Counter,
	wfApplePortDdpForwRequests
		Counter,
	wfApplePortDdpOutNoRoutes
		Counter,
	wfApplePortDdpBroadcastErrors
		Counter,
	wfApplePortDdpHopCountErrors
		Counter,
	wfApplePortRtmpInDataPkts
		Counter,
	wfApplePortRtmpOutDataPkts
		Counter,
	wfApplePortRtmpInRequestPkts
		Counter,
	wfApplePortRtmpNextIREqualChanges
		Counter,
	wfApplePortRtmpNextIRLessChanges
		Counter,
	wfApplePortRtmpRouteDeletes
		Counter,
	wfApplePortRtmpNetworkMismatchErrors
		Counter,
	wfApplePortRtmpRoutingTableOverflows
		Counter,
	wfApplePortZipInZipQueries
		Counter,
	wfApplePortZipInZipReplies
		Counter,
	wfApplePortZipOutZipReplies
		Counter,
	wfApplePortZipInZipExtendedReplies
		Counter,
	wfApplePortZipOutZipExtendedReplies
		Counter,
	wfApplePortZipInGetZoneLists
		Counter,
	wfApplePortZipOutGetZoneListReplies
		Counter,
	wfApplePortZipInGetLocalZones
		Counter,
	wfApplePortZipOutGetLocalZoneReplies
		Counter,
	wfApplePortZipInGetMyZones
		Counter,
	wfApplePortZipOutGetMyZoneReplies
		Counter,
	wfApplePortZipZoneConflictErrors
		Counter,
	wfApplePortZipInGetNetInfos
		Counter,
	wfApplePortZipOutGetNetInfoReplies
		Counter,
	wfApplePortZipZoneOutInvalids
		Counter,
	wfApplePortZipAddressInvalids
		Counter,
	wfApplePortZipOutGetNetInfos
		Counter,
	wfApplePortZipInGetNetInfoReplies
		Counter,
	wfApplePortZipOutZipQueries
		Counter,
	wfApplePortZipInErrors
		Counter,
	wfApplePortNbpInLookUpRequests
		Counter,
	wfApplePortNbpInLookUpReplies
		Counter,
	wfApplePortNbpInBroadcastRequests
		Counter,
	wfApplePortNbpInForwardRequests
		Counter,
	wfApplePortNbpOutLookUpRequests
		Counter,
	wfApplePortNbpOutLookUpReplies
		Counter,
	wfApplePortNbpOutBroadcastRequests
		Counter,
	wfApplePortNbpOutForwardRequests
		Counter,
	wfApplePortNbpRegistrationFailures
		Counter,
	wfApplePortNbpInErrors
		Counter,
	wfApplePortEchoRequests
		Counter,
	wfApplePortEchoReplies
		Counter
}

wfApplePortDelete OBJECT-TYPE
	SYNTAX	INTEGER {
		created(1),
		deleted(2)
	}
	ACCESS	read-write
	STATUS	mandatory
	DESCRIPTION
		" Create/Delete parameter. Users perform an SNMP SET
		  operation on this object to create/delete an AppleTalk 
		  interface. The default is create.
		      "
	DEFVAL	{ created }
	::= { wfApplePortEntry 1 }

wfApplePortDisable OBJECT-TYPE
	SYNTAX	INTEGER {
		enabled(1),
		disabled(2)
	}
	ACCESS	read-write
	STATUS	mandatory
	DESCRIPTION
		" Enable/Disable parameter. Users perforn an SNMP SET
		  operation on this object to enable/disable an AppleTalk
		  interface.  Default is enabled.
		      "
	DEFVAL	{ enabled }
	::= { wfApplePortEntry 2 }

wfApplePortCircuit OBJECT-TYPE
	SYNTAX	INTEGER
	ACCESS	read-only
	STATUS	mandatory
	DESCRIPTION
		" The circuit number for this interface "
	::= { wfApplePortEntry 3 }

wfApplePortState OBJECT-TYPE
	SYNTAX	INTEGER {
		up(1),
		down(2)
	}
	ACCESS	read-only
	STATUS	mandatory
	DESCRIPTION
		" The current state of the AppleTalk port. "
	DEFVAL	{ down }
	::= { wfApplePortEntry 4 }

wfApplePortType OBJECT-TYPE
	SYNTAX	INTEGER
	ACCESS	read-only
	STATUS	mandatory
	DESCRIPTION
		" The type for the port "
	::= { wfApplePortEntry 5 }

wfApplePortCksumDisable OBJECT-TYPE
	SYNTAX	INTEGER {
		enabled(1),
		disabled(2)
	}
	ACCESS	read-write
	STATUS	mandatory
	DESCRIPTION
		" Flag to enable/disable the calculation of the
		  DDP checksum for packets sourced by the router
		  over this interface.  This value has no effect 
		  on incoming packets.
		      "
	DEFVAL	{ disabled }
	::= { wfApplePortEntry 6 }

wfApplePortTrEndStation OBJECT-TYPE
	SYNTAX	INTEGER {
		enabled(1),
		disabled(2)
	}
	ACCESS	read-write
	STATUS	mandatory
	DESCRIPTION
		" When an interface is running token ring this attribute
		  allows for end station source routing. If the interface
		  is not running token ring the attribute has no meaning.
		      "
	DEFVAL	{ disabled }
	::= { wfApplePortEntry 7 }

wfApplePortGniForever OBJECT-TYPE
	SYNTAX	INTEGER
	ACCESS	read-write
	STATUS	mandatory
	DESCRIPTION
		" During initialization default behavior is to send 3
		  GetNetInfos and then shut down the port. This will
		  send GetNetInfos forever.
		      "
	::= { wfApplePortEntry 8 }

wfApplePortAarpFlush OBJECT-TYPE
	SYNTAX	INTEGER
	ACCESS	read-only
	STATUS	mandatory
	DESCRIPTION
		" Setting this to a non-null value causes the aarp table
		  to be emptied of all entries.
		      "
	::= { wfApplePortEntry 9 }

wfApplePortMacAddress OBJECT-TYPE
	SYNTAX	OCTET STRING
	ACCESS	read-write
	STATUS	mandatory
	DESCRIPTION
		" Configured mac address "
	::= { wfApplePortEntry 10 }

wfApplePortNodeId OBJECT-TYPE
	SYNTAX	INTEGER
	ACCESS	read-write
	STATUS	mandatory
	DESCRIPTION
		" The AppleTalk node id configured for this
		  port/interface.
		      "
	::= { wfApplePortEntry 11 }

wfApplePortNetwork OBJECT-TYPE
	SYNTAX	INTEGER
	ACCESS	read-write
	STATUS	mandatory
	DESCRIPTION
		" The Network NUMBER for this interface/port.  "
	::= { wfApplePortEntry 12 }

wfApplePortNetStart OBJECT-TYPE
	SYNTAX	INTEGER
	ACCESS	read-write
	STATUS	mandatory
	DESCRIPTION
		" The Network start value in the network range
		  for this interface/port.
		      "
	::= { wfApplePortEntry 13 }

wfApplePortNetEnd OBJECT-TYPE
	SYNTAX	INTEGER
	ACCESS	read-write
	STATUS	mandatory
	DESCRIPTION
		" The Network end value in the network range
		  for this interface/port.
		      "
	::= { wfApplePortEntry 14 }

wfApplePortDfltZone OBJECT-TYPE
	SYNTAX	DisplayString
	ACCESS	read-write
	STATUS	mandatory
	DESCRIPTION
		" The default zone name for this network range/
		  interface. 
		      "
	::= { wfApplePortEntry 15 }

wfApplePortCurMacAddress OBJECT-TYPE
	SYNTAX	OCTET STRING
	ACCESS	read-only
	STATUS	mandatory
	DESCRIPTION
		" Mac Address used "
	::= { wfApplePortEntry 16 }

wfApplePortCurNodeId OBJECT-TYPE
	SYNTAX	INTEGER
	ACCESS	read-only
	STATUS	mandatory
	DESCRIPTION
		" The AppleTalk node id of this port "
	::= { wfApplePortEntry 17 }

wfApplePortCurNetwork OBJECT-TYPE
	SYNTAX	INTEGER
	ACCESS	read-only
	STATUS	mandatory
	DESCRIPTION
		" The network number for this port.  "
	::= { wfApplePortEntry 18 }

wfApplePortCurNetStart OBJECT-TYPE
	SYNTAX	INTEGER
	ACCESS	read-only
	STATUS	mandatory
	DESCRIPTION
		" The Network start value in the network range
		  for this port.
		      "
	::= { wfApplePortEntry 19 }

wfApplePortCurNetEnd OBJECT-TYPE
	SYNTAX	INTEGER
	ACCESS	read-only
	STATUS	mandatory
	DESCRIPTION
		" The Network end value in the network range
		  for this port.
		      "
	::= { wfApplePortEntry 20 }

wfApplePortCurDfltZone OBJECT-TYPE
	SYNTAX	DisplayString
	ACCESS	read-only
	STATUS	mandatory
	DESCRIPTION
		" The default zone name for this port "
	::= { wfApplePortEntry 21 }

wfApplePortAarpProbeRxs OBJECT-TYPE
	SYNTAX	Counter
	ACCESS	read-only
	STATUS	mandatory
	DESCRIPTION
		" The number of AARP Probe packets received on
		  this interface.
		      "
	::= { wfApplePortEntry 22 }

wfApplePortAarpProbeTxs OBJECT-TYPE
	SYNTAX	Counter
	ACCESS	read-only
	STATUS	mandatory
	DESCRIPTION
		" The number of AARP Probe packets transmitted on
		  this interface.
		      "
	::= { wfApplePortEntry 23 }

wfApplePortAarpReqRxs OBJECT-TYPE
	SYNTAX	Counter
	ACCESS	read-only
	STATUS	mandatory
	DESCRIPTION
		" The number of AARP Request packets received on
		  this interface.
		      "
	::= { wfApplePortEntry 24 }

wfApplePortAarpReqTxs OBJECT-TYPE
	SYNTAX	Counter
	ACCESS	read-only
	STATUS	mandatory
	DESCRIPTION
		" The number of AARP Request packets transmitted on
		  this interface.
		      "
	::= { wfApplePortEntry 25 }

wfApplePortAarpRspRxs OBJECT-TYPE
	SYNTAX	Counter
	ACCESS	read-only
	STATUS	mandatory
	DESCRIPTION
		" The number of AARP Response packets received on
		  this interface.
		      "
	::= { wfApplePortEntry 26 }

wfApplePortAarpRspTxs OBJECT-TYPE
	SYNTAX	Counter
	ACCESS	read-only
	STATUS	mandatory
	DESCRIPTION
		" The number of AARP Response packets transmitted on
		  this interface.
		      "
	::= { wfApplePortEntry 27 }

wfApplePortDdpOutRequests OBJECT-TYPE
	SYNTAX	Counter
	ACCESS	read-only
	STATUS	mandatory
	DESCRIPTION
		" The total number of DDP datagrams which were supplied
		  to DDP by local DDP clients in requests for
		  transmission.  Note that this counter does not
		  include any datagrams counted in ddpForwRequests.
		      "
	::= { wfApplePortEntry 28 }

wfApplePortDdpInReceives OBJECT-TYPE
	SYNTAX	Counter
	ACCESS	read-only
	STATUS	mandatory
	DESCRIPTION
		" The total number of input datagrams received by DDP,
		  including those received in error.
		      "
	::= { wfApplePortEntry 29 }

wfApplePortDdpInLocalDatagrams OBJECT-TYPE
	SYNTAX	Counter
	ACCESS	read-only
	STATUS	mandatory
	DESCRIPTION
		" The total number of input DDP datagrams for which this
		  entity was their final DDP destination.
		      "
	::= { wfApplePortEntry 30 }

wfApplePortDdpNoProtocolHandlers OBJECT-TYPE
	SYNTAX	Counter
	ACCESS	read-only
	STATUS	mandatory
	DESCRIPTION
		" The total number of DDP datagrams addressed to this
		  entity that were addressed to an upper layer protocol
		  for which no protocol handler existed.
		      "
	::= { wfApplePortEntry 31 }

wfApplePortDdpTooShortErrors OBJECT-TYPE
	SYNTAX	Counter
	ACCESS	read-only
	STATUS	mandatory
	DESCRIPTION
		" The total number of input DDP datagrams dropped because
		  the received data length was less than the data length
		  specified in the DDP header or the received data length
		  was less than the length of the expected DDP header.
		      "
	::= { wfApplePortEntry 32 }

wfApplePortDdpTooLongErrors OBJECT-TYPE
	SYNTAX	Counter
	ACCESS	read-only
	STATUS	mandatory
	DESCRIPTION
		" The total number of input DDP datagrams dropped because
		  the received data length was greater than the data length
		  specified in the DDP header or because they exceeded the
		  maximum DDP datagram size.
		      "
	::= { wfApplePortEntry 33 }

wfApplePortDdpChecksumErrors OBJECT-TYPE
	SYNTAX	Counter
	ACCESS	read-only
	STATUS	mandatory
	DESCRIPTION
		" The total number of input DDP datagrams for which this
		  DDP entity was their final destination, and which were
		  dropped because of a checksum error.
		      "
	::= { wfApplePortEntry 34 }

wfApplePortDdpForwRequests OBJECT-TYPE
	SYNTAX	Counter
	ACCESS	read-only
	STATUS	mandatory
	DESCRIPTION
		" The number of input datagrams for which this entity was
		  not their final DDP destination, as a result of which an
		  attempt was made to find a route to forward them to that
		  final destination.
		      "
	::= { wfApplePortEntry 35 }

wfApplePortDdpOutNoRoutes OBJECT-TYPE
	SYNTAX	Counter
	ACCESS	read-only
	STATUS	mandatory
	DESCRIPTION
		" The total number of DDP datagrams dropped because a
		  route could not be found to their final destination.
		      "
	::= { wfApplePortEntry 36 }

wfApplePortDdpBroadcastErrors OBJECT-TYPE
	SYNTAX	Counter
	ACCESS	read-only
	STATUS	mandatory
	DESCRIPTION
		" The total number of input DDP datagrams dropped because
		  this entity was not their final destination and they
		  were addressed to the link level broadcast.
		      "
	::= { wfApplePortEntry 37 }

wfApplePortDdpHopCountErrors OBJECT-TYPE
	SYNTAX	Counter
	ACCESS	read-only
	STATUS	mandatory
	DESCRIPTION
		" The total number of input DDP datagrams dropped because
		  this entity was not their final destination and their
		  hop count would exceed 15.
		      "
	::= { wfApplePortEntry 38 }

wfApplePortRtmpInDataPkts OBJECT-TYPE
	SYNTAX	Counter
	ACCESS	read-only
	STATUS	mandatory
	DESCRIPTION
		" A count of the number of good RTMP data packets
		  received by this entity.
		      "
	::= { wfApplePortEntry 39 }

wfApplePortRtmpOutDataPkts OBJECT-TYPE
	SYNTAX	Counter
	ACCESS	read-only
	STATUS	mandatory
	DESCRIPTION
		" A count of the number of RTMP packets sent by this
		  entity.
		      "
	::= { wfApplePortEntry 40 }

wfApplePortRtmpInRequestPkts OBJECT-TYPE
	SYNTAX	Counter
	ACCESS	read-only
	STATUS	mandatory
	DESCRIPTION
		" A count of the number of good RTMP Request packets
		  received by this entity.
		      "
	::= { wfApplePortEntry 41 }

wfApplePortRtmpNextIREqualChanges OBJECT-TYPE
	SYNTAX	Counter
	ACCESS	read-only
	STATUS	mandatory
	DESCRIPTION
		" A count of the number of times RTMP changes the Next
		  Internet Router in a routing entry because the hop count
		  advertised in a routing tuple was equal to the current
		  hop count for a particular network.
		      "
	::= { wfApplePortEntry 42 }

wfApplePortRtmpNextIRLessChanges OBJECT-TYPE
	SYNTAX	Counter
	ACCESS	read-only
	STATUS	mandatory
	DESCRIPTION
		" A count of the number of times RTMP changes the Next
		  Internet Router in a routing entry because the hop count
		  advertised in a routing tuple was less than the current
		  hop count for a particular network.
		      "
	::= { wfApplePortEntry 43 }

wfApplePortRtmpRouteDeletes OBJECT-TYPE
	SYNTAX	Counter
	ACCESS	read-only
	STATUS	mandatory
	DESCRIPTION
		" A count of the number of times RTMP deletes a route because
		  it was aged out of the table.  This can help to detect
		  routing problems.
		      "
	::= { wfApplePortEntry 44 }

wfApplePortRtmpNetworkMismatchErrors OBJECT-TYPE
	SYNTAX	Counter
	ACCESS	read-only
	STATUS	mandatory
	DESCRIPTION
		" The number of times RTMP receives a Data packet from a
		  router who claims to be on a different network than that
		  configured for the receiving port.  This can help to
		  detect configuration errors.
		      "
	::= { wfApplePortEntry 45 }

wfApplePortRtmpRoutingTableOverflows OBJECT-TYPE
	SYNTAX	Counter
	ACCESS	read-only
	STATUS	mandatory
	DESCRIPTION
		" The number of times RTMP attempted to add a route
		  to the RTMP table but failed due to overflow.
		      "
	::= { wfApplePortEntry 46 }

wfApplePortZipInZipQueries OBJECT-TYPE
	SYNTAX	Counter
	ACCESS	read-only
	STATUS	mandatory
	DESCRIPTION
		" The number of ZIP Queries received by this entity.
		      "
	::= { wfApplePortEntry 47 }

wfApplePortZipInZipReplies OBJECT-TYPE
	SYNTAX	Counter
	ACCESS	read-only
	STATUS	mandatory
	DESCRIPTION
		" The number of ZIP Replies received by this entity.
		      "
	::= { wfApplePortEntry 48 }

wfApplePortZipOutZipReplies OBJECT-TYPE
	SYNTAX	Counter
	ACCESS	read-only
	STATUS	mandatory
	DESCRIPTION
		" The number of ZIP Replies sent by this entity.
		      "
	::= { wfApplePortEntry 49 }

wfApplePortZipInZipExtendedReplies OBJECT-TYPE
	SYNTAX	Counter
	ACCESS	read-only
	STATUS	mandatory
	DESCRIPTION
		" The number of ZIP Extended Replies received by this entity.
		      "
	::= { wfApplePortEntry 50 }

wfApplePortZipOutZipExtendedReplies OBJECT-TYPE
	SYNTAX	Counter
	ACCESS	read-only
	STATUS	mandatory
	DESCRIPTION
		" The number of ZIP Extended Replies sent by this entity.
		      "
	::= { wfApplePortEntry 51 }

wfApplePortZipInGetZoneLists OBJECT-TYPE
	SYNTAX	Counter
	ACCESS	read-only
	STATUS	mandatory
	DESCRIPTION
		" The number of ZIP GetZoneList transactions received by
		  this entity.
		      "
	::= { wfApplePortEntry 52 }

wfApplePortZipOutGetZoneListReplies OBJECT-TYPE
	SYNTAX	Counter
	ACCESS	read-only
	STATUS	mandatory
	DESCRIPTION
		" The number of ZIP GetZoneListReply transactions sent by
		  this entity.
		      "
	::= { wfApplePortEntry 53 }

wfApplePortZipInGetLocalZones OBJECT-TYPE
	SYNTAX	Counter
	ACCESS	read-only
	STATUS	mandatory
	DESCRIPTION
		" The number of ZIP GetLocalZone transactions received
		  by this entity.
		      "
	::= { wfApplePortEntry 54 }

wfApplePortZipOutGetLocalZoneReplies OBJECT-TYPE
	SYNTAX	Counter
	ACCESS	read-only
	STATUS	mandatory
	DESCRIPTION
		" The number of ZIP GetLocalZoneReply transactions sent
		  by this entity.
		      "
	::= { wfApplePortEntry 55 }

wfApplePortZipInGetMyZones OBJECT-TYPE
	SYNTAX	Counter
	ACCESS	read-only
	STATUS	mandatory
	DESCRIPTION
		" The number of ZIP GetMyZone transactions received by
		  this entity.
		      "
	::= { wfApplePortEntry 56 }

wfApplePortZipOutGetMyZoneReplies OBJECT-TYPE
	SYNTAX	Counter
	ACCESS	read-only
	STATUS	mandatory
	DESCRIPTION
		" The number of ZIP GetMyZoneReply transactions sent by
		  this entity.
		      "
	::= { wfApplePortEntry 57 }

wfApplePortZipZoneConflictErrors OBJECT-TYPE
	SYNTAX	Counter
	ACCESS	read-only
	STATUS	mandatory
	DESCRIPTION
		" The number of times a conflict has been detected between
		  this entity's zone information and another entity's
		  zone information.
		      "
	::= { wfApplePortEntry 58 }

wfApplePortZipInGetNetInfos OBJECT-TYPE
	SYNTAX	Counter
	ACCESS	read-only
	STATUS	mandatory
	DESCRIPTION
		" The number of ZIP GetNetInfo packets received on this
		  port by this entity.
		      "
	::= { wfApplePortEntry 59 }

wfApplePortZipOutGetNetInfoReplies OBJECT-TYPE
	SYNTAX	Counter
	ACCESS	read-only
	STATUS	mandatory
	DESCRIPTION
		" The number of ZIP GetNetInfoReply packets sent out this
		  port by this entity.
		      "
	::= { wfApplePortEntry 60 }

wfApplePortZipZoneOutInvalids OBJECT-TYPE
	SYNTAX	Counter
	ACCESS	read-only
	STATUS	mandatory
	DESCRIPTION
		" The number of times this entity has sent a ZIP GetNetInfo
		  Reply with the zone invalid bit set in response to a
		  GetNetInfo Request with an invalid zone name.
		      "
	::= { wfApplePortEntry 61 }

wfApplePortZipAddressInvalids OBJECT-TYPE
	SYNTAX	Counter
	ACCESS	read-only
	STATUS	mandatory
	DESCRIPTION
		" The number of times this entity had to broadcast a ZIP
		  GetNetInfo Reply because the GetNetInfo Request had an
		  invalid address.
		      "
	::= { wfApplePortEntry 62 }

wfApplePortZipOutGetNetInfos OBJECT-TYPE
	SYNTAX	Counter
	ACCESS	read-only
	STATUS	mandatory
	DESCRIPTION
		" The number of ZIP GetNetInfo packets sent out this port
		  by this entity.
		      "
	::= { wfApplePortEntry 63 }

wfApplePortZipInGetNetInfoReplies OBJECT-TYPE
	SYNTAX	Counter
	ACCESS	read-only
	STATUS	mandatory
	DESCRIPTION
		" The number of ZIP GetNetInfoReply packets received on
		  this port by this entity.
		      "
	::= { wfApplePortEntry 64 }

wfApplePortZipOutZipQueries OBJECT-TYPE
	SYNTAX	Counter
	ACCESS	read-only
	STATUS	mandatory
	DESCRIPTION
		" The number of ZIP Queries sent by this entity.
		      "
	::= { wfApplePortEntry 65 }

wfApplePortZipInErrors OBJECT-TYPE
	SYNTAX	Counter
	ACCESS	read-only
	STATUS	mandatory
	DESCRIPTION
		" The number of ZIP packets received by this entity
		  that were rejected for any error.
		      "
	::= { wfApplePortEntry 66 }

wfApplePortNbpInLookUpRequests OBJECT-TYPE
	SYNTAX	Counter
	ACCESS	read-only
	STATUS	mandatory
	DESCRIPTION
		" The number of NBP LookUp Requests received.
		      "
	::= { wfApplePortEntry 67 }

wfApplePortNbpInLookUpReplies OBJECT-TYPE
	SYNTAX	Counter
	ACCESS	read-only
	STATUS	mandatory
	DESCRIPTION
		" The number of NBP LookUp Replies received.
		      "
	::= { wfApplePortEntry 68 }

wfApplePortNbpInBroadcastRequests OBJECT-TYPE
	SYNTAX	Counter
	ACCESS	read-only
	STATUS	mandatory
	DESCRIPTION
		" The number of NBP Broadcast Requests received.
		      "
	::= { wfApplePortEntry 69 }

wfApplePortNbpInForwardRequests OBJECT-TYPE
	SYNTAX	Counter
	ACCESS	read-only
	STATUS	mandatory
	DESCRIPTION
		" The number of NBP Forward Requests received.
		      "
	::= { wfApplePortEntry 70 }

wfApplePortNbpOutLookUpRequests OBJECT-TYPE
	SYNTAX	Counter
	ACCESS	read-only
	STATUS	mandatory
	DESCRIPTION
		" The number of NBP LookUp Requests sent.
		      "
	::= { wfApplePortEntry 71 }

wfApplePortNbpOutLookUpReplies OBJECT-TYPE
	SYNTAX	Counter
	ACCESS	read-only
	STATUS	mandatory
	DESCRIPTION
		" The number of NBP LookUp Replies sent.
		      "
	::= { wfApplePortEntry 72 }

wfApplePortNbpOutBroadcastRequests OBJECT-TYPE
	SYNTAX	Counter
	ACCESS	read-only
	STATUS	mandatory
	DESCRIPTION
		" The number of NBP Broadcast Requests sent.
		      "
	::= { wfApplePortEntry 73 }

wfApplePortNbpOutForwardRequests OBJECT-TYPE
	SYNTAX	Counter
	ACCESS	read-only
	STATUS	mandatory
	DESCRIPTION
		" The number of NBP Forward Requests sent.
		      "
	::= { wfApplePortEntry 74 }

wfApplePortNbpRegistrationFailures OBJECT-TYPE
	SYNTAX	Counter
	ACCESS	read-only
	STATUS	mandatory
	DESCRIPTION
		" The number of times this node experienced a failure in
		  attempting to register an NBP entity.
		      "
	::= { wfApplePortEntry 75 }

wfApplePortNbpInErrors OBJECT-TYPE
	SYNTAX	Counter
	ACCESS	read-only
	STATUS	mandatory
	DESCRIPTION
		" The number of NBP packets received by this entity that were
		  rejected for any error.
		      "
	::= { wfApplePortEntry 76 }

wfApplePortEchoRequests OBJECT-TYPE
	SYNTAX	Counter
	ACCESS	read-only
	STATUS	mandatory
	DESCRIPTION
		" The number of AppleTalk Echo requests received.
		      "
	::= { wfApplePortEntry 77 }

wfApplePortEchoReplies OBJECT-TYPE
	SYNTAX	Counter
	ACCESS	read-only
	STATUS	mandatory
	DESCRIPTION
		" The number of AppleTalk Echo replies sent.
		      "
	::= { wfApplePortEntry 78 }

wfAppleLclZoneTable OBJECT-TYPE
	SYNTAX	SEQUENCE OF WfAppleLclZoneEntry
	ACCESS	not-accessible
	STATUS	mandatory
	DESCRIPTION
		" The Local Zone table describes a list of zone names s
		  serviced by a particular AppleTalk port/interface.  
		  In other words, the list of zone names that are 
		  associated with a particular network range.
		  "
	::= { wfAppletalkGroup 4 }

wfAppleLclZoneEntry OBJECT-TYPE
	SYNTAX	WfAppleLclZoneEntry
	ACCESS	not-accessible
	STATUS	mandatory
	DESCRIPTION
		" An entry in the Local Zone table "
	INDEX	{ wfAppleLclZonePortCircuit,
		wfAppleLclZoneIndex }
	::= { wfAppleLclZoneTable 1 }

WfAppleLclZoneEntry ::= SEQUENCE {
	wfAppleLclZoneDelete
		INTEGER,
	wfAppleLclZonePortCircuit
		INTEGER,
	wfAppleLclZoneIndex
		INTEGER,
	wfAppleLclZoneName
		DisplayString
}

wfAppleLclZoneDelete OBJECT-TYPE
	SYNTAX	INTEGER {
		created(1),
		deleted(2)
	}
	ACCESS	read-write
	STATUS	mandatory
	DESCRIPTION
		" Create/Delete parameter for adding/deleting a
		  zone name to the Local Zone List for a particular
		  AppleTalk network interface.
		     "
	DEFVAL	{ created }
	::= { wfAppleLclZoneEntry 1 }

wfAppleLclZonePortCircuit OBJECT-TYPE
	SYNTAX	INTEGER
	ACCESS	read-only
	STATUS	mandatory
	DESCRIPTION
		" The circuit number for the corresponding AppleTalk interface
		  /port for this zone list. 
		      "
	::= { wfAppleLclZoneEntry 2 }

wfAppleLclZoneIndex OBJECT-TYPE
	SYNTAX	INTEGER
	ACCESS	read-only
	STATUS	mandatory
	DESCRIPTION
		" A unique value for this zone name. "
	::= { wfAppleLclZoneEntry 3 }

wfAppleLclZoneName OBJECT-TYPE
	SYNTAX	DisplayString
	ACCESS	read-write
	STATUS	mandatory
	DESCRIPTION
		" One of the local zone names defined for this/
		  interface. 
		      "
	::= { wfAppleLclZoneEntry 4 }

wfAppleAarpTable OBJECT-TYPE
	SYNTAX	SEQUENCE OF WfAppleAarpEntry
	ACCESS	not-accessible
	STATUS	mandatory
	DESCRIPTION
		" The AppleTalk Address Translation table
		  contains a mapping of AppleTalk Network addresses
		  to its corresponding physical address.
		  "
	::= { wfAppletalkGroup 5 }

wfAppleAarpEntry OBJECT-TYPE
	SYNTAX	WfAppleAarpEntry
	ACCESS	not-accessible
	STATUS	mandatory
	DESCRIPTION
		" An entry in the Address Mapping table "
	INDEX	{ wfAppleAarpNet,
		wfAppleAarpNode,
		wfAppleAarpIfIndex }
	::= { wfAppleAarpTable 1 }

WfAppleAarpEntry ::= SEQUENCE {
	wfAppleAarpIfIndex
		INTEGER,
	wfAppleAarpNet
		INTEGER,
	wfAppleAarpNode
		INTEGER,
	wfAppleAarpPhysAddress
		OCTET STRING
}

wfAppleAarpIfIndex OBJECT-TYPE
	SYNTAX	INTEGER
	ACCESS	read-only
	STATUS	mandatory
	DESCRIPTION
		" The unique value for this interface/cct. This
		  value is the same interface as identified by 
		  the value of ifIndex.
		      "
	::= { wfAppleAarpEntry 1 }

wfAppleAarpNet OBJECT-TYPE
	SYNTAX	INTEGER
	ACCESS	read-only
	STATUS	mandatory
	DESCRIPTION
		" The host's AppleTalk address (Net.Nodeid). This
		  address corresponds to the media-dependent 'physical' 
		  address for this host.
		      "
	::= { wfAppleAarpEntry 2 }

wfAppleAarpNode OBJECT-TYPE
	SYNTAX	INTEGER
	ACCESS	read-only
	STATUS	mandatory
	DESCRIPTION
		" The host's AppleTalk address (Net.Nodeid). This
		  address corresponds to the media-dependent 'physical' 
		  address for this host.
		      "
	::= { wfAppleAarpEntry 3 }

wfAppleAarpPhysAddress OBJECT-TYPE
	SYNTAX	OCTET STRING
	ACCESS	read-only
	STATUS	mandatory
	DESCRIPTION
		" The media-dependent 'physical' address. "
	::= { wfAppleAarpEntry 4 }

wfAppleZipTable OBJECT-TYPE
	SYNTAX	SEQUENCE OF WfAppleZipEntry
	ACCESS	not-accessible
	STATUS	mandatory
	DESCRIPTION
		" The Zone Information table for reachable AppleTalk
		  Networks.
		  "
	::= { wfAppletalkGroup 6 }

wfAppleZipEntry OBJECT-TYPE
	SYNTAX	WfAppleZipEntry
	ACCESS	not-accessible
	STATUS	mandatory
	DESCRIPTION
		" An entry in the Zone Information table "
	INDEX	{ wfAppleZipZoneNetStart,
		wfAppleZipIndex }
	::= { wfAppleZipTable 1 }

WfAppleZipEntry ::= SEQUENCE {
	wfAppleZipZoneNetStart
		INTEGER,
	wfAppleZipZoneNetEnd
		INTEGER,
	wfAppleZipIndex
		INTEGER,
	wfAppleZipZoneName
		DisplayString,
	wfAppleZipZoneState
		INTEGER
}

wfAppleZipZoneNetStart OBJECT-TYPE
	SYNTAX	INTEGER
	ACCESS	read-only
	STATUS	mandatory
	DESCRIPTION
		" The network that starts the range for this entry. "
	::= { wfAppleZipEntry 1 }

wfAppleZipZoneNetEnd OBJECT-TYPE
	SYNTAX	INTEGER
	ACCESS	read-only
	STATUS	mandatory
	DESCRIPTION
		" The network that ends the range for this entry. "
	::= { wfAppleZipEntry 2 }

wfAppleZipIndex OBJECT-TYPE
	SYNTAX	INTEGER
	ACCESS	read-only
	STATUS	mandatory
	DESCRIPTION
		" The unique value for this zone name.  "
	::= { wfAppleZipEntry 3 }

wfAppleZipZoneName OBJECT-TYPE
	SYNTAX	DisplayString
	ACCESS	read-only
	STATUS	mandatory
	DESCRIPTION
		" The ASCII xone name of this entry.  "
	::= { wfAppleZipEntry 4 }

wfAppleZipZoneState OBJECT-TYPE
	SYNTAX	INTEGER {
		valid(1),
		invalid(2)
	}
	ACCESS	read-only
	STATUS	mandatory
	DESCRIPTION
		" The state of the ZIP entry. Setting this object
		  to the value invalid(2) has the effect of 
		  invalidating the corresponding entry in the ZipTable.
		  It effectively, disassociates the mapping identified
		  with this entry.
		      "
	::= { wfAppleZipEntry 5 }

wfBrTp		OBJECT IDENTIFIER ::= { wfBrLearning 1 }

wfBrTpBaseDelete OBJECT-TYPE
	SYNTAX	INTEGER {
		created(1),
		deleted(2)
	}
	ACCESS	read-write
	STATUS	mandatory
	DESCRIPTION
		" Create/Delete parameter. Default is created.
		  Users perform an SNMP SET operation on this
		  object in order to create/delete the bridge. "
	DEFVAL	{ created }
	::= { wfBrTp 1 }

wfBrTpBaseEnable OBJECT-TYPE
	SYNTAX	INTEGER {
		enabled(1),
		disabled(2)
	}
	ACCESS	read-write
	STATUS	mandatory
	DESCRIPTION
		" Enable/Disable parameter. Default is enabled.
		  Users perform an SNMP SET operation on this
		  object in order to enable/disable the bridge. "
	DEFVAL	{ enabled }
	::= { wfBrTp 2 }

wfBrTpBaseState OBJECT-TYPE
	SYNTAX	INTEGER {
		up(1),
		down(2),
		init(3),
		pres(4)
	}
	ACCESS	read-only
	STATUS	mandatory
	DESCRIPTION
		" The current state of the entire Bridge. "
	DEFVAL	{ down }
	::= { wfBrTp 3 }

wfBrTpFdbTable OBJECT-TYPE
	SYNTAX	SEQUENCE OF WfBrTpFdbEntry
	ACCESS	not-accessible
	STATUS	mandatory
	DESCRIPTION
		" A table that contains information about unicast
		  entries for which the bridge has forwarding and/or
		  filtering information.  This information is used
		  by the transparent bridging function in
		  determining how to propagate a received frame.
		  inst = wfBrTpBaseFdbAddress "
	::= { wfBrLearning 2 }

wfBrTpFdbEntry OBJECT-TYPE
	SYNTAX	WfBrTpFdbEntry
	ACCESS	not-accessible
	STATUS	mandatory
	DESCRIPTION
		" An entry in the wfBrTpFdbTable. "
	INDEX	{ wfBrTpBaseFdbAddress }
	::= { wfBrTpFdbTable 1 }

WfBrTpFdbEntry ::= SEQUENCE {
	wfBrTpBaseFdbAddress
		OCTET STRING,
	wfBrTpBaseFdbPort
		INTEGER,
	wfBrTpBaseFdbStatus
		INTEGER
}

wfBrTpBaseFdbAddress OBJECT-TYPE
	SYNTAX	OCTET STRING
	ACCESS	read-only
	STATUS	mandatory
	DESCRIPTION
		" A unicast MAC address for which the bridge has
		  forwarding and/or filtering information. "
	::= { wfBrTpFdbEntry 1 }

wfBrTpBaseFdbPort OBJECT-TYPE
	SYNTAX	INTEGER
	ACCESS	read-only
	STATUS	mandatory
	DESCRIPTION
		" The port number on which the wfBrTpBaseFdbAddress
		  was learned. "
	::= { wfBrTpFdbEntry 2 }

wfBrTpBaseFdbStatus OBJECT-TYPE
	SYNTAX	INTEGER {
		learned(3)
	}
	ACCESS	read-only
	STATUS	mandatory
	DESCRIPTION
		" The status of this entry. The meanings of the
		  values are:
		    learned(3) : the value of the corresponding
		                instance of wfBrTpFdbPort was
		                learned, and is being used. "
	DEFVAL	{ learned }
	::= { wfBrTpFdbEntry 3 }

wfBrTpInterface OBJECT-TYPE
	SYNTAX	SEQUENCE OF WfBrTpInterfaceEntry
	ACCESS	not-accessible
	STATUS	mandatory
	DESCRIPTION
		" A table that contains information about every
		  interface that is associated with this
		  transparent bridge.
		  inst_id[1] = wfBrTpInterfaceCircuit "
	::= { wfBridgeGroup 3 }

wfBrTpInterfaceEntry OBJECT-TYPE
	SYNTAX	WfBrTpInterfaceEntry
	ACCESS	not-accessible
	STATUS	mandatory
	DESCRIPTION
		" An entry in wfBrTpInterface. "
	INDEX	{ wfBrTpInterfaceCircuit }
	::= { wfBrTpInterface 1 }

WfBrTpInterfaceEntry ::= SEQUENCE {
	wfBrTpInterfaceDelete
		INTEGER,
	wfBrTpInterfaceEnable
		INTEGER,
	wfBrTpInterfaceState
		INTEGER,
	wfBrTpInterfaceCircuit
		INTEGER,
	wfBrTpInterfaceMaxInfo
		INTEGER,
	wfBrTpInterfaceInFrames
		Counter,
	wfBrTpInterfaceOutFrames
		Counter,
	wfBrTpInterfaceInDiscards
		Counter
}

wfBrTpInterfaceDelete OBJECT-TYPE
	SYNTAX	INTEGER {
		created(1),
		deleted(2)
	}
	ACCESS	read-write
	STATUS	mandatory
	DESCRIPTION
		" Create/Delete parameter. Default is created.
		  Users perform an SNMP SET operation on this
		  object in order to create/delete an interface. "
	DEFVAL	{ created }
	::= { wfBrTpInterfaceEntry 1 }

wfBrTpInterfaceEnable OBJECT-TYPE
	SYNTAX	INTEGER {
		enabled(1),
		disabled(2)
	}
	ACCESS	read-write
	STATUS	mandatory
	DESCRIPTION
		" Enable/Disable parameter. Default is enabled.
		  Users perform an SNMP SET operation on this
		  object in order to enable/disable an interface. "
	DEFVAL	{ enabled }
	::= { wfBrTpInterfaceEntry 2 }

wfBrTpInterfaceState OBJECT-TYPE
	SYNTAX	INTEGER {
		up(1),
		down(2),
		init(3),
		pres(4)
	}
	ACCESS	read-only
	STATUS	mandatory
	DESCRIPTION
		" The current state of the interface. "
	DEFVAL	{ down }
	::= { wfBrTpInterfaceEntry 3 }

wfBrTpInterfaceCircuit OBJECT-TYPE
	SYNTAX	INTEGER
	ACCESS	read-only
	STATUS	mandatory
	DESCRIPTION
		" The circuit that this interface runs over. "
	::= { wfBrTpInterfaceEntry 4 }

wfBrTpInterfaceMaxInfo OBJECT-TYPE
	SYNTAX	INTEGER
	ACCESS	read-only
	STATUS	mandatory
	DESCRIPTION
		" The maximum size of the INFO (non-MAC) field that
		  this port will receive or transmit. "
	::= { wfBrTpInterfaceEntry 5 }

wfBrTpInterfaceInFrames OBJECT-TYPE
	SYNTAX	Counter
	ACCESS	read-only
	STATUS	mandatory
	DESCRIPTION
		" The number of frames that have been received by
		  this interface from its circuit. "
	::= { wfBrTpInterfaceEntry 6 }

wfBrTpInterfaceOutFrames OBJECT-TYPE
	SYNTAX	Counter
	ACCESS	read-only
	STATUS	mandatory
	DESCRIPTION
		" The number of frames that have been transmitted
		  by this interface to its circuit. "
	::= { wfBrTpInterfaceEntry 7 }

wfBrTpInterfaceInDiscards OBJECT-TYPE
	SYNTAX	Counter
	ACCESS	read-only
	STATUS	mandatory
	DESCRIPTION
		" Count of valid frames received which were
		  received on this interface but then discarded. "
	::= { wfBrTpInterfaceEntry 8 }

wfBrTrafficFilterTable OBJECT-TYPE
	SYNTAX	SEQUENCE OF WfBrTrafficFilterEntry
	ACCESS	not-accessible
	STATUS	mandatory
	DESCRIPTION
		" Bridge Traffic Filters "
	::= { wfBridgeGroup 4 }

wfBrTrafficFilterEntry OBJECT-TYPE
	SYNTAX	WfBrTrafficFilterEntry
	ACCESS	not-accessible
	STATUS	mandatory
	DESCRIPTION
		" An entry in WfBrTrafficFilterTable. "
	INDEX	{ wfBrTrafficFilterCircuit,
		wfBrTrafficFilterRuleNumber,
		wfBrTrafficFilterFragment }
	::= { wfBrTrafficFilterTable 1 }

WfBrTrafficFilterEntry ::= SEQUENCE {
	wfBrTrafficFilterCreate
		INTEGER,
	wfBrTrafficFilterEnable
		INTEGER,
	wfBrTrafficFilterStatus
		INTEGER,
	wfBrTrafficFilterCounter
		Counter,
	wfBrTrafficFilterDefinition
		Opaque,
	wfBrTrafficFilterReserved
		INTEGER,
	wfBrTrafficFilterCircuit
		INTEGER,
	wfBrTrafficFilterRuleNumber
		INTEGER,
	wfBrTrafficFilterFragment
		INTEGER
}

wfBrTrafficFilterCreate OBJECT-TYPE
	SYNTAX	INTEGER {
		created(1),
		deleted(2)
	}
	ACCESS	read-write
	STATUS	mandatory
	DESCRIPTION
		" Defines the existence of the traffic filter rule:
		  created - traffic filter exists
		  delete - traffic filter does not exist and can be deleted. "
	DEFVAL	{ created }
	::= { wfBrTrafficFilterEntry 1 }

wfBrTrafficFilterEnable OBJECT-TYPE
	SYNTAX	INTEGER {
		enabled(1),
		disabled(2)
	}
	ACCESS	read-write
	STATUS	mandatory
	DESCRIPTION
		" Defines whether or not the traffic filter rule should be used:
		  enabled - activate the rule.
		  disabled - inactivate the rule. "
	DEFVAL	{ enabled }
	::= { wfBrTrafficFilterEntry 2 }

wfBrTrafficFilterStatus OBJECT-TYPE
	SYNTAX	INTEGER {
		active(1),
		error(2),
		inactive(3)
	}
	ACCESS	read-only
	STATUS	mandatory
	DESCRIPTION
		" Defines the current status of the traffic filter:
		  inactive - the rule is not in use.
		  active - the rule is being used.
		  error - the application detected an error in the rule. "
	DEFVAL	{ inactive }
	::= { wfBrTrafficFilterEntry 3 }

wfBrTrafficFilterCounter OBJECT-TYPE
	SYNTAX	Counter
	ACCESS	read-only
	STATUS	mandatory
	DESCRIPTION
		" The number of received packets that have
		           matched this rule. "
	::= { wfBrTrafficFilterEntry 4 }

wfBrTrafficFilterDefinition OBJECT-TYPE
	SYNTAX	Opaque
	ACCESS	read-write
	STATUS	mandatory
	DESCRIPTION
		" The filter rule definition. "
	::= { wfBrTrafficFilterEntry 5 }

wfBrTrafficFilterReserved OBJECT-TYPE
	SYNTAX	INTEGER
	ACCESS	not-accessible
	STATUS	mandatory
	DESCRIPTION
		" Reserved field. "
	::= { wfBrTrafficFilterEntry 6 }

wfBrTrafficFilterCircuit OBJECT-TYPE
	SYNTAX	INTEGER
	ACCESS	read-only
	STATUS	mandatory
	DESCRIPTION
		" The ID of the Bridge Circuit to which the
		    filter is applied. "
	::= { wfBrTrafficFilterEntry 7 }

wfBrTrafficFilterRuleNumber OBJECT-TYPE
	SYNTAX	INTEGER
	ACCESS	read-only
	STATUS	mandatory
	DESCRIPTION
		" ID for the rule. "
	::= { wfBrTrafficFilterEntry 8 }

wfBrTrafficFilterFragment OBJECT-TYPE
	SYNTAX	INTEGER
	ACCESS	read-only
	STATUS	mandatory
	DESCRIPTION
		" Fragment number - for large rules. "
	::= { wfBrTrafficFilterEntry 9 }

wfCctOptsTable OBJECT-TYPE
	SYNTAX	SEQUENCE OF WfCctOptsEntry
	ACCESS	not-accessible
	STATUS	mandatory
	DESCRIPTION
		" The table of circuit names "
	::= { wfCircuitOptsGroup 1 }

wfCctOptsEntry OBJECT-TYPE
	SYNTAX	WfCctOptsEntry
	ACCESS	not-accessible
	STATUS	mandatory
	DESCRIPTION
		" Entry format for the table of circuit options "
	INDEX	{ wfCctOptsCct }
	::= { wfCctOptsTable 1 }

WfCctOptsEntry ::= SEQUENCE {
	wfCctOptsDelete
		INTEGER,
	wfCctOptsPriorityQueueingDisable
		INTEGER,
	wfCctOptsCct
		INTEGER,
	wfCctOptsHighPriorityQueueLimit
		INTEGER,
	wfCctOptsNormalPriorityQueueLimit
		INTEGER,
	wfCctOptsLowPriorityQueueLimit
		INTEGER,
	wfCctOptsMaxInterruptQueueLatency
		INTEGER,
	wfCctOptsMaxHighPriorityQueueLatency
		INTEGER,
	wfCctOptsHiXmits
		Counter,
	wfCctOptsNormalXmits
		Counter,
	wfCctOptsLoXmits
		Counter,
	wfCctOptsHiClippedPkts
		Counter,
	wfCctOptsNormalClippedPkts
		Counter,
	wfCctOptsLoClippedPkts
		Counter,
	wfCctOptsIntrQHighWaterPkts
		Gauge,
	wfCctOptsHiQHighWaterPkts
		Gauge,
	wfCctOptsNormalQHighWaterPkts
		Gauge,
	wfCctOptsLoQHighWaterPkts
		Gauge,
	wfCctOptsHighWaterPktsClear
		INTEGER,
	wfCctOptsDroppedPkts
		Counter,
	wfCctOptsLargePkts
		Counter,
	wfCctOptsRxPkts
		Counter
}

wfCctOptsDelete OBJECT-TYPE
	SYNTAX	INTEGER {
		created(1),
		deleted(2)
	}
	ACCESS	read-write
	STATUS	mandatory
	DESCRIPTION
		" Creation and deletion flag for this record "
	DEFVAL	{ created }
	::= { wfCctOptsEntry 1 }

wfCctOptsPriorityQueueingDisable OBJECT-TYPE
	SYNTAX	INTEGER {
		enabled(1),
		disabled(2)
	}
	ACCESS	read-write
	STATUS	mandatory
	DESCRIPTION
		" Priority Queuing option "
	DEFVAL	{ enabled }
	::= { wfCctOptsEntry 2 }

wfCctOptsCct OBJECT-TYPE
	SYNTAX	INTEGER
	ACCESS	read-only
	STATUS	mandatory
	DESCRIPTION
		" circuit number "
	::= { wfCctOptsEntry 3 }

wfCctOptsHighPriorityQueueLimit OBJECT-TYPE
	SYNTAX	INTEGER {
		default(20)
	}
	ACCESS	read-write
	STATUS	mandatory
	DESCRIPTION
		" High Priority Queue limit
		  The minimum valid value is zero.
		  The maximum valid value is 63 (HW xmit ring size)
		  minus the sum of the Normal and Low queue limits.
		 "
	DEFVAL	{ default }
	::= { wfCctOptsEntry 4 }

wfCctOptsNormalPriorityQueueLimit OBJECT-TYPE
	SYNTAX	INTEGER {
		default(20)
	}
	ACCESS	read-write
	STATUS	mandatory
	DESCRIPTION
		" Normal Priority Queue limit
		  The minimum valid value is zero.
		  The maximum valid value is 63 (HW xmit ring size) 
		  minus the sum of the High and Low queue limits.
		 "
	DEFVAL	{ default }
	::= { wfCctOptsEntry 5 }

wfCctOptsLowPriorityQueueLimit OBJECT-TYPE
	SYNTAX	INTEGER {
		default(20)
	}
	ACCESS	read-write
	STATUS	mandatory
	DESCRIPTION
		" Low Priority Queue limit
		  The minimum valid value is zero.
		  The maximum valid value is 63 (HW xmit ring size)
		  minus the sum of the High and Normal queue limits.
		 "
	DEFVAL	{ default }
	::= { wfCctOptsEntry 6 }

wfCctOptsMaxInterruptQueueLatency OBJECT-TYPE
	SYNTAX	INTEGER {
		minimum(100),
		default(2500),
		maximum(5000)
	}
	ACCESS	read-write
	STATUS	mandatory
	DESCRIPTION
		" Interrupt Queue Latency "
	DEFVAL	{ default }
	::= { wfCctOptsEntry 7 }

wfCctOptsMaxHighPriorityQueueLatency OBJECT-TYPE
	SYNTAX	INTEGER {
		minimum(100),
		default(250),
		maximum(5000)
	}
	ACCESS	read-write
	STATUS	mandatory
	DESCRIPTION
		" High Priority Queue Latency "
	DEFVAL	{ default }
	::= { wfCctOptsEntry 8 }

wfCctOptsHiXmits OBJECT-TYPE
	SYNTAX	Counter
	ACCESS	read-only
	STATUS	mandatory
	DESCRIPTION
		" High Priority Transmit count "
	::= { wfCctOptsEntry 9 }

wfCctOptsNormalXmits OBJECT-TYPE
	SYNTAX	Counter
	ACCESS	read-only
	STATUS	mandatory
	DESCRIPTION
		" Normal Priority Transmit count "
	::= { wfCctOptsEntry 10 }

wfCctOptsLoXmits OBJECT-TYPE
	SYNTAX	Counter
	ACCESS	read-only
	STATUS	mandatory
	DESCRIPTION
		" Low Priority Transmit count "
	::= { wfCctOptsEntry 11 }

wfCctOptsHiClippedPkts OBJECT-TYPE
	SYNTAX	Counter
	ACCESS	read-only
	STATUS	mandatory
	DESCRIPTION
		" High Prio Transmit Clip Count "
	::= { wfCctOptsEntry 12 }

wfCctOptsNormalClippedPkts OBJECT-TYPE
	SYNTAX	Counter
	ACCESS	read-only
	STATUS	mandatory
	DESCRIPTION
		" Normal Prio Transmit Clip Count "
	::= { wfCctOptsEntry 13 }

wfCctOptsLoClippedPkts OBJECT-TYPE
	SYNTAX	Counter
	ACCESS	read-only
	STATUS	mandatory
	DESCRIPTION
		" Low Prio Transmit Clip Count "
	::= { wfCctOptsEntry 14 }

wfCctOptsIntrQHighWaterPkts OBJECT-TYPE
	SYNTAX	Gauge
	ACCESS	read-only
	STATUS	mandatory
	DESCRIPTION
		" Interrupt Queue high-water mark "
	::= { wfCctOptsEntry 15 }

wfCctOptsHiQHighWaterPkts OBJECT-TYPE
	SYNTAX	Gauge
	ACCESS	read-only
	STATUS	mandatory
	DESCRIPTION
		" High-priority Queue high-water mark "
	::= { wfCctOptsEntry 16 }

wfCctOptsNormalQHighWaterPkts OBJECT-TYPE
	SYNTAX	Gauge
	ACCESS	read-only
	STATUS	mandatory
	DESCRIPTION
		" Normal Queue high-water mark "
	::= { wfCctOptsEntry 17 }

wfCctOptsLoQHighWaterPkts OBJECT-TYPE
	SYNTAX	Gauge
	ACCESS	read-only
	STATUS	mandatory
	DESCRIPTION
		" Low-priority Queue high-water mark "
	::= { wfCctOptsEntry 18 }

wfCctOptsHighWaterPktsClear OBJECT-TYPE
	SYNTAX	INTEGER
	ACCESS	read-write
	STATUS	mandatory
	DESCRIPTION
		" Attribute to clear the high-water marks. When the MIB
		  changes, Priority Queueing (if ENABLED) checks to see
		  if HighWaterPktsClear is different than the last time the MIB
		  was modified in any way.  If it is different, 
		  all the high water marks (see above) are set to zero.
		 "
	::= { wfCctOptsEntry 19 }

wfCctOptsDroppedPkts OBJECT-TYPE
	SYNTAX	Counter
	ACCESS	read-only
	STATUS	mandatory
	DESCRIPTION
		" Packets which were filtered in Priority Queueing "
	::= { wfCctOptsEntry 20 }

wfCctOptsLargePkts OBJECT-TYPE
	SYNTAX	Counter
	ACCESS	read-only
	STATUS	mandatory
	DESCRIPTION
		" Large Packets which became an exception to latency rules "
	::= { wfCctOptsEntry 21 }

wfCctOptsRxPkts OBJECT-TYPE
	SYNTAX	Counter
	ACCESS	read-only
	STATUS	mandatory
	DESCRIPTION
		" Packets received "
	::= { wfCctOptsEntry 22 }

wfCctOptsBrFilterTable OBJECT-TYPE
	SYNTAX	SEQUENCE OF WfCctOptsBrFilterEntry
	ACCESS	not-accessible
	STATUS	mandatory
	DESCRIPTION
		" Bridge  Filters "
	::= { wfCircuitOptsGroup 2 }

wfCctOptsBrFilterEntry OBJECT-TYPE
	SYNTAX	WfCctOptsBrFilterEntry
	ACCESS	not-accessible
	STATUS	mandatory
	DESCRIPTION
		" An entry in WfCctOptsBrFilterTable. "
	INDEX	{ wfCctOptsBrFilterCct,
		wfCctOptsBrFilterRuleNumber,
		wfCctOptsBrFilterFragment }
	::= { wfCctOptsBrFilterTable 1 }

WfCctOptsBrFilterEntry ::= SEQUENCE {
	wfCctOptsBrFilterCreate
		INTEGER,
	wfCctOptsBrFilterEnable
		INTEGER,
	wfCctOptsBrFilterState
		INTEGER,
	wfCctOptsBrFilterCounter
		Counter,
	wfCctOptsBrFilterDefinition
		OCTET STRING,
	wfCctOptsBrFilterReserved
		INTEGER,
	wfCctOptsBrFilterCct
		INTEGER,
	wfCctOptsBrFilterRuleNumber
		INTEGER,
	wfCctOptsBrFilterFragment
		INTEGER
}

wfCctOptsBrFilterCreate OBJECT-TYPE
	SYNTAX	INTEGER {
		created(1),
		deleted(2)
	}
	ACCESS	read-write
	STATUS	mandatory
	DESCRIPTION
		" Defines the existence of the traffic filter rule:
		  created - traffic filter exists
		  delete - traffic filter does not exist and can be deleted. "
	DEFVAL	{ created }
	::= { wfCctOptsBrFilterEntry 1 }

wfCctOptsBrFilterEnable OBJECT-TYPE
	SYNTAX	INTEGER {
		enabled(1),
		disabled(2)
	}
	ACCESS	read-write
	STATUS	mandatory
	DESCRIPTION
		" Defines whether or not the traffic filter rule should be used:
		  enabled - activate the rule.
		  disabled - inactivate the rule. "
	DEFVAL	{ enabled }
	::= { wfCctOptsBrFilterEntry 2 }

wfCctOptsBrFilterState OBJECT-TYPE
	SYNTAX	INTEGER {
		active(1),
		error(2),
		inactive(3)
	}
	ACCESS	read-only
	STATUS	mandatory
	DESCRIPTION
		" Defines the current State of the traffic filter:
		  inactive - the rule is not in use.
		  active - the rule is being used.
		  error - the application detected an error in the rule. "
	DEFVAL	{ inactive }
	::= { wfCctOptsBrFilterEntry 3 }

wfCctOptsBrFilterCounter OBJECT-TYPE
	SYNTAX	Counter
	ACCESS	read-only
	STATUS	mandatory
	DESCRIPTION
		" The number of received packets that have
		           matched this rule. "
	::= { wfCctOptsBrFilterEntry 4 }

wfCctOptsBrFilterDefinition OBJECT-TYPE
	SYNTAX	OCTET STRING
	ACCESS	read-write
	STATUS	mandatory
	DESCRIPTION
		" The filter rule definition. "
	::= { wfCctOptsBrFilterEntry 5 }

wfCctOptsBrFilterReserved OBJECT-TYPE
	SYNTAX	INTEGER
	ACCESS	not-accessible
	STATUS	mandatory
	DESCRIPTION
		" Reserved field. "
	::= { wfCctOptsBrFilterEntry 6 }

wfCctOptsBrFilterCct OBJECT-TYPE
	SYNTAX	INTEGER
	ACCESS	read-only
	STATUS	mandatory
	DESCRIPTION
		" The ID of the CctBridge Cct to which the
		    filter is applied. "
	::= { wfCctOptsBrFilterEntry 7 }

wfCctOptsBrFilterRuleNumber OBJECT-TYPE
	SYNTAX	INTEGER
	ACCESS	read-only
	STATUS	mandatory
	DESCRIPTION
		" ID for the rule. "
	::= { wfCctOptsBrFilterEntry 8 }

wfCctOptsBrFilterFragment OBJECT-TYPE
	SYNTAX	INTEGER
	ACCESS	read-only
	STATUS	mandatory
	DESCRIPTION
		" Fragment number - for large rules. "
	::= { wfCctOptsBrFilterEntry 9 }

wfCctOptsIpFilterTable OBJECT-TYPE
	SYNTAX	SEQUENCE OF WfCctOptsIpFilterEntry
	ACCESS	not-accessible
	STATUS	mandatory
	DESCRIPTION
		" Ip  Filters "
	::= { wfCircuitOptsGroup 3 }

wfCctOptsIpFilterEntry OBJECT-TYPE
	SYNTAX	WfCctOptsIpFilterEntry
	ACCESS	not-accessible
	STATUS	mandatory
	DESCRIPTION
		" An entry in WfCctOptsIpFilterTable. "
	INDEX	{ wfCctOptsIpFilterCct,
		wfCctOptsIpFilterRuleNumber,
		wfCctOptsIpFilterFragment }
	::= { wfCctOptsIpFilterTable 1 }

WfCctOptsIpFilterEntry ::= SEQUENCE {
	wfCctOptsIpFilterCreate
		INTEGER,
	wfCctOptsIpFilterEnable
		INTEGER,
	wfCctOptsIpFilterState
		INTEGER,
	wfCctOptsIpFilterCounter
		Counter,
	wfCctOptsIpFilterDefinition
		OCTET STRING,
	wfCctOptsIpFilterReserved
		INTEGER,
	wfCctOptsIpFilterCct
		INTEGER,
	wfCctOptsIpFilterRuleNumber
		INTEGER,
	wfCctOptsIpFilterFragment
		INTEGER
}

wfCctOptsIpFilterCreate OBJECT-TYPE
	SYNTAX	INTEGER {
		created(1),
		deleted(2)
	}
	ACCESS	read-write
	STATUS	mandatory
	DESCRIPTION
		" Defines the existence of the traffic filter rule:
		  created - traffic filter exists
		  delete - traffic filter does not exist and can be deleted. "
	DEFVAL	{ created }
	::= { wfCctOptsIpFilterEntry 1 }

wfCctOptsIpFilterEnable OBJECT-TYPE
	SYNTAX	INTEGER {
		enabled(1),
		disabled(2)
	}
	ACCESS	read-write
	STATUS	mandatory
	DESCRIPTION
		" Defines whether or not the traffic filter rule should be used:
		  enabled - activate the rule.
		  disabled - inactivate the rule. "
	DEFVAL	{ enabled }
	::= { wfCctOptsIpFilterEntry 2 }

wfCctOptsIpFilterState OBJECT-TYPE
	SYNTAX	INTEGER {
		active(1),
		error(2),
		inactive(3)
	}
	ACCESS	read-only
	STATUS	mandatory
	DESCRIPTION
		" Defines the current State of the traffic filter:
		  inactive - the rule is not in use.
		  active - the rule is being used.
		  error - the application detected an error in the rule. "
	DEFVAL	{ inactive }
	::= { wfCctOptsIpFilterEntry 3 }

wfCctOptsIpFilterCounter OBJECT-TYPE
	SYNTAX	Counter
	ACCESS	read-only
	STATUS	mandatory
	DESCRIPTION
		" The number of received packets that have
		           matched this rule. "
	::= { wfCctOptsIpFilterEntry 4 }

wfCctOptsIpFilterDefinition OBJECT-TYPE
	SYNTAX	OCTET STRING
	ACCESS	read-write
	STATUS	mandatory
	DESCRIPTION
		" The filter rule definition. "
	::= { wfCctOptsIpFilterEntry 5 }

wfCctOptsIpFilterReserved OBJECT-TYPE
	SYNTAX	INTEGER
	ACCESS	not-accessible
	STATUS	mandatory
	DESCRIPTION
		" Reserved field. "
	::= { wfCctOptsIpFilterEntry 6 }

wfCctOptsIpFilterCct OBJECT-TYPE
	SYNTAX	INTEGER
	ACCESS	read-only
	STATUS	mandatory
	DESCRIPTION
		" The ID of the CctIp Cct to which the
		    filter is applied. "
	::= { wfCctOptsIpFilterEntry 7 }

wfCctOptsIpFilterRuleNumber OBJECT-TYPE
	SYNTAX	INTEGER
	ACCESS	read-only
	STATUS	mandatory
	DESCRIPTION
		" ID for the rule. "
	::= { wfCctOptsIpFilterEntry 8 }

wfCctOptsIpFilterFragment OBJECT-TYPE
	SYNTAX	INTEGER
	ACCESS	read-only
	STATUS	mandatory
	DESCRIPTION
		" Fragment number - for large rules. "
	::= { wfCctOptsIpFilterEntry 9 }

wfCctOptsLengthBasedTable OBJECT-TYPE
	SYNTAX	SEQUENCE OF WfCctOptsLengthBasedEntry
	ACCESS	not-accessible
	STATUS	mandatory
	DESCRIPTION
		" Length Based Priority Table "
	::= { wfCircuitOptsGroup 4 }

wfCctOptsLengthBasedEntry OBJECT-TYPE
	SYNTAX	WfCctOptsLengthBasedEntry
	ACCESS	not-accessible
	STATUS	mandatory
	DESCRIPTION
		" An entry in WfCctOptsLengthBasedTable. "
	INDEX	{ wfCctOptsLengthBasedCct,
		wfCctOptsLengthBasedMux,
		wfCctOptsLengthBasedData }
	::= { wfCctOptsLengthBasedTable 1 }

WfCctOptsLengthBasedEntry ::= SEQUENCE {
	wfCctOptsLengthBasedDelete
		INTEGER,
	wfCctOptsLengthBasedDisable
		INTEGER,
	wfCctOptsLengthBasedState
		INTEGER,
	wfCctOptsLengthBasedCct
		INTEGER,
	wfCctOptsLengthBasedMux
		INTEGER,
	wfCctOptsLengthBasedData
		OCTET STRING,
	wfCctOptsLengthBasedLength
		INTEGER,
	wfCctOptsLengthBasedLessThanQ
		INTEGER,
	wfCctOptsLengthBasedGreaterThanQ
		INTEGER
}

wfCctOptsLengthBasedDelete OBJECT-TYPE
	SYNTAX	INTEGER {
		created(1),
		deleted(2)
	}
	ACCESS	read-write
	STATUS	mandatory
	DESCRIPTION
		" Defines the existence of the length based priority filter rule:
		  created - traffic filter exists
		  delete - traffic filter does not exist and can be deleted. "
	DEFVAL	{ created }
	::= { wfCctOptsLengthBasedEntry 1 }

wfCctOptsLengthBasedDisable OBJECT-TYPE
	SYNTAX	INTEGER {
		enabled(1),
		disabled(2)
	}
	ACCESS	read-write
	STATUS	mandatory
	DESCRIPTION
		" Defines whether or not the length based priority filter rule should be used:
		  enabled - activate the rule.
		  disabled - inactivate the rule. "
	DEFVAL	{ enabled }
	::= { wfCctOptsLengthBasedEntry 2 }

wfCctOptsLengthBasedState OBJECT-TYPE
	SYNTAX	INTEGER {
		active(1),
		error(2),
		inactive(3)
	}
	ACCESS	read-only
	STATUS	mandatory
	DESCRIPTION
		" Defines the current State of the length based priority filter:
		  inactive - the rule is not in use.
		  active - the rule is being used.
		  error - the application detected an error in the rule. "
	DEFVAL	{ inactive }
	::= { wfCctOptsLengthBasedEntry 3 }

wfCctOptsLengthBasedCct OBJECT-TYPE
	SYNTAX	INTEGER
	ACCESS	read-only
	STATUS	mandatory
	DESCRIPTION
		" The ID of the Cct to which the filter is applied "
	::= { wfCctOptsLengthBasedEntry 4 }

wfCctOptsLengthBasedMux OBJECT-TYPE
	SYNTAX	INTEGER {
		etype(1),
		lsap(2),
		snap(3)
	}
	ACCESS	read-only
	STATUS	mandatory
	DESCRIPTION
		" packet mux type "
	DEFVAL	{ etype }
	::= { wfCctOptsLengthBasedEntry 5 }

wfCctOptsLengthBasedData OBJECT-TYPE
	SYNTAX	OCTET STRING
	ACCESS	read-only
	STATUS	mandatory
	DESCRIPTION
		" a five byte quantity of the form
		  ethernet  - 0x6003000000 (e.g. DECnet)
		  lsap      - 0xfefe030000 (e.g. OSI)
		  snap      - 0x0000000800 (e.g. IP)
		     - 0x0800070800 (e.g. Appletalk DDP) "
	::= { wfCctOptsLengthBasedEntry 6 }

wfCctOptsLengthBasedLength OBJECT-TYPE
	SYNTAX	INTEGER
	ACCESS	read-write
	STATUS	mandatory
	DESCRIPTION
		" Maximum length of a packet to be considered high priority "
	::= { wfCctOptsLengthBasedEntry 7 }

wfCctOptsLengthBasedLessThanQ OBJECT-TYPE
	SYNTAX	INTEGER {
		hi(3),
		normal(2),
		lo(1)
	}
	ACCESS	read-write
	STATUS	mandatory
	DESCRIPTION
		" queue into which packets of length less than or equal
		    wfCctOptsLengthBasedLength are placed "
	DEFVAL	{ normal }
	::= { wfCctOptsLengthBasedEntry 8 }

wfCctOptsLengthBasedGreaterThanQ OBJECT-TYPE
	SYNTAX	INTEGER {
		hi(3),
		normal(2),
		lo(1)
	}
	ACCESS	read-write
	STATUS	mandatory
	DESCRIPTION
		" queue into which packets of length greater than
		    wfCctOptsLengthBasedLength are placed "
	DEFVAL	{ lo }
	::= { wfCctOptsLengthBasedEntry 9 }

wfCircuitNameTable OBJECT-TYPE
	SYNTAX	SEQUENCE OF WfCircuitNameEntry
	ACCESS	not-accessible
	STATUS	mandatory
	DESCRIPTION
		" The table of circuit names "
	::= { wfServices 3 }

wfCircuitNameEntry OBJECT-TYPE
	SYNTAX	WfCircuitNameEntry
	ACCESS	not-accessible
	STATUS	mandatory
	DESCRIPTION
		" Entry format for the table of circuit names "
	INDEX	{ wfCircuitNumber }
	::= { wfCircuitNameTable 1 }

WfCircuitNameEntry ::= SEQUENCE {
	wfCircuitNameDelete
		INTEGER,
	wfCircuitNumber
		INTEGER,
	wfCircuitName
		DisplayString,
	wfCircuitIfType
		INTEGER,
	wfCircuitProtoMap
		OCTET STRING
}

wfCircuitNameDelete OBJECT-TYPE
	SYNTAX	INTEGER {
		create(1),
		delete(2)
	}
	ACCESS	read-write
	STATUS	mandatory
	DESCRIPTION
		" Creation and deletion flag for this record "
	DEFVAL	{ create }
	::= { wfCircuitNameEntry 1 }

wfCircuitNumber OBJECT-TYPE
	SYNTAX	INTEGER
	ACCESS	read-only
	STATUS	mandatory
	DESCRIPTION
		" circuit number "
	::= { wfCircuitNameEntry 2 }

wfCircuitName OBJECT-TYPE
	SYNTAX	DisplayString
	ACCESS	read-write
	STATUS	mandatory
	DESCRIPTION
		" circuit name "
	::= { wfCircuitNameEntry 3 }

wfCircuitIfType OBJECT-TYPE
	SYNTAX	INTEGER {
		csmacd(10),
		sync(20),
		t1(30),
		e1(40),
		token(50),
		fddi(60),
		hssi(70)
	}
	ACCESS	read-write
	STATUS	mandatory
	DESCRIPTION
		" circuit interface type "
	::= { wfCircuitNameEntry 4 }

wfCircuitProtoMap OBJECT-TYPE
	SYNTAX	OCTET STRING
	ACCESS	read-write
	STATUS	mandatory
	DESCRIPTION
		" The Circuit-Protocol mask "
	::= { wfCircuitNameEntry 5 }

wfConsole	OBJECT IDENTIFIER ::= { wfServices 1 }

wfBaudRate OBJECT-TYPE
	SYNTAX	INTEGER
	ACCESS	read-write
	STATUS	mandatory
	DESCRIPTION
		" Baud rate configured on the Technician Interface console "
	DEFVAL	{ 9600 }
	::= { wfConsole 1 }

wfDataBits OBJECT-TYPE
	SYNTAX	INTEGER
	ACCESS	read-write
	STATUS	mandatory
	DESCRIPTION
		" Number of data bits configured on the Technician Interface console "
	DEFVAL	{ 8 }
	::= { wfConsole 2 }

wfParity OBJECT-TYPE
	SYNTAX	INTEGER {
		none(1),
		odd(2),
		even(3)
	}
	ACCESS	read-write
	STATUS	mandatory
	DESCRIPTION
		" Type of parity configured on the Technician Interface console "
	DEFVAL	{ none }
	::= { wfConsole 3 }

wfStopBits OBJECT-TYPE
	SYNTAX	INTEGER {
		s1bit(1),
		s15bit(2),
		s2bit(3)
	}
	ACCESS	read-write
	STATUS	mandatory
	DESCRIPTION
		" Number of stop bits configured on the Technician Interface console "
	DEFVAL	{ s1bit }
	::= { wfConsole 4 }

wfModemEnable OBJECT-TYPE
	SYNTAX	INTEGER {
		enabled(1),
		disabled(2)
	}
	ACCESS	read-write
	STATUS	mandatory
	DESCRIPTION
		" Enable the Technician Interface console to run over a modem "
	DEFVAL	{ disabled }
	::= { wfConsole 5 }

wfLinesPerScreen OBJECT-TYPE
	SYNTAX	INTEGER
	ACCESS	read-write
	STATUS	mandatory
	DESCRIPTION
		" Number of lines which can be displayed in one screen on the Technician
		   Interface console "
	DEFVAL	{ 24 }
	::= { wfConsole 6 }

wfMoreEnable OBJECT-TYPE
	SYNTAX	INTEGER {
		enabled(1),
		disabled(2)
	}
	ACCESS	read-write
	STATUS	mandatory
	DESCRIPTION
		" Enable the 'more' feature on the Technician Interface console "
	DEFVAL	{ enabled }
	::= { wfConsole 7 }

wfPrompt OBJECT-TYPE
	SYNTAX	DisplayString
	ACCESS	read-write
	STATUS	mandatory
	DESCRIPTION
		" Character string which will be used as the system prompt on
		   the Technician Interface console "
	::= { wfConsole 8 }

wfLoginTimeOut OBJECT-TYPE
	SYNTAX	INTEGER {
		minimum(1),
		maximum(99),
		default(1)
	}
	ACCESS	read-write
	STATUS	mandatory
	DESCRIPTION
		" IF MODEM_ENABLED then time out in minutes to HUP when at the login prompt "
	DEFVAL	{ default }
	::= { wfConsole 9 }

wfPasswordTimeOut OBJECT-TYPE
	SYNTAX	INTEGER {
		minimum(1),
		maximum(99),
		default(1)
	}
	ACCESS	read-write
	STATUS	mandatory
	DESCRIPTION
		" Timout on Password entry "
	DEFVAL	{ default }
	::= { wfConsole 10 }

wfCommandTimeOut OBJECT-TYPE
	SYNTAX	INTEGER {
		minimum(1),
		maximum(99),
		default(15)
	}
	ACCESS	read-write
	STATUS	mandatory
	DESCRIPTION
		" IF MODEM_ENABLED then time out in minutes to HUP when at the command prompt "
	DEFVAL	{ default }
	::= { wfConsole 11 }

wfLoginRetries OBJECT-TYPE
	SYNTAX	INTEGER {
		minimum(1),
		maximum(99),
		default(3)
	}
	ACCESS	read-write
	STATUS	mandatory
	DESCRIPTION
		" IF MODEM_ENABLED then limit # of login attempts then HUP "
	DEFVAL	{ default }
	::= { wfConsole 12 }

wfTotalLogins OBJECT-TYPE
	SYNTAX	Counter
	ACCESS	read-only
	STATUS	mandatory
	DESCRIPTION
		" Total number of TI login attempts "
	::= { wfConsole 13 }

wfUserLoginErrors OBJECT-TYPE
	SYNTAX	Counter
	ACCESS	read-only
	STATUS	mandatory
	DESCRIPTION
		" Total number of FAILED User login attempts "
	::= { wfConsole 14 }

wfManagerLoginErrors OBJECT-TYPE
	SYNTAX	Counter
	ACCESS	read-only
	STATUS	mandatory
	DESCRIPTION
		" Total number of FAILED Manager login attempts "
	::= { wfConsole 15 }

wfOtherLoginErrors OBJECT-TYPE
	SYNTAX	Counter
	ACCESS	read-only
	STATUS	mandatory
	DESCRIPTION
		" Total number of FAILED Other login attempts "
	::= { wfConsole 16 }

wfTtyFrameErrors OBJECT-TYPE
	SYNTAX	Counter
	ACCESS	read-only
	STATUS	mandatory
	DESCRIPTION
		" Count of TTY Frame errors "
	::= { wfConsole 17 }

wfTtyOverrunErrors OBJECT-TYPE
	SYNTAX	Counter
	ACCESS	read-only
	STATUS	mandatory
	DESCRIPTION
		" Count of TTY Overrun errors "
	::= { wfConsole 18 }

wfTtyParityErrors OBJECT-TYPE
	SYNTAX	Counter
	ACCESS	read-only
	STATUS	mandatory
	DESCRIPTION
		" Count of TTY Parity errors "
	::= { wfConsole 19 }

wfTtyInfifoErrors OBJECT-TYPE
	SYNTAX	Counter
	ACCESS	read-only
	STATUS	mandatory
	DESCRIPTION
		" Count of TTY Input Fifo errors "
	::= { wfConsole 20 }

wfCSMACDTable OBJECT-TYPE
	SYNTAX	SEQUENCE OF WfCSMACDEntry
	ACCESS	not-accessible
	STATUS	mandatory
	DESCRIPTION
		"
		   CSMA/CD line record
		 "
	::= { wfLine 1 }

wfCSMACDEntry OBJECT-TYPE
	SYNTAX	WfCSMACDEntry
	ACCESS	not-accessible
	STATUS	mandatory
	DESCRIPTION
		" An entry in the csmacd table "
	INDEX	{ wfCSMACDSlot,
		wfCSMACDConnector }
	::= { wfCSMACDTable 1 }

WfCSMACDEntry ::= SEQUENCE {
	wfCSMACDDelete
		INTEGER,
	wfCSMACDEnable
		INTEGER,
	wfCSMACDState
		INTEGER,
	wfCSMACDSlot
		INTEGER,
	wfCSMACDConnector
		INTEGER,
	wfCSMACDCct
		INTEGER,
	wfCSMACDBofl
		INTEGER,
	wfCSMACDBoflTmo
		INTEGER,
	wfCSMACDMtu
		INTEGER,
	wfCSMACDMadr
		OCTET STRING,
	wfCSMACDOctetsRxOk
		Counter,
	wfCSMACDFramesRxOk
		Counter,
	wfCSMACDOctetsTxOk
		Counter,
	wfCSMACDFramesTxOk
		Counter,
	wfCSMACDDeferredTx
		Counter,
	wfCSMACDLateCollnTx
		Counter,
	wfCSMACDExcessvCollnTx
		Counter,
	wfCSMACDBablErrorTx
		Counter,
	wfCSMACDBufErrorTx
		Counter,
	wfCSMACDLcarTx
		Counter,
	wfCSMACDUfloTx
		Counter,
	wfCSMACDFcsErrorRx
		Counter,
	wfCSMACDAlignErrorRx
		Counter,
	wfCSMACDLackRescErrorRx
		Counter,
	wfCSMACDTooLongErrorRx
		Counter,
	wfCSMACDOfloRx
		Counter,
	wfCSMACDMerr
		Counter,
	wfCSMACDCerr
		Counter,
	wfCSMACDHardwareFilter
		INTEGER,
	wfCSMACDTxQueueLength
		INTEGER,
	wfCSMACDRxQueueLength
		INTEGER,
	wfCSMACDTxClipFrames
		Counter,
	wfCSMACDRxReplenMisses
		Counter
}

wfCSMACDDelete OBJECT-TYPE
	SYNTAX	INTEGER {
		create(1),
		delete(2)
	}
	ACCESS	read-write
	STATUS	mandatory
	DESCRIPTION
		" create/delete parameter, dflt = created "
	DEFVAL	{ create }
	::= { wfCSMACDEntry 1 }

wfCSMACDEnable OBJECT-TYPE
	SYNTAX	INTEGER {
		enable(1),
		disable(2)
	}
	ACCESS	read-write
	STATUS	mandatory
	DESCRIPTION
		" enable/disable parameter, dflt = enabled "
	DEFVAL	{ enable }
	::= { wfCSMACDEntry 2 }

wfCSMACDState OBJECT-TYPE
	SYNTAX	INTEGER {
		up(1),
		down(2),
		init(3),
		notpresent(4)
	}
	ACCESS	read-only
	STATUS	mandatory
	DESCRIPTION
		" line driver state variable, Not Present, Init, Down, Up "
	DEFVAL	{ notpresent }
	::= { wfCSMACDEntry 3 }

wfCSMACDSlot OBJECT-TYPE
	SYNTAX	INTEGER {
		minimum(1),
		maximum(14)
	}
	ACCESS	read-only
	STATUS	mandatory
	DESCRIPTION
		" instance ID Slot, filled in by driver "
	::= { wfCSMACDEntry 4 }

wfCSMACDConnector OBJECT-TYPE
	SYNTAX	INTEGER {
		one(1),
		two(2),
		three(3),
		four(4)
	}
	ACCESS	read-only
	STATUS	mandatory
	DESCRIPTION
		" instance ID Connector, filled in by driver "
	::= { wfCSMACDEntry 5 }

wfCSMACDCct OBJECT-TYPE
	SYNTAX	INTEGER {
		minimum(1),
		maximum(1023)
	}
	ACCESS	read-write
	STATUS	mandatory
	DESCRIPTION
		" cct number for this line instance "
	::= { wfCSMACDEntry 6 }

wfCSMACDBofl OBJECT-TYPE
	SYNTAX	INTEGER {
		enable(1),
		disable(2)
	}
	ACCESS	read-write
	STATUS	mandatory
	DESCRIPTION
		" bofl parameter, dflt = enabled "
	DEFVAL	{ enable }
	::= { wfCSMACDEntry 7 }

wfCSMACDBoflTmo OBJECT-TYPE
	SYNTAX	INTEGER {
		minimum(1),
		maximum(60),
		default(5)
	}
	ACCESS	read-write
	STATUS	mandatory
	DESCRIPTION
		" bofl parameter, dflt = 5 "
	DEFVAL	{ default }
	::= { wfCSMACDEntry 8 }

wfCSMACDMtu OBJECT-TYPE
	SYNTAX	INTEGER {
		default(1518)
	}
	ACCESS	read-only
	STATUS	mandatory
	DESCRIPTION
		" mtu parameter, fixed "
	DEFVAL	{ default }
	::= { wfCSMACDEntry 9 }

wfCSMACDMadr OBJECT-TYPE
	SYNTAX	OCTET STRING
	ACCESS	read-only
	STATUS	mandatory
	DESCRIPTION
		" line MAC address, fixed - line driver fills in "
	::= { wfCSMACDEntry 10 }

wfCSMACDOctetsRxOk OBJECT-TYPE
	SYNTAX	Counter
	ACCESS	read-only
	STATUS	mandatory
	DESCRIPTION
		" Number of octets received without error "
	::= { wfCSMACDEntry 11 }

wfCSMACDFramesRxOk OBJECT-TYPE
	SYNTAX	Counter
	ACCESS	read-only
	STATUS	mandatory
	DESCRIPTION
		" Number of frames received without error "
	::= { wfCSMACDEntry 12 }

wfCSMACDOctetsTxOk OBJECT-TYPE
	SYNTAX	Counter
	ACCESS	read-only
	STATUS	mandatory
	DESCRIPTION
		" Number of octets transmitted without error "
	::= { wfCSMACDEntry 13 }

wfCSMACDFramesTxOk OBJECT-TYPE
	SYNTAX	Counter
	ACCESS	read-only
	STATUS	mandatory
	DESCRIPTION
		" Number of frames transmitted without error "
	::= { wfCSMACDEntry 14 }

wfCSMACDDeferredTx OBJECT-TYPE
	SYNTAX	Counter
	ACCESS	read-only
	STATUS	mandatory
	DESCRIPTION
		" Number of deferred transmissions "
	::= { wfCSMACDEntry 15 }

wfCSMACDLateCollnTx OBJECT-TYPE
	SYNTAX	Counter
	ACCESS	read-only
	STATUS	mandatory
	DESCRIPTION
		" Number of late collisions "
	::= { wfCSMACDEntry 16 }

wfCSMACDExcessvCollnTx OBJECT-TYPE
	SYNTAX	Counter
	ACCESS	read-only
	STATUS	mandatory
	DESCRIPTION
		" Number of excessive collisions "
	::= { wfCSMACDEntry 17 }

wfCSMACDBablErrorTx OBJECT-TYPE
	SYNTAX	Counter
	ACCESS	read-only
	STATUS	mandatory
	DESCRIPTION
		" Number of frames transmitted larger than 1518 octets "
	::= { wfCSMACDEntry 18 }

wfCSMACDBufErrorTx OBJECT-TYPE
	SYNTAX	Counter
	ACCESS	read-only
	STATUS	mandatory
	DESCRIPTION
		" Number of internal buffer errors "
	::= { wfCSMACDEntry 19 }

wfCSMACDLcarTx OBJECT-TYPE
	SYNTAX	Counter
	ACCESS	read-only
	STATUS	mandatory
	DESCRIPTION
		" Number of loss of carrier errors "
	::= { wfCSMACDEntry 20 }

wfCSMACDUfloTx OBJECT-TYPE
	SYNTAX	Counter
	ACCESS	read-only
	STATUS	mandatory
	DESCRIPTION
		" Number of transmitter underflow errors "
	::= { wfCSMACDEntry 21 }

wfCSMACDFcsErrorRx OBJECT-TYPE
	SYNTAX	Counter
	ACCESS	read-only
	STATUS	mandatory
	DESCRIPTION
		" Number of receiver checksum errors "
	::= { wfCSMACDEntry 22 }

wfCSMACDAlignErrorRx OBJECT-TYPE
	SYNTAX	Counter
	ACCESS	read-only
	STATUS	mandatory
	DESCRIPTION
		" Number of receiver alignment errors "
	::= { wfCSMACDEntry 23 }

wfCSMACDLackRescErrorRx OBJECT-TYPE
	SYNTAX	Counter
	ACCESS	read-only
	STATUS	mandatory
	DESCRIPTION
		" Number of receiver lack of resource errors "
	::= { wfCSMACDEntry 24 }

wfCSMACDTooLongErrorRx OBJECT-TYPE
	SYNTAX	Counter
	ACCESS	read-only
	STATUS	mandatory
	DESCRIPTION
		" Number of frames received exceeding 1518 octets "
	::= { wfCSMACDEntry 25 }

wfCSMACDOfloRx OBJECT-TYPE
	SYNTAX	Counter
	ACCESS	read-only
	STATUS	mandatory
	DESCRIPTION
		" Number of receiver overflow errors "
	::= { wfCSMACDEntry 26 }

wfCSMACDMerr OBJECT-TYPE
	SYNTAX	Counter
	ACCESS	read-only
	STATUS	mandatory
	DESCRIPTION
		" Number of internal memory errors "
	::= { wfCSMACDEntry 27 }

wfCSMACDCerr OBJECT-TYPE
	SYNTAX	Counter
	ACCESS	read-only
	STATUS	mandatory
	DESCRIPTION
		" Number of collision errors "
	::= { wfCSMACDEntry 28 }

wfCSMACDHardwareFilter OBJECT-TYPE
	SYNTAX	INTEGER {
		enable(1),
		disable(2)
	}
	ACCESS	read-write
	STATUS	mandatory
	DESCRIPTION
		" Hardware filtering parameter. "
	DEFVAL	{ disable }
	::= { wfCSMACDEntry 29 }

wfCSMACDTxQueueLength OBJECT-TYPE
	SYNTAX	INTEGER {
		minimum(1),
		maximum(255),
		default(32)
	}
	ACCESS	read-write
	STATUS	mandatory
	DESCRIPTION
		" Transmit Queue Length, values larger than the compiled ring size
		   are truncated to the compiled ring size.
		"
	DEFVAL	{ default }
	::= { wfCSMACDEntry 30 }

wfCSMACDRxQueueLength OBJECT-TYPE
	SYNTAX	INTEGER {
		minimum(1),
		maximum(255),
		default(32)
	}
	ACCESS	read-write
	STATUS	mandatory
	DESCRIPTION
		" Receive Queue Length, values larger than the compiled ring size
		   are truncated to the compiled ring size.
		"
	DEFVAL	{ default }
	::= { wfCSMACDEntry 31 }

wfCSMACDTxClipFrames OBJECT-TYPE
	SYNTAX	Counter
	ACCESS	read-only
	STATUS	mandatory
	DESCRIPTION
		" Number of frames clipped in driver's transmit routine due to transmit
		   congestion.
		"
	::= { wfCSMACDEntry 32 }

wfCSMACDRxReplenMisses OBJECT-TYPE
	SYNTAX	Counter
	ACCESS	read-only
	STATUS	mandatory
	DESCRIPTION
		" Number of packet buffer misses while attempting to replenish driver
		   receive ring.
		"
	::= { wfCSMACDEntry 33 }

wfivRouteGroup	OBJECT IDENTIFIER ::= { wfDecGroup 1 }

wfivRouteCreateDelete OBJECT-TYPE
	SYNTAX	INTEGER {
		create(1),
		delete(2)
	}
	ACCESS	read-write
	STATUS	mandatory
	DESCRIPTION
		"
		 'This value determines whether DECnet is configured on this slot.'
		 "
	DEFVAL	{ create }
	::= { wfivRouteGroup 1 }

wfivRouteEnableDisable OBJECT-TYPE
	SYNTAX	INTEGER {
		enable(1),
		disable(2)
	}
	ACCESS	read-write
	STATUS	mandatory
	DESCRIPTION
		"
		  'This value determines whether DECnet is to startup.'
		 "
	DEFVAL	{ enable }
	::= { wfivRouteGroup 2 }

wfivRouteState OBJECT-TYPE
	SYNTAX	INTEGER {
		notpresent(4),
		initializing(3),
		down(2),
		up(1)
	}
	ACCESS	read-only
	STATUS	mandatory
	DESCRIPTION
		"
		  'This value determines whether DECnet is to startup.'
		 "
	DEFVAL	{ notpresent }
	::= { wfivRouteGroup 3 }

wfivRouteBroadcastRouteTimer OBJECT-TYPE
	SYNTAX	INTEGER {
		routetimermin(1),
		routetimerdflt(180),
		routetimermax(65535)
	}
	ACCESS	read-write
	STATUS	mandatory
	DESCRIPTION
		"
		  'This value determines the maximum time allowed between
		  Routing updates on Ethernet circuits. When this timer expires
		  before a routing update occurs, a routing update is forced.
		  With a standard calculation, Routing also uses this timer to
		  enforce a minimum delay between routing updates. Seconds is a
		  decimal integer in the range 1-65535.'
		 "
	DEFVAL	{ routetimerdflt }
	::= { wfivRouteGroup 4 }

wfivRouteRoutingVers OBJECT-TYPE
	SYNTAX	DisplayString
	ACCESS	read-only
	STATUS	mandatory
	DESCRIPTION
		"
		  'This read-only parameter identifies the executor node's
		  Routing version number. The format is the same as for the
		  Network Management version number.'
		  "
	::= { wfivRouteGroup 5 }

wfivRouteMaxAddr OBJECT-TYPE
	SYNTAX	INTEGER {
		minaddr(1),
		maxaddr(1023)
	}
	ACCESS	read-write
	STATUS	mandatory
	DESCRIPTION
		"
		 'This value represents the largest node number and,
		 therefore, number of nodes that can be known about
		 by the executor node's home area. The number is an integer
		 in the range 1-1023.'
		 "
	DEFVAL	{ maxaddr }
	::= { wfivRouteGroup 6 }

wfivRouteMaxBdcastNonRouters OBJECT-TYPE
	SYNTAX	INTEGER {
		nonroutersdflt(64),
		nonroutersmax(1023)
	}
	ACCESS	read-write
	STATUS	mandatory
	DESCRIPTION
		"
		 'This value represents the maximum total number of nonrouters
		 the executor node can have on its broadcast circuits for one slot. 
		 The number is an integer in the range 0-1023.'
		 "
	DEFVAL	{ nonroutersdflt }
	::= { wfivRouteGroup 7 }

wfivRouteMaxBdcastRouters OBJECT-TYPE
	SYNTAX	INTEGER {
		routersdflt(32),
		routersdmax(1023)
	}
	ACCESS	read-write
	STATUS	mandatory
	DESCRIPTION
		"
		 'This value represents the maximum total number of routers the
		 executor node can have on its broadcast circuits for one slot.
		 The number is an integer in the range 0-1023.'
		 "
	DEFVAL	{ routersdflt }
	::= { wfivRouteGroup 8 }

wfivRouteMaxCircuits OBJECT-TYPE
	SYNTAX	INTEGER {
		circuitsmin(1),
		circuitsdflt(16),
		circuitswfmax(1024),
		circuitsmax(65535)
	}
	ACCESS	read-write
	STATUS	mandatory
	DESCRIPTION
		"
		 'This value represents the maximum number of Routing circuits
		 that the executor node can know about. The number is decimal
		 in the range 1-65535. Wellfleet limits this to 1024'
		 "
	DEFVAL	{ circuitswfmax }
	::= { wfivRouteGroup 9 }

wfivRouteMaxCost OBJECT-TYPE
	SYNTAX	INTEGER {
		mincost(1),
		maxcost(1022)
	}
	ACCESS	read-write
	STATUS	mandatory
	DESCRIPTION
		"
		 'This value represents the maximum total path cost allowed
		 from the executor to any node within an area. The path cost is
		 the sum of the circuit costs along a path between two nodes.
		 This parameter defines the point where the executor node's
		 Routing decision algorithm declares another node
		 unreachable because the cost of the least costly path to the
		 other node is excessive. For correct operation, this parameter
		 must not be less than the maximum path cost of the network.
		 The MAXIMUM COST number is decimal in the range
		 1-1022.'
		 "
	DEFVAL	{ maxcost }
	::= { wfivRouteGroup 10 }

wfivRouteMaxHops OBJECT-TYPE
	SYNTAX	INTEGER {
		minhops(1),
		maxhops(30)
	}
	ACCESS	read-write
	STATUS	mandatory
	DESCRIPTION
		"
		 'This value represents the maximum number of routing hops
		 allowable from the executor to any other reachable node within
		 an area. (A hop is the logical distance over a circuit between
		 two adjacent nodes.) This parameter defines the point where
		 the executor node's Routing decision algorithm
		 declares another node unreachable because the length of the
		 shortest path between the two nodes is too long. For correct
		 operation, this parameter must not be less than the network
		 diameter. (The network diameter is the reachability distance
		 between the two nodes of the network having the greatest
		 reachability distance, where reachability distance is the
		 length the shortest path between a given pair of nodes.) The
		 MAXIMUM HOPS number is decimal in the range 1-30.'
		 "
	DEFVAL	{ maxhops }
	::= { wfivRouteGroup 11 }

wfivRouteMaxVisits OBJECT-TYPE
	SYNTAX	INTEGER {
		maxvisits(63)
	}
	ACCESS	read-write
	STATUS	mandatory
	DESCRIPTION
		"
		 'This value represents the maximum number of nodes a message
		 coming into the executor node can have visited. If the message
		 is not for this node and the MAXIMUM VISITS number is exceeded,
		 the message is discarded. The MAXIMUM VISITS parameter defines
		 the point where the packet lifetime control algorithm discards
		 a packet that has traversed too many nodes. For correct
		 operation, this parameter must not be less than the maximum
		 path length of the network. (The maximum path length is the
		 routing distance between the two nodes of the network having
		 the greatest routing distance, where routing distance is the
		 length of the least costly path between a given pair of nodes.)
		 The MAXIMUM VISITS number is decimal in the range MAXIMUM HOPS
		 to 63.'
		 "
	DEFVAL	{ maxvisits }
	::= { wfivRouteGroup 12 }

wfivRouteAreaMaxCost OBJECT-TYPE
	SYNTAX	INTEGER {
		amincost(1),
		amaxcost(1022)
	}
	ACCESS	read-write
	STATUS	mandatory
	DESCRIPTION
		"
		 'This value represents the maximum total path cost allowed
		 from the executor to any other level 2 routing node. The AREA
		 MAXIMUM COST number is decimal in the range
		 1-1022. This parameter is only applicable if the executor
		 node is of type AREA.'
		 "
	DEFVAL	{ amaxcost }
	::= { wfivRouteGroup 13 }

wfivRouteAreaMaxHops OBJECT-TYPE
	SYNTAX	INTEGER {
		aminhops(1),
		amaxhops(30)
	}
	ACCESS	read-write
	STATUS	mandatory
	DESCRIPTION
		"
		 'This value represents the maximum number of routing hops
		 allowable from the executor to any other level 2 routing node.
		 The AREA MAXIMUM HOPS number is decimal in the range
		 1-30.This parameter is only applicable if the executor node
		 is of type AREA.'
		 "
	DEFVAL	{ amaxhops }
	::= { wfivRouteGroup 14 }

wfivRouteMaxArea OBJECT-TYPE
	SYNTAX	INTEGER {
		minarea(1),
		maxarea(63)
	}
	ACCESS	read-write
	STATUS	mandatory
	DESCRIPTION
		"
		 'This value represents the largest area number and, therefore,
		 number of areas that can be known about by the executor node's
		 Routing. This parameter is only applicable if the executor
		 node is of type AREA. The number is an integer in the range
		 1-63.'
		 "
	DEFVAL	{ maxarea }
	::= { wfivRouteGroup 15 }

wfivRouteType OBJECT-TYPE
	SYNTAX	INTEGER {
		area(3),
		routingiv(4),
		nonroutingiv(5)
	}
	ACCESS	read-only
	STATUS	mandatory
	DESCRIPTION
		"
		 'This parameter indicates the type of the executor node. The
		 node-type is one of the following:
		 ROUTING III
		 NONROUTING III
		 ROUTING IV
		 NONROUTING IV
		 AREA
		 A routing node has full routing capability. A nonrouting node
		 contains a subset of the Routing modules. The III and
		 IV indicate the DNA phase of the node. Nonrouting nodes can
		 deliver and receive packets to and from any node, but cannot
		 route packets from other nodes through to other nodes. An
		 area node routes between areas. Refer to the Routing
		 specification for details.
		 For adjacent nodes, this is a read-only parameter that
		 indicates the type of the reachable adjacent node.
		 NOTE: The ROUTING III and NONROUTING III values are
		 incremented by one compared to the standard DECnet values in
		 order to maintain compliance with RFC 1155)'
		 "
	DEFVAL	{ area }
	::= { wfivRouteGroup 16 }

wfivCircuitTable OBJECT-TYPE
	SYNTAX	SEQUENCE OF WfivCircuitEntry
	ACCESS	not-accessible
	STATUS	mandatory
	DESCRIPTION
		"
		' Table of DECnet Circuit Configuration and Counter Records'
		"
	::= { wfDecGroup 2 }

wfivCircuitEntry OBJECT-TYPE
	SYNTAX	WfivCircuitEntry
	ACCESS	not-accessible
	STATUS	mandatory
	DESCRIPTION
		"
		 'Parameters information about all circuits currently known.
		 NOTE: depending on the type of object being querried (e.g., a
		 level 1 vs. a level 2 router or end system) some variables may
		 not be present.'
		 "
	INDEX	{ wfivCircuitID }
	::= { wfivCircuitTable 1 }

WfivCircuitEntry ::= SEQUENCE {
	wfivCircuitCreateDelete
		INTEGER,
	wfivCircuitEnableDisable
		INTEGER,
	wfivCircuitCommonState
		INTEGER,
	wfivCircuitArea
		INTEGER,
	wfivCircuitNodeid
		INTEGER,
	wfivCircuitNodeAddr
		DisplayString,
	wfivCircuitID
		INTEGER,
	wfivCircuitCommonType
		INTEGER,
	wfivCircuitExecCost
		INTEGER,
	wfivCircuitExecHelloTimer
		INTEGER,
	wfivCircuitDesigRouterNodeAddr
		DisplayString,
	wfivCircuitMaxRouters
		INTEGER,
	wfivCircuitRouterPri
		INTEGER,
	wfivCircuitCountAgedPktLoss
		Counter,
	wfivCircuitCountNodeUnrPktLoss
		Counter,
	wfivCircuitCountOutRngePktLoss
		Counter,
	wfivCircuitCountOverSzePktLoss
		Counter,
	wfivCircuitCountPacketFmtErr
		Counter,
	wfivCircuitCountPtlRteUpdtLoss
		Counter,
	wfivCircuitCountTransitPksRecd
		Counter,
	wfivCircuitCountTransitPkSent
		Counter,
	wfivCircuitCountRtHelloSent
		Counter,
	wfivCircuitCountRtHelloRcvd
		Counter,
	wfivCircuitCountHelloSent
		Counter,
	wfivCircuitCountHelloRcvd
		Counter,
	wfivCircuitCountL1UpdSent
		Counter,
	wfivCircuitCountL1UpdRcvd
		Counter,
	wfivCircuitCountAreaUpdSent
		Counter,
	wfivCircuitCountAreaUpdRcvd
		Counter,
	wfivCircuitCountDropped
		Counter,
	wfivCircuitAllEndnodesMac
		OCTET STRING,
	wfivCircuitAllRoutersMac
		OCTET STRING,
	wfivCircuitAllAreaRoutersMac
		OCTET STRING,
	wfivCircuitHelloEnableDisable
		INTEGER,
	wfivCircuitRtHelloEnableDisable
		INTEGER,
	wfivCircuitL1UpdateEnableDisable
		INTEGER
}

wfivCircuitCreateDelete OBJECT-TYPE
	SYNTAX	INTEGER {
		create(1),
		delete(2)
	}
	ACCESS	read-write
	STATUS	mandatory
	DESCRIPTION
		"
		 'This value determines whether the circuit is configured'
		 "
	DEFVAL	{ create }
	::= { wfivCircuitEntry 1 }

wfivCircuitEnableDisable OBJECT-TYPE
	SYNTAX	INTEGER {
		enable(1),
		disable(2)
	}
	ACCESS	read-write
	STATUS	mandatory
	DESCRIPTION
		"
		 'This value represents the circuit's Network Management
		 operational state. NOTE: These values are incremented by one
		 compared to the standard DECnet values in order to maintain
		 compliance with RFC 1155.'
		 "
	DEFVAL	{ enable }
	::= { wfivCircuitEntry 2 }

wfivCircuitCommonState OBJECT-TYPE
	SYNTAX	INTEGER {
		notpresent(4),
		initializing(3),
		down(2),
		up(1)
	}
	ACCESS	read-only
	STATUS	mandatory
	DESCRIPTION
		"
		 'This value represents the circuit's operational state.'
		 "
	DEFVAL	{ down }
	::= { wfivCircuitEntry 3 }

wfivCircuitArea OBJECT-TYPE
	SYNTAX	INTEGER {
		minarea(1),
		defarea(1),
		maxarea(63)
	}
	ACCESS	read-write
	STATUS	mandatory
	DESCRIPTION
		"
		 'DECnet Phase IV area number for this circuit.'
		 "
	DEFVAL	{ defarea }
	::= { wfivCircuitEntry 4 }

wfivCircuitNodeid OBJECT-TYPE
	SYNTAX	INTEGER {
		minnodeid(1),
		defnodeid(1),
		maxnodeid(1023)
	}
	ACCESS	read-write
	STATUS	mandatory
	DESCRIPTION
		"
		 'DECnet Phase IV node address for this circuit.'
		 "
	DEFVAL	{ defnodeid }
	::= { wfivCircuitEntry 5 }

wfivCircuitNodeAddr OBJECT-TYPE
	SYNTAX	DisplayString
	ACCESS	read-only
	STATUS	mandatory
	DESCRIPTION
		"
		 'The address of the adjacent node.'
		 "
	::= { wfivCircuitEntry 6 }

wfivCircuitID OBJECT-TYPE
	SYNTAX	INTEGER
	ACCESS	read-only
	STATUS	mandatory
	DESCRIPTION
		"
		 'A unique value for each known circuit.'
		 "
	::= { wfivCircuitEntry 7 }

wfivCircuitCommonType OBJECT-TYPE
	SYNTAX	INTEGER {
		sync(1),
		x25(4),
		ethernet(6),
		fddi(15),
		smds(100),
		fr(101)
	}
	ACCESS	read-only
	STATUS	mandatory
	DESCRIPTION
		"
		 'Represents the type of the circuit. For X.25 circuits, the
		 value must be set to X25. For DDCMP and Ethernet circuits it
		 is read only and is the same value as the protocol of
		 the associated line.
		 NOTE: Values 1 - 5 are incremented by one compared to the
		 standard DECnet values in order to maintain compliance with
		 RFC 1155.'
		 "
	::= { wfivCircuitEntry 8 }

wfivCircuitExecCost OBJECT-TYPE
	SYNTAX	INTEGER {
		mincost(1),
		defcost(10),
		maxcost(63)
	}
	ACCESS	read-write
	STATUS	mandatory
	DESCRIPTION
		"
		 'This value represents the Routing cost of the circuit.
		 Routing routes messages along the path between two nodes having
		 the smallest cost. The cost is a decimal integer in the range
		 1-63.'
		 "
	DEFVAL	{ defcost }
	::= { wfivCircuitEntry 9 }

wfivCircuitExecHelloTimer OBJECT-TYPE
	SYNTAX	INTEGER {
		hellomin(1),
		hellodef(15),
		hellomax(8191)
	}
	ACCESS	read-write
	STATUS	mandatory
	DESCRIPTION
		"
		 'This value determines the frequency of Routing Hello (T3) messages
		 sent to the adjacent node on the circuit. Seconds is a decimal
		 integer in the range 1-8191.'
		 "
	DEFVAL	{ hellodef }
	::= { wfivCircuitEntry 10 }

wfivCircuitDesigRouterNodeAddr OBJECT-TYPE
	SYNTAX	DisplayString
	ACCESS	read-only
	STATUS	mandatory
	DESCRIPTION
		"
		 'This value is the address of the designated router.'
		 "
	::= { wfivCircuitEntry 11 }

wfivCircuitMaxRouters OBJECT-TYPE
	SYNTAX	INTEGER {
		maxroutersdef(33),
		maxroutersmax(33)
	}
	ACCESS	read-write
	STATUS	mandatory
	DESCRIPTION
		"
		 'NR -This parameter is the maximum number of routers (including
		 the executor itself) allowed on the circuit by Routing for
		 circuits that are owned by the executor node. Number is a
		 decimal integer in the range 1-33.'
		 "
	DEFVAL	{ maxroutersdef }
	::= { wfivCircuitEntry 12 }

wfivCircuitRouterPri OBJECT-TYPE
	SYNTAX	INTEGER {
		routerpridef(64),
		routerprimax(127)
	}
	ACCESS	read-write
	STATUS	mandatory
	DESCRIPTION
		"
		 'This parameter is the priority that this router is to have in
		 the selection of designated router for the circuit on circuits
		 that are owned by the executor node. Number is a decimal
		 integer in the range 0-127. The default value is 64.'
		 "
	DEFVAL	{ routerpridef }
	::= { wfivCircuitEntry 13 }

wfivCircuitCountAgedPktLoss OBJECT-TYPE
	SYNTAX	Counter
	ACCESS	read-only
	STATUS	mandatory
	DESCRIPTION
		"
		 'Aged packet loss.'
		 "
	::= { wfivCircuitEntry 14 }

wfivCircuitCountNodeUnrPktLoss OBJECT-TYPE
	SYNTAX	Counter
	ACCESS	read-only
	STATUS	mandatory
	DESCRIPTION
		"
		 'Node unreachable packet loss.'
		 "
	::= { wfivCircuitEntry 15 }

wfivCircuitCountOutRngePktLoss OBJECT-TYPE
	SYNTAX	Counter
	ACCESS	read-only
	STATUS	mandatory
	DESCRIPTION
		"
		 'Node out-of-range packet loss.'
		 "
	::= { wfivCircuitEntry 16 }

wfivCircuitCountOverSzePktLoss OBJECT-TYPE
	SYNTAX	Counter
	ACCESS	read-only
	STATUS	mandatory
	DESCRIPTION
		"
		 'Oversized packet loss.'
		 "
	::= { wfivCircuitEntry 17 }

wfivCircuitCountPacketFmtErr OBJECT-TYPE
	SYNTAX	Counter
	ACCESS	read-only
	STATUS	mandatory
	DESCRIPTION
		"
		 'Packet format errors.'
		 "
	::= { wfivCircuitEntry 18 }

wfivCircuitCountPtlRteUpdtLoss OBJECT-TYPE
	SYNTAX	Counter
	ACCESS	read-only
	STATUS	mandatory
	DESCRIPTION
		"
		 'Partial routing update loss.'
		 "
	::= { wfivCircuitEntry 19 }

wfivCircuitCountTransitPksRecd OBJECT-TYPE
	SYNTAX	Counter
	ACCESS	read-only
	STATUS	mandatory
	DESCRIPTION
		"
		 'Transit packets Received. This value is stored internally as
		 a 32 bit value.'
		 "
	::= { wfivCircuitEntry 20 }

wfivCircuitCountTransitPkSent OBJECT-TYPE
	SYNTAX	Counter
	ACCESS	read-only
	STATUS	mandatory
	DESCRIPTION
		"
		 'Transit packets sent. This value is stored internally as
		 a 32 bit value.'
		 "
	::= { wfivCircuitEntry 21 }

wfivCircuitCountRtHelloSent OBJECT-TYPE
	SYNTAX	Counter
	ACCESS	read-only
	STATUS	mandatory
	DESCRIPTION
		"
		 ' Router Hellos Sent'
		 "
	::= { wfivCircuitEntry 22 }

wfivCircuitCountRtHelloRcvd OBJECT-TYPE
	SYNTAX	Counter
	ACCESS	read-only
	STATUS	mandatory
	DESCRIPTION
		"
		 ' Router Hellos Received'
		 "
	::= { wfivCircuitEntry 23 }

wfivCircuitCountHelloSent OBJECT-TYPE
	SYNTAX	Counter
	ACCESS	read-only
	STATUS	mandatory
	DESCRIPTION
		"
		 ' Endnode Hellos Sent'
		 "
	::= { wfivCircuitEntry 24 }

wfivCircuitCountHelloRcvd OBJECT-TYPE
	SYNTAX	Counter
	ACCESS	read-only
	STATUS	mandatory
	DESCRIPTION
		"
		 ' Endnode Hellos Received'
		 "
	::= { wfivCircuitEntry 25 }

wfivCircuitCountL1UpdSent OBJECT-TYPE
	SYNTAX	Counter
	ACCESS	read-only
	STATUS	mandatory
	DESCRIPTION
		"
		 ' Level 1 Routing Updates Sent'
		 "
	::= { wfivCircuitEntry 26 }

wfivCircuitCountL1UpdRcvd OBJECT-TYPE
	SYNTAX	Counter
	ACCESS	read-only
	STATUS	mandatory
	DESCRIPTION
		"
		 ' Level 1 Routing Updates Received'
		 "
	::= { wfivCircuitEntry 27 }

wfivCircuitCountAreaUpdSent OBJECT-TYPE
	SYNTAX	Counter
	ACCESS	read-only
	STATUS	mandatory
	DESCRIPTION
		"
		 ' Area Routing Updates Sent'
		 "
	::= { wfivCircuitEntry 28 }

wfivCircuitCountAreaUpdRcvd OBJECT-TYPE
	SYNTAX	Counter
	ACCESS	read-only
	STATUS	mandatory
	DESCRIPTION
		"
		 ' Area Routing Updates Received'
		 "
	::= { wfivCircuitEntry 29 }

wfivCircuitCountDropped OBJECT-TYPE
	SYNTAX	Counter
	ACCESS	read-only
	STATUS	mandatory
	DESCRIPTION
		"
		 ' Dropped Packets '
		 "
	::= { wfivCircuitEntry 30 }

wfivCircuitAllEndnodesMac OBJECT-TYPE
	SYNTAX	OCTET STRING
	ACCESS	read-write
	STATUS	mandatory
	DESCRIPTION
		"
		        'This parameter can be used to assign the AllEndnodes multicast
		        MAC address value for use over WAN media (e.g. Frame Relay).'
		        "
	::= { wfivCircuitEntry 31 }

wfivCircuitAllRoutersMac OBJECT-TYPE
	SYNTAX	OCTET STRING
	ACCESS	read-write
	STATUS	mandatory
	DESCRIPTION
		"
		        'This parameter can be used to assign the AllRouters multicast
		        MAC address value for use over WAN media (e.g. Frame Relay).'
		        "
	::= { wfivCircuitEntry 32 }

wfivCircuitAllAreaRoutersMac OBJECT-TYPE
	SYNTAX	OCTET STRING
	ACCESS	read-write
	STATUS	mandatory
	DESCRIPTION
		"
		        'This parameter can be used to assign the AllAreaRouters multicast
		        MAC address value for use over WAN media (e.g. Frame Relay).'
		        "
	::= { wfivCircuitEntry 33 }

wfivCircuitHelloEnableDisable OBJECT-TYPE
	SYNTAX	INTEGER {
		enable(1),
		disable(2)
	}
	ACCESS	read-write
	STATUS	mandatory
	DESCRIPTION
		"
		 ' This parameter is used to disable to sending of Hellos
		 to Endnodes. It would be used in conjunction with Static
		 Adjacencies to limit the amount of data passed over a WAN
		 link (e.g. Frame Relay).'
		 "
	DEFVAL	{ enable }
	::= { wfivCircuitEntry 34 }

wfivCircuitRtHelloEnableDisable OBJECT-TYPE
	SYNTAX	INTEGER {
		enable(1),
		disable(2)
	}
	ACCESS	read-write
	STATUS	mandatory
	DESCRIPTION
		"
		 ' This parameter is used to disable to sending of Hellos
		 to Routers. It would be used in conjunction with Static
		 Adjacencies to limit the amount of data passed over a WAN
		 link (e.g. Frame Relay).'
		 "
	DEFVAL	{ enable }
	::= { wfivCircuitEntry 35 }

wfivCircuitL1UpdateEnableDisable OBJECT-TYPE
	SYNTAX	INTEGER {
		enable(1),
		disable(2)
	}
	ACCESS	read-write
	STATUS	mandatory
	DESCRIPTION
		"
		 ' This parameter is used to disable to sending of Level 1
		 topology updates. It would be used in conjunction with Static
		 Adjacencies to limit the amount of data passed over a WAN
		 link (e.g. Frame Relay).'
		 "
	DEFVAL	{ enable }
	::= { wfivCircuitEntry 36 }

wfivLevel1RouteTable OBJECT-TYPE
	SYNTAX	SEQUENCE OF WfivLevel1RouteEntry
	ACCESS	not-accessible
	STATUS	mandatory
	DESCRIPTION
		"
		' Table of Level 1 Routing Table Entries'
		"
	::= { wfDecGroup 3 }

wfivLevel1RouteEntry OBJECT-TYPE
	SYNTAX	WfivLevel1RouteEntry
	ACCESS	not-accessible
	STATUS	mandatory
	DESCRIPTION
		"
		 'A Record in the Level 1 Routing Table'
		 "
	INDEX	{ wfivLevel1AreaId,
		wfivLevel1NodeId }
	::= { wfivLevel1RouteTable 1 }

WfivLevel1RouteEntry ::= SEQUENCE {
	wfivLevel1AreaId
		INTEGER,
	wfivLevel1NodeId
		INTEGER,
	wfivLevel1RouteNodeAddr
		DisplayString,
	wfivLevel1RouteCircuitID
		INTEGER,
	wfivLevel1RouteCost
		INTEGER,
	wfivLevel1RouteHops
		INTEGER,
	wfivLevel1RouteNextNode
		DisplayString
}

wfivLevel1AreaId OBJECT-TYPE
	SYNTAX	INTEGER
	ACCESS	read-only
	STATUS	mandatory
	DESCRIPTION
		"
		 'Area Id for this node'
		 "
	::= { wfivLevel1RouteEntry 1 }

wfivLevel1NodeId OBJECT-TYPE
	SYNTAX	INTEGER
	ACCESS	read-only
	STATUS	mandatory
	DESCRIPTION
		"
		 'Area Id for this node'
		 "
	::= { wfivLevel1RouteEntry 2 }

wfivLevel1RouteNodeAddr OBJECT-TYPE
	SYNTAX	DisplayString
	ACCESS	read-only
	STATUS	mandatory
	DESCRIPTION
		"
		 'This value is the address of the node about which routing
		 information is contained in this level 1 routing table.'
		 "
	::= { wfivLevel1RouteEntry 3 }

wfivLevel1RouteCircuitID OBJECT-TYPE
	SYNTAX	INTEGER
	ACCESS	read-only
	STATUS	mandatory
	DESCRIPTION
		"
		 'This READ_ONLY parameter identifies the circuit used to get
		 to a remote node. Circuit-id is an id-string. This parameter
		 can be used when displaying a list of nodes to indicate that
		 the display is to be restricted to those nodes adjacent on the
		 specified circuit.'
		 "
	::= { wfivLevel1RouteEntry 4 }

wfivLevel1RouteCost OBJECT-TYPE
	SYNTAX	INTEGER
	ACCESS	read-only
	STATUS	mandatory
	DESCRIPTION
		"
		 'This READ_ONLY parameter represents the total cost over the
		 current path to the destination node. Cost is a positive
		 integer value associated with using a circuit. Routing routes
		 messages (data) along the path between two nodes with the
		 smallest cost. COST is kept on a remote node basis.'
		 "
	::= { wfivLevel1RouteEntry 5 }

wfivLevel1RouteHops OBJECT-TYPE
	SYNTAX	INTEGER
	ACCESS	read-only
	STATUS	mandatory
	DESCRIPTION
		"
		 'This READ_ONLY parameter represents the number of hops over
		 to a destination node. A hop is Routing value representing
		 the logical distance between two nodes in a network. HOPS is
		 kept on a remote node basis.'
		 "
	::= { wfivLevel1RouteEntry 6 }

wfivLevel1RouteNextNode OBJECT-TYPE
	SYNTAX	DisplayString
	ACCESS	read-only
	STATUS	mandatory
	DESCRIPTION
		"
		 'This READ_ONLY value indicates the next node on the circuit
		 used to get to the node under scrutiny (next hop).'
		 "
	::= { wfivLevel1RouteEntry 7 }

wfivAreaTable OBJECT-TYPE
	SYNTAX	SEQUENCE OF WfivAreaEntry
	ACCESS	not-accessible
	STATUS	mandatory
	DESCRIPTION
		"
		'Table of Area Routing Table Entries'
		"
	::= { wfDecGroup 4 }

wfivAreaEntry OBJECT-TYPE
	SYNTAX	WfivAreaEntry
	ACCESS	not-accessible
	STATUS	mandatory
	DESCRIPTION
		"
		 'The area routing information.'
		 "
	INDEX	{ wfivAreaNum }
	::= { wfivAreaTable 1 }

WfivAreaEntry ::= SEQUENCE {
	wfivAreaNum
		INTEGER,
	wfivAreaState
		INTEGER,
	wfivAreaCost
		INTEGER,
	wfivAreaHops
		INTEGER,
	wfivAreaCircuitID
		INTEGER,
	wfivAreaNextNode
		DisplayString
}

wfivAreaNum OBJECT-TYPE
	SYNTAX	INTEGER
	ACCESS	read-only
	STATUS	mandatory
	DESCRIPTION
		"
		 'This value indicates the area number of this entry.'
		 "
	::= { wfivAreaEntry 1 }

wfivAreaState OBJECT-TYPE
	SYNTAX	INTEGER {
		reachable(4),
		unreachable(5)
	}
	ACCESS	read-only
	STATUS	mandatory
	DESCRIPTION
		"
		 'This value indicates the state of the area'
		 "
	::= { wfivAreaEntry 2 }

wfivAreaCost OBJECT-TYPE
	SYNTAX	INTEGER
	ACCESS	read-only
	STATUS	mandatory
	DESCRIPTION
		"
		 'The total cost over the current path to the
		 destination area. Cost is a value associated with
		 using a circuit. Routing routes messages (data)
		 along the path between 2 areas with the smallest
		 cost.'
		 "
	::= { wfivAreaEntry 3 }

wfivAreaHops OBJECT-TYPE
	SYNTAX	INTEGER
	ACCESS	read-only
	STATUS	mandatory
	DESCRIPTION
		"
		 'The number of hops to a destination area. A hop is
		 the routing value representing the logical distance
		 between two areas in network.'
		 "
	::= { wfivAreaEntry 4 }

wfivAreaCircuitID OBJECT-TYPE
	SYNTAX	INTEGER
	ACCESS	read-only
	STATUS	mandatory
	DESCRIPTION
		"
		 'The circuit used to get to the remote area'
		 "
	::= { wfivAreaEntry 5 }

wfivAreaNextNode OBJECT-TYPE
	SYNTAX	DisplayString
	ACCESS	read-only
	STATUS	mandatory
	DESCRIPTION
		"
		 'The next node on the circuit used to get to the
		 area under scrutiny.'
		 "
	::= { wfivAreaEntry 6 }

wfivAdjTable OBJECT-TYPE
	SYNTAX	SEQUENCE OF WfivAdjEntry
	ACCESS	not-accessible
	STATUS	mandatory
	DESCRIPTION
		"
		  Adjacency Table
		"
	::= { wfDecGroup 5 }

wfivAdjEntry OBJECT-TYPE
	SYNTAX	WfivAdjEntry
	ACCESS	not-accessible
	STATUS	mandatory
	DESCRIPTION
		"
		 ' Adjacency Table - the real index is the adjacency index'
		 "
	INDEX	{ wfivAdjIndex }
	::= { wfivAdjTable 1 }

WfivAdjEntry ::= SEQUENCE {
	wfivAdjIndex
		INTEGER,
	wfivAdjNodeAddr
		DisplayString,
	wfivAdjBlockSize
		INTEGER,
	wfivAdjListenTimer
		INTEGER,
	wfivAdjCircuitID
		INTEGER,
	wfivAdjType
		INTEGER,
	wfivAdjState
		INTEGER,
	wfivAdjPriority
		INTEGER,
	wfivAdjClass
		INTEGER
}

wfivAdjIndex OBJECT-TYPE
	SYNTAX	INTEGER
	ACCESS	read-only
	STATUS	mandatory
	DESCRIPTION
		"
		 'Index in the Adjacency Table'
		 "
	::= { wfivAdjEntry 1 }

wfivAdjNodeAddr OBJECT-TYPE
	SYNTAX	DisplayString
	ACCESS	read-only
	STATUS	mandatory
	DESCRIPTION
		"
		 'The address of the adjacent node.'
		 "
	::= { wfivAdjEntry 2 }

wfivAdjBlockSize OBJECT-TYPE
	SYNTAX	INTEGER
	ACCESS	read-only
	STATUS	mandatory
	DESCRIPTION
		"
		 'This READ_ONLY parameter is the block size that was
		 negotiated with the adjacent Routing layer during Routing
		 initialization over a particular circuit. It includes the
		 routing header, but excludes the data link header. This
		 parameter is qualified by ADJACENT NODE.'
		 "
	::= { wfivAdjEntry 3 }

wfivAdjListenTimer OBJECT-TYPE
	SYNTAX	INTEGER
	ACCESS	read-only
	STATUS	mandatory
	DESCRIPTION
		"
		 'This READ_ONLY value determines the maximum time allowed to
		 elapse before Routing receives some message (either a Hello
		 message or a user message) from the adjacent node on the
		 circuit. It was agreed during Routing initialization with the
		 adjacent Routing layer. Seconds is a decimal integer in the
		 range 1-65535. This parameter is qualified by ADJACENT NODE.'
		 "
	::= { wfivAdjEntry 4 }

wfivAdjCircuitID OBJECT-TYPE
	SYNTAX	INTEGER
	ACCESS	read-only
	STATUS	mandatory
	DESCRIPTION
		"
		 'A unique value for each known circuit.'
		 "
	::= { wfivAdjEntry 5 }

wfivAdjType OBJECT-TYPE
	SYNTAX	INTEGER
	ACCESS	read-only
	STATUS	mandatory
	DESCRIPTION
		"
		 'This parameter indicates the type of adjacency.
		 For adjacent nodes, this is a READ_ONLY parameter that
		 indicates the type of the reachable adjacent node.
		 NOTE: The ROUTING III and NONROUTING III values are
		 incremented by one compared to the standard DECnet values in
		 order to maintain compliance with RFC 1155)
		 ROUTING III (1),
		 NONROUTING III (2),
		 AREA (3),
		 ROUTING IV (4),
		 NONROUTING IV (5)'
		 "
	::= { wfivAdjEntry 6 }

wfivAdjState OBJECT-TYPE
	SYNTAX	INTEGER {
		init(1),
		up(2)
	}
	ACCESS	read-only
	STATUS	mandatory
	DESCRIPTION
		"
		 'This value indicates the state of a router adjacency.
		 On adjacencies over a circuit of type (wfivCircuitCommonType)
		 Ethernet, CI, or FDDI, with an adjacent node of type
		 (wfivAdjType) ROUTING IV or AREA, this variable is the state
		 of the Ethernet Initialization Layer for this adjacency, and
		 can have values INITIALIZING or UP. (See Section 9.1.1 of
		 DECnet Phase IV Routing Layer Functional Specification.)
		 On adjacencies over a circuit of type (wfivCircuitCommonType)
		 Ethernet, CI, or FDDI, with an adjacent node of type
		 (wfivAdjType) NONROUTING IV, this varaible will always take on
		 the value UP.
		 On adjacencies over a circuit of type (wfivCircuitCommonType)
		 DDCMP POINT, DDCMP CONTROL, DDCMP TRIBUTARY, DDCMP DMC, or
		 X.25, this variable is the state of the Routing Layer
		 Initialization Circuit State. (See section 7.3, ibid.) It can
		 have values between RUN and HALT.
		 On adjacencies over a circuit of type (wfivCircuitCommonType)
		 OTHER, this variable may be used in a manner consistent with
		 the Initialization Layer used on that circuit.
		 INITIALIZING (1), -- Ethernet one-way
		 UP (2), -- Ethernet two-way
		 RUN (3), -- The eight DDCMP/X.25 states
		 CIRCUIT REJECTED (4),
		 DATA LINK START (5),
		 ROUTING LAYER INITIALIZE (6),
		 ROUTING LAYER VERIFY (7),
		 ROUTING LAYER COMPLETE (8),
		 OFF (9),
		 HALT (10)'
		 "
	::= { wfivAdjEntry 7 }

wfivAdjPriority OBJECT-TYPE
	SYNTAX	INTEGER
	ACCESS	read-only
	STATUS	mandatory
	DESCRIPTION
		"
		 'Priority assigned by the adjacent node for this circuit.'
		 "
	::= { wfivAdjEntry 8 }

wfivAdjClass OBJECT-TYPE
	SYNTAX	INTEGER
	ACCESS	read-only
	STATUS	mandatory
	DESCRIPTION
		"
		 'Specifies whether this adjacency is Static or Dynamic'
		 "
	::= { wfivAdjEntry 9 }

wfivTrafficFilterTable OBJECT-TYPE
	SYNTAX	SEQUENCE OF WfivTrafficFilterEntry
	ACCESS	not-accessible
	STATUS	mandatory
	DESCRIPTION
		" DECNET Traffic Filters "
	::= { wfDecGroup 6 }

wfivTrafficFilterEntry OBJECT-TYPE
	SYNTAX	WfivTrafficFilterEntry
	ACCESS	not-accessible
	STATUS	mandatory
	DESCRIPTION
		" An entry in WfivTrafficFilterTable. "
	INDEX	{ wfivTrafficFilterCircuit,
		wfivTrafficFilterRuleNumber,
		wfivTrafficFilterFragment }
	::= { wfivTrafficFilterTable 1 }

WfivTrafficFilterEntry ::= SEQUENCE {
	wfivTrafficFilterCreate
		INTEGER,
	wfivTrafficFilterEnable
		INTEGER,
	wfivTrafficFilterStatus
		INTEGER,
	wfivTrafficFilterCounter
		Counter,
	wfivTrafficFilterDefinition
		Opaque,
	wfivTrafficFilterReserved
		INTEGER,
	wfivTrafficFilterCircuit
		INTEGER,
	wfivTrafficFilterRuleNumber
		INTEGER,
	wfivTrafficFilterFragment
		INTEGER
}

wfivTrafficFilterCreate OBJECT-TYPE
	SYNTAX	INTEGER {
		created(1),
		deleted(2)
	}
	ACCESS	read-write
	STATUS	mandatory
	DESCRIPTION
		" Defines the existence of the traffic filter rule:
		  created - traffic filter exists
		  delete - traffic filter does not exist and can be deleted. "
	DEFVAL	{ created }
	::= { wfivTrafficFilterEntry 1 }

wfivTrafficFilterEnable OBJECT-TYPE
	SYNTAX	INTEGER {
		enabled(1),
		disabled(2)
	}
	ACCESS	read-write
	STATUS	mandatory
	DESCRIPTION
		" Defines whether or not the traffic filter rule should be used:
		  enabled - activate the rule.
		  disabled - inactivate the rule. "
	DEFVAL	{ enabled }
	::= { wfivTrafficFilterEntry 2 }

wfivTrafficFilterStatus OBJECT-TYPE
	SYNTAX	INTEGER {
		active(1),
		error(2),
		inactive(3)
	}
	ACCESS	read-only
	STATUS	mandatory
	DESCRIPTION
		" Defines the current status of the traffic filter:
		  inactive - the rule is not in use.
		  active - the rule is being used.
		  error - the application detected an error in the rule. "
	DEFVAL	{ inactive }
	::= { wfivTrafficFilterEntry 3 }

wfivTrafficFilterCounter OBJECT-TYPE
	SYNTAX	Counter
	ACCESS	read-only
	STATUS	mandatory
	DESCRIPTION
		" The number of received packets that have
		           matched this rule. "
	::= { wfivTrafficFilterEntry 4 }

wfivTrafficFilterDefinition OBJECT-TYPE
	SYNTAX	Opaque
	ACCESS	read-write
	STATUS	mandatory
	DESCRIPTION
		" The filter rule definition. "
	::= { wfivTrafficFilterEntry 5 }

wfivTrafficFilterReserved OBJECT-TYPE
	SYNTAX	INTEGER
	ACCESS	not-accessible
	STATUS	mandatory
	DESCRIPTION
		" Reserved field. "
	::= { wfivTrafficFilterEntry 6 }

wfivTrafficFilterCircuit OBJECT-TYPE
	SYNTAX	INTEGER
	ACCESS	read-only
	STATUS	mandatory
	DESCRIPTION
		" The ID of the Circuit to which the
		    filter is applied. "
	::= { wfivTrafficFilterEntry 7 }

wfivTrafficFilterRuleNumber OBJECT-TYPE
	SYNTAX	INTEGER
	ACCESS	read-only
	STATUS	mandatory
	DESCRIPTION
		" ID for the rule. "
	::= { wfivTrafficFilterEntry 8 }

wfivTrafficFilterFragment OBJECT-TYPE
	SYNTAX	INTEGER
	ACCESS	read-only
	STATUS	mandatory
	DESCRIPTION
		" Fragment number - for large rules. "
	::= { wfivTrafficFilterEntry 9 }

wfivStaticAdjTable OBJECT-TYPE
	SYNTAX	SEQUENCE OF WfivStaticAdjEntry
	ACCESS	not-accessible
	STATUS	mandatory
	DESCRIPTION
		"
		  Static Adjacency Table
		"
	::= { wfDecGroup 7 }

wfivStaticAdjEntry OBJECT-TYPE
	SYNTAX	WfivStaticAdjEntry
	ACCESS	not-accessible
	STATUS	mandatory
	DESCRIPTION
		"
		 ' Static Adjacency Table '
		 "
	INDEX	{ wfivStaticAdjCircuitID,
		wfivStaticAdjArea,
		wfivStaticAdjNodeid }
	::= { wfivStaticAdjTable 1 }

WfivStaticAdjEntry ::= SEQUENCE {
	wfivStaticAdjCreateDelete
		INTEGER,
	wfivStaticAdjEnableDisable
		INTEGER,
	wfivStaticAdjArea
		INTEGER,
	wfivStaticAdjNodeid
		INTEGER,
	wfivStaticAdjCircuitID
		INTEGER,
	wfivStaticAdjNodeAddr
		DisplayString,
	wfivStaticAdjType
		INTEGER,
	wfivStaticAdjPriority
		INTEGER,
	wfivStaticAdjDestMACAddr
		OCTET STRING
}

wfivStaticAdjCreateDelete OBJECT-TYPE
	SYNTAX	INTEGER {
		create(1),
		delete(2)
	}
	ACCESS	read-write
	STATUS	mandatory
	DESCRIPTION
		"
		 'This value determines whether the static adjacency is configured'
		 "
	DEFVAL	{ create }
	::= { wfivStaticAdjEntry 1 }

wfivStaticAdjEnableDisable OBJECT-TYPE
	SYNTAX	INTEGER {
		enable(1),
		disable(2)
	}
	ACCESS	read-write
	STATUS	mandatory
	DESCRIPTION
		"
		 'This value determines whether the static adjacency is active '
		 "
	DEFVAL	{ enable }
	::= { wfivStaticAdjEntry 2 }

wfivStaticAdjArea OBJECT-TYPE
	SYNTAX	INTEGER
	ACCESS	read-only
	STATUS	mandatory
	DESCRIPTION
		"
		 'DECnet Phase IV area number for this static Adjacency.'
		 "
	::= { wfivStaticAdjEntry 3 }

wfivStaticAdjNodeid OBJECT-TYPE
	SYNTAX	INTEGER
	ACCESS	read-only
	STATUS	mandatory
	DESCRIPTION
		"
		 'DECnet Phase IV node address for this static adjacency.'
		 "
	::= { wfivStaticAdjEntry 4 }

wfivStaticAdjCircuitID OBJECT-TYPE
	SYNTAX	INTEGER
	ACCESS	read-only
	STATUS	mandatory
	DESCRIPTION
		"
		 'The circuit used for this static adjacency.'
		 "
	::= { wfivStaticAdjEntry 5 }

wfivStaticAdjNodeAddr OBJECT-TYPE
	SYNTAX	DisplayString
	ACCESS	read-only
	STATUS	mandatory
	DESCRIPTION
		"
		 'The address of the adjacent node in display format.'
		 "
	::= { wfivStaticAdjEntry 6 }

wfivStaticAdjType OBJECT-TYPE
	SYNTAX	INTEGER {
		area(3),
		routingiv(4),
		nonroutingiv(5)
	}
	ACCESS	read-write
	STATUS	mandatory
	DESCRIPTION
		"
		 ' Specifies whether the static adjacency is to a router or end
		 station.'
		 "
	DEFVAL	{ area }
	::= { wfivStaticAdjEntry 7 }

wfivStaticAdjPriority OBJECT-TYPE
	SYNTAX	INTEGER
	ACCESS	read-write
	STATUS	mandatory
	DESCRIPTION
		"
		 ' Specifies the priority of the static adjacency if it's a
		 router.'
		 "
	::= { wfivStaticAdjEntry 8 }

wfivStaticAdjDestMACAddr OBJECT-TYPE
	SYNTAX	OCTET STRING
	ACCESS	read-write
	STATUS	mandatory
	DESCRIPTION
		"
		 ' Specifies the destination MAC address of the Static Adjacency
		 if the circuit type is Frame Relay or SMDS.'
		 "
	::= { wfivStaticAdjEntry 9 }

wfDs1Config OBJECT-TYPE
	SYNTAX	SEQUENCE OF WfDs1ConfigEntry
	ACCESS	not-accessible
	STATUS	mandatory
	DESCRIPTION
		" The DS1 Configuration table "
	::= { wfDs1Group 1 }

wfDs1ConfigEntry OBJECT-TYPE
	SYNTAX	WfDs1ConfigEntry
	ACCESS	not-accessible
	STATUS	mandatory
	DESCRIPTION
		" per circuit DS1 configuration objects; wfDs1LineIndex
		    corresponds to Wellfleet circuit number "
	INDEX	{ wfDs1LineIndex }
	::= { wfDs1Config 1 }

WfDs1ConfigEntry ::= SEQUENCE {
	wfDs1LineIndex
		INTEGER,
	wfDs1TimeElapsed
		INTEGER,
	wfDs1ValidIntervals
		INTEGER,
	wfDs1LineType
		INTEGER,
	wfDs1ZeroCoding
		INTEGER,
	wfDs1SendCode
		INTEGER,
	wfDs1CircuitIdentifier
		DisplayString,
	wfDs1LoopbackConfig
		INTEGER,
	wfDs1LineStatus
		INTEGER
}

wfDs1LineIndex OBJECT-TYPE
	SYNTAX	INTEGER {
		minimum(1),
		maximum(1024)
	}
	ACCESS	read-only
	STATUS	mandatory
	DESCRIPTION
		" this corresponds to the Wellfleet circuit number "
	::= { wfDs1ConfigEntry 1 }

wfDs1TimeElapsed OBJECT-TYPE
	SYNTAX	INTEGER
	ACCESS	read-only
	STATUS	mandatory
	DESCRIPTION
		" 1..900 seconds within the current 15-minute interval "
	::= { wfDs1ConfigEntry 2 }

wfDs1ValidIntervals OBJECT-TYPE
	SYNTAX	INTEGER
	ACCESS	read-only
	STATUS	mandatory
	DESCRIPTION
		" 0..96 previous intervals that valid data
		    were collected. This is 96 unless the CSU
		    device was brought on line within the last 24
		    hours. "
	::= { wfDs1ConfigEntry 3 }

wfDs1LineType OBJECT-TYPE
	SYNTAX	INTEGER {
		ds1ansi-esf(4)
	}
	ACCESS	read-only
	STATUS	mandatory
	DESCRIPTION
		" the variety of DS1 implementing this circuit "
	::= { wfDs1ConfigEntry 4 }

wfDs1ZeroCoding OBJECT-TYPE
	SYNTAX	INTEGER {
		ds1b8zs(2),
		ds1zbtsi(5)
	}
	ACCESS	read-only
	STATUS	mandatory
	DESCRIPTION
		" the variety of Zero Code Suppression used on the link "
	::= { wfDs1ConfigEntry 5 }

wfDs1SendCode OBJECT-TYPE
	SYNTAX	INTEGER {
		ds1sendnocode(2)
	}
	ACCESS	read-only
	STATUS	mandatory
	DESCRIPTION
		" the type of code being sent across the DS1 circuit by
		    the CSU "
	::= { wfDs1ConfigEntry 6 }

wfDs1CircuitIdentifier OBJECT-TYPE
	SYNTAX	DisplayString
	ACCESS	read-only
	STATUS	mandatory
	DESCRIPTION
		" the transmission vendor's circuit identifier "
	::= { wfDs1ConfigEntry 7 }

wfDs1LoopbackConfig OBJECT-TYPE
	SYNTAX	INTEGER {
		ds1noloop(1),
		ds1mgrpayloadloop(2),
		ds1mgrlineloop(3),
		ds1netreqpayloadloop(4),
		ds1netreqlineloop(5),
		ds1otherloop(6)
	}
	ACCESS	read-only
	STATUS	mandatory
	DESCRIPTION
		" the loopback state of the CSU "
	::= { wfDs1ConfigEntry 8 }

wfDs1LineStatus OBJECT-TYPE
	SYNTAX	INTEGER {
		ds1noalarm(1),
		ds1farendalarm(2),
		ds1alarmindicationsignal(4),
		ds1lossofframe(8),
		ds1lossofsignal(16),
		ds1loopbackstate(32)
	}
	ACCESS	read-only
	STATUS	mandatory
	DESCRIPTION
		" the state of the DS1 line "
	::= { wfDs1ConfigEntry 9 }

wfDs1Current OBJECT-TYPE
	SYNTAX	SEQUENCE OF WfDs1CurrentEntry
	ACCESS	not-accessible
	STATUS	mandatory
	DESCRIPTION
		" The DS1 Current table "
	::= { wfDs1Group 2 }

wfDs1CurrentEntry OBJECT-TYPE
	SYNTAX	WfDs1CurrentEntry
	ACCESS	not-accessible
	STATUS	mandatory
	DESCRIPTION
		" per circuit DS1 current objects - wfDs1CurrentIndex
		    corresponds to Wellfleet circuit number "
	INDEX	{ wfDs1CurrentIndex }
	::= { wfDs1Current 1 }

WfDs1CurrentEntry ::= SEQUENCE {
	wfDs1CurrentIndex
		INTEGER,
	wfDs1CurrentESs
		Counter,
	wfDs1CurrentSESs
		Counter,
	wfDs1CurrentSEFs
		Counter,
	wfDs1CurrentUASs
		Counter,
	wfDs1CurrentBPVs
		Counter,
	wfDs1CurrentCVs
		Counter
}

wfDs1CurrentIndex OBJECT-TYPE
	SYNTAX	INTEGER {
		minimum(1),
		maximum(1024)
	}
	ACCESS	read-only
	STATUS	mandatory
	DESCRIPTION
		" this corresponds to the Wellfleet circuit number "
	::= { wfDs1CurrentEntry 1 }

wfDs1CurrentESs OBJECT-TYPE
	SYNTAX	Counter
	ACCESS	read-only
	STATUS	mandatory
	DESCRIPTION
		" the count of errored seconds in the current interval "
	::= { wfDs1CurrentEntry 2 }

wfDs1CurrentSESs OBJECT-TYPE
	SYNTAX	Counter
	ACCESS	read-only
	STATUS	mandatory
	DESCRIPTION
		" the count of severely errored seconds in the
		    current interval "
	::= { wfDs1CurrentEntry 3 }

wfDs1CurrentSEFs OBJECT-TYPE
	SYNTAX	Counter
	ACCESS	read-only
	STATUS	mandatory
	DESCRIPTION
		" the count of severely errored framing seconds in the current
		    interval "
	::= { wfDs1CurrentEntry 4 }

wfDs1CurrentUASs OBJECT-TYPE
	SYNTAX	Counter
	ACCESS	read-only
	STATUS	mandatory
	DESCRIPTION
		" the number of unavailable seconds in the current interval "
	::= { wfDs1CurrentEntry 5 }

wfDs1CurrentBPVs OBJECT-TYPE
	SYNTAX	Counter
	ACCESS	read-only
	STATUS	mandatory
	DESCRIPTION
		" the count of bipolar violations in the current interval "
	::= { wfDs1CurrentEntry 6 }

wfDs1CurrentCVs OBJECT-TYPE
	SYNTAX	Counter
	ACCESS	read-only
	STATUS	mandatory
	DESCRIPTION
		" the count of code violation error events in the
		    current interval "
	::= { wfDs1CurrentEntry 7 }

wfDs1Interval OBJECT-TYPE
	SYNTAX	SEQUENCE OF WfDs1IntervalEntry
	ACCESS	not-accessible
	STATUS	mandatory
	DESCRIPTION
		" The DS1 Interval table "
	::= { wfDs1Group 3 }

wfDs1IntervalEntry OBJECT-TYPE
	SYNTAX	WfDs1IntervalEntry
	ACCESS	not-accessible
	STATUS	mandatory
	DESCRIPTION
		" per circuit DS1 interval objects - wfDs1IntervalIndex
		    corresponds to Wellfleet circuit number, 
		    wfDs1IntervalNumber is the numbered previous
		    15-minute interval "
	INDEX	{ wfDs1IntervalIndex,
		wfDs1IntervalNumber }
	::= { wfDs1Interval 1 }

WfDs1IntervalEntry ::= SEQUENCE {
	wfDs1IntervalIndex
		INTEGER,
	wfDs1IntervalNumber
		INTEGER,
	wfDs1IntervalESs
		Gauge,
	wfDs1IntervalSESs
		Gauge,
	wfDs1IntervalSEFs
		Gauge,
	wfDs1IntervalUASs
		Gauge,
	wfDs1IntervalBPVs
		Gauge,
	wfDs1IntervalCVs
		Gauge
}

wfDs1IntervalIndex OBJECT-TYPE
	SYNTAX	INTEGER {
		minimum(1),
		maximum(1024)
	}
	ACCESS	read-only
	STATUS	mandatory
	DESCRIPTION
		" this corresponds to the Wellfleet circuit number "
	::= { wfDs1IntervalEntry 1 }

wfDs1IntervalNumber OBJECT-TYPE
	SYNTAX	INTEGER {
		minimum(1),
		maximum(96)
	}
	ACCESS	read-only
	STATUS	mandatory
	DESCRIPTION
		" 1..96 where 1 is the most recent 15-minute interval and 96 is
		    the least "
	::= { wfDs1IntervalEntry 2 }

wfDs1IntervalESs OBJECT-TYPE
	SYNTAX	Gauge
	ACCESS	read-only
	STATUS	mandatory
	DESCRIPTION
		" the count of errored seconds in the specified interval "
	::= { wfDs1IntervalEntry 3 }

wfDs1IntervalSESs OBJECT-TYPE
	SYNTAX	Gauge
	ACCESS	read-only
	STATUS	mandatory
	DESCRIPTION
		" the count of severely errored seconds in the specified
		    interval "
	::= { wfDs1IntervalEntry 4 }

wfDs1IntervalSEFs OBJECT-TYPE
	SYNTAX	Gauge
	ACCESS	read-only
	STATUS	mandatory
	DESCRIPTION
		" the count of severely errored framing seconds in the specified
		    interval "
	::= { wfDs1IntervalEntry 5 }

wfDs1IntervalUASs OBJECT-TYPE
	SYNTAX	Gauge
	ACCESS	read-only
	STATUS	mandatory
	DESCRIPTION
		" the number of unavailable seconds in the specified interval "
	::= { wfDs1IntervalEntry 6 }

wfDs1IntervalBPVs OBJECT-TYPE
	SYNTAX	Gauge
	ACCESS	read-only
	STATUS	mandatory
	DESCRIPTION
		" the count of bipolar violations in the specified interval "
	::= { wfDs1IntervalEntry 7 }

wfDs1IntervalCVs OBJECT-TYPE
	SYNTAX	Gauge
	ACCESS	read-only
	STATUS	mandatory
	DESCRIPTION
		" the count of code violation error events in the
		    specified interval "
	::= { wfDs1IntervalEntry 8 }

wfDs1Total OBJECT-TYPE
	SYNTAX	SEQUENCE OF WfDs1TotalEntry
	ACCESS	not-accessible
	STATUS	mandatory
	DESCRIPTION
		" The DS1 Total table "
	::= { wfDs1Group 4 }

wfDs1TotalEntry OBJECT-TYPE
	SYNTAX	WfDs1TotalEntry
	ACCESS	not-accessible
	STATUS	mandatory
	DESCRIPTION
		" per circuit DS1 total objects - wfDs1TotalIndex
		    corresponds to Wellfleet circuit number "
	INDEX	{ wfDs1TotalIndex }
	::= { wfDs1Total 1 }

WfDs1TotalEntry ::= SEQUENCE {
	wfDs1TotalIndex
		INTEGER,
	wfDs1TotalESs
		Gauge,
	wfDs1TotalSESs
		Gauge,
	wfDs1TotalSEFs
		Gauge,
	wfDs1TotalUASs
		Gauge,
	wfDs1TotalBPVs
		Gauge,
	wfDs1TotalCVs
		Gauge
}

wfDs1TotalIndex OBJECT-TYPE
	SYNTAX	INTEGER {
		minimum(1),
		maximum(1024)
	}
	ACCESS	read-only
	STATUS	mandatory
	DESCRIPTION
		" this corresponds to the Wellfleet circuit number "
	::= { wfDs1TotalEntry 1 }

wfDs1TotalESs OBJECT-TYPE
	SYNTAX	Gauge
	ACCESS	read-only
	STATUS	mandatory
	DESCRIPTION
		" total count of errored seconds "
	::= { wfDs1TotalEntry 2 }

wfDs1TotalSESs OBJECT-TYPE
	SYNTAX	Gauge
	ACCESS	read-only
	STATUS	mandatory
	DESCRIPTION
		" total count of severely errored seconds "
	::= { wfDs1TotalEntry 3 }

wfDs1TotalSEFs OBJECT-TYPE
	SYNTAX	Gauge
	ACCESS	read-only
	STATUS	mandatory
	DESCRIPTION
		" total count of severely errored framing seconds "
	::= { wfDs1TotalEntry 4 }

wfDs1TotalUASs OBJECT-TYPE
	SYNTAX	Gauge
	ACCESS	read-only
	STATUS	mandatory
	DESCRIPTION
		" total number of unavailable seconds "
	::= { wfDs1TotalEntry 5 }

wfDs1TotalBPVs OBJECT-TYPE
	SYNTAX	Gauge
	ACCESS	read-only
	STATUS	mandatory
	DESCRIPTION
		" total count of bipolar violations "
	::= { wfDs1TotalEntry 6 }

wfDs1TotalCVs OBJECT-TYPE
	SYNTAX	Gauge
	ACCESS	read-only
	STATUS	mandatory
	DESCRIPTION
		" total count of code violation error events "
	::= { wfDs1TotalEntry 7 }

wfDs1FeCurrent OBJECT-TYPE
	SYNTAX	SEQUENCE OF WfDs1FeCurrentEntry
	ACCESS	not-accessible
	STATUS	mandatory
	DESCRIPTION
		" The DS1 Far End Current table "
	::= { wfDs1Group 5 }

wfDs1FeCurrentEntry OBJECT-TYPE
	SYNTAX	WfDs1FeCurrentEntry
	ACCESS	not-accessible
	STATUS	mandatory
	DESCRIPTION
		" per circuit DS1 far end current objects
		    wfDs1CurrentIndex corresponds to Wellfleet circuit
		    number "
	INDEX	{ wfDs1FeCurrentIndex }
	::= { wfDs1FeCurrent 1 }

WfDs1FeCurrentEntry ::= SEQUENCE {
	wfDs1FeCurrentIndex
		INTEGER,
	wfDs1FeCurrentESs
		Counter,
	wfDs1FeCurrentSESs
		Counter,
	wfDs1FeCurrentSEFs
		Counter,
	wfDs1FeCurrentBPVs
		Counter,
	wfDs1FeCurrentCVs
		Counter
}

wfDs1FeCurrentIndex OBJECT-TYPE
	SYNTAX	INTEGER {
		minimum(1),
		maximum(1024)
	}
	ACCESS	read-only
	STATUS	mandatory
	DESCRIPTION
		" this corresponds to the Wellfleet circuit number "
	::= { wfDs1FeCurrentEntry 1 }

wfDs1FeCurrentESs OBJECT-TYPE
	SYNTAX	Counter
	ACCESS	read-only
	STATUS	mandatory
	DESCRIPTION
		" the count of errored seconds in the current interval "
	::= { wfDs1FeCurrentEntry 2 }

wfDs1FeCurrentSESs OBJECT-TYPE
	SYNTAX	Counter
	ACCESS	read-only
	STATUS	mandatory
	DESCRIPTION
		" the count of severely errored seconds in the
		    current interval "
	::= { wfDs1FeCurrentEntry 3 }

wfDs1FeCurrentSEFs OBJECT-TYPE
	SYNTAX	Counter
	ACCESS	read-only
	STATUS	mandatory
	DESCRIPTION
		" the count of severely errored framing seconds in the current
		    interval "
	::= { wfDs1FeCurrentEntry 4 }

wfDs1FeCurrentBPVs OBJECT-TYPE
	SYNTAX	Counter
	ACCESS	read-only
	STATUS	mandatory
	DESCRIPTION
		" the count of bipolar violations in the current interval "
	::= { wfDs1FeCurrentEntry 5 }

wfDs1FeCurrentCVs OBJECT-TYPE
	SYNTAX	Counter
	ACCESS	read-only
	STATUS	mandatory
	DESCRIPTION
		" the count of code violation error events in the
		    current interval "
	::= { wfDs1FeCurrentEntry 6 }

wfDs1FeInterval OBJECT-TYPE
	SYNTAX	SEQUENCE OF WfDs1FeIntervalEntry
	ACCESS	not-accessible
	STATUS	mandatory
	DESCRIPTION
		" The DS1 Far End Interval table "
	::= { wfDs1Group 6 }

wfDs1FeIntervalEntry OBJECT-TYPE
	SYNTAX	WfDs1FeIntervalEntry
	ACCESS	not-accessible
	STATUS	mandatory
	DESCRIPTION
		" per circuit DS1 far end interval objects -
		    wfDs1FeIntervalIndex corresponds to Wellfleet circuit
		    number, wfDs1FeIntervalNumber is the numbered
		    previous 15-minute interval "
	INDEX	{ wfDs1FeIntervalIndex,
		wfDs1FeIntervalNumber }
	::= { wfDs1FeInterval 1 }

WfDs1FeIntervalEntry ::= SEQUENCE {
	wfDs1FeIntervalIndex
		INTEGER,
	wfDs1FeIntervalNumber
		INTEGER,
	wfDs1FeIntervalESs
		Gauge,
	wfDs1FeIntervalSESs
		Gauge,
	wfDs1FeIntervalSEFs
		Gauge,
	wfDs1FeIntervalBPVs
		Gauge,
	wfDs1FeIntervalCVs
		Gauge
}

wfDs1FeIntervalIndex OBJECT-TYPE
	SYNTAX	INTEGER {
		minimum(1),
		maximum(1024)
	}
	ACCESS	read-only
	STATUS	mandatory
	DESCRIPTION
		" this corresponds to the Wellfleet circuit number "
	::= { wfDs1FeIntervalEntry 1 }

wfDs1FeIntervalNumber OBJECT-TYPE
	SYNTAX	INTEGER {
		minimum(1),
		maximum(96)
	}
	ACCESS	read-only
	STATUS	mandatory
	DESCRIPTION
		" 1..96 where 1 is the most recent 15-minute interval and 96 is
		    the least "
	::= { wfDs1FeIntervalEntry 2 }

wfDs1FeIntervalESs OBJECT-TYPE
	SYNTAX	Gauge
	ACCESS	read-only
	STATUS	mandatory
	DESCRIPTION
		" the count of errored seconds in the specified interval "
	::= { wfDs1FeIntervalEntry 3 }

wfDs1FeIntervalSESs OBJECT-TYPE
	SYNTAX	Gauge
	ACCESS	read-only
	STATUS	mandatory
	DESCRIPTION
		" the count of severely errored seconds in the specified
		    interval "
	::= { wfDs1FeIntervalEntry 4 }

wfDs1FeIntervalSEFs OBJECT-TYPE
	SYNTAX	Gauge
	ACCESS	read-only
	STATUS	mandatory
	DESCRIPTION
		" the count of severely errored framing seconds in the specified
		    interval "
	::= { wfDs1FeIntervalEntry 5 }

wfDs1FeIntervalBPVs OBJECT-TYPE
	SYNTAX	Gauge
	ACCESS	read-only
	STATUS	mandatory
	DESCRIPTION
		" the count of bipolar violations in the specified interval "
	::= { wfDs1FeIntervalEntry 6 }

wfDs1FeIntervalCVs OBJECT-TYPE
	SYNTAX	Gauge
	ACCESS	read-only
	STATUS	mandatory
	DESCRIPTION
		" the count of code violation error events in the
		    specified interval "
	::= { wfDs1FeIntervalEntry 7 }

wfDs1FeTotal OBJECT-TYPE
	SYNTAX	SEQUENCE OF WfDs1FeTotalEntry
	ACCESS	not-accessible
	STATUS	mandatory
	DESCRIPTION
		" The DS1 Far End Total table "
	::= { wfDs1Group 7 }

wfDs1FeTotalEntry OBJECT-TYPE
	SYNTAX	WfDs1FeTotalEntry
	ACCESS	not-accessible
	STATUS	mandatory
	DESCRIPTION
		" per circuit DS1 far end total objects - wfDs1FeTotalIndex
		    corresponds to Wellfleet circuit number "
	INDEX	{ wfDs1FeTotalIndex }
	::= { wfDs1FeTotal 1 }

WfDs1FeTotalEntry ::= SEQUENCE {
	wfDs1FeTotalIndex
		INTEGER,
	wfDs1FeTotalESs
		Gauge,
	wfDs1FeTotalSESs
		Gauge,
	wfDs1FeTotalSEFs
		Gauge,
	wfDs1FeTotalBPVs
		Gauge,
	wfDs1FeTotalCVs
		Gauge
}

wfDs1FeTotalIndex OBJECT-TYPE
	SYNTAX	INTEGER {
		minimum(1),
		maximum(1024)
	}
	ACCESS	read-only
	STATUS	mandatory
	DESCRIPTION
		" this corresponds to the Wellfleet circuit number "
	::= { wfDs1FeTotalEntry 1 }

wfDs1FeTotalESs OBJECT-TYPE
	SYNTAX	Gauge
	ACCESS	read-only
	STATUS	mandatory
	DESCRIPTION
		" total count of errored seconds "
	::= { wfDs1FeTotalEntry 2 }

wfDs1FeTotalSESs OBJECT-TYPE
	SYNTAX	Gauge
	ACCESS	read-only
	STATUS	mandatory
	DESCRIPTION
		" total count of severely errored seconds "
	::= { wfDs1FeTotalEntry 3 }

wfDs1FeTotalSEFs OBJECT-TYPE
	SYNTAX	Gauge
	ACCESS	read-only
	STATUS	mandatory
	DESCRIPTION
		" total count of severely errored framing seconds "
	::= { wfDs1FeTotalEntry 4 }

wfDs1FeTotalBPVs OBJECT-TYPE
	SYNTAX	Gauge
	ACCESS	read-only
	STATUS	mandatory
	DESCRIPTION
		" total count of bipolar violations "
	::= { wfDs1FeTotalEntry 5 }

wfDs1FeTotalCVs OBJECT-TYPE
	SYNTAX	Gauge
	ACCESS	read-only
	STATUS	mandatory
	DESCRIPTION
		" total count of code violation error events "
	::= { wfDs1FeTotalEntry 6 }

wfDs3Config OBJECT-TYPE
	SYNTAX	SEQUENCE OF WfDs3ConfigEntry
	ACCESS	not-accessible
	STATUS	mandatory
	DESCRIPTION
		" The DS3 Configuration table "
	::= { wfDs3Group 1 }

wfDs3ConfigEntry OBJECT-TYPE
	SYNTAX	WfDs3ConfigEntry
	ACCESS	not-accessible
	STATUS	mandatory
	DESCRIPTION
		" per circuit DS3 configuration objects; wfDs3LineIndex
		    corresponds to Wellfleet circuit number "
	INDEX	{ wfDs3LineIndex }
	::= { wfDs3Config 1 }

WfDs3ConfigEntry ::= SEQUENCE {
	wfDs3LineIndex
		INTEGER,
	wfDs3TimeElapsed
		INTEGER,
	wfDs3ValidIntervals
		INTEGER,
	wfDs3LineType
		INTEGER,
	wfDs3ZeroCoding
		INTEGER,
	wfDs3SendCode
		INTEGER,
	wfDs3CircuitIdentifier
		DisplayString,
	wfDs3LoopbackConfig
		INTEGER,
	wfDs3LineStatus
		INTEGER
}

wfDs3LineIndex OBJECT-TYPE
	SYNTAX	INTEGER {
		minimum(1),
		maximum(1024)
	}
	ACCESS	read-only
	STATUS	mandatory
	DESCRIPTION
		" this corresponds to the Wellfleet circuit number "
	::= { wfDs3ConfigEntry 1 }

wfDs3TimeElapsed OBJECT-TYPE
	SYNTAX	INTEGER
	ACCESS	read-only
	STATUS	mandatory
	DESCRIPTION
		" 1..900 seconds within the current 15-minute interval "
	::= { wfDs3ConfigEntry 2 }

wfDs3ValidIntervals OBJECT-TYPE
	SYNTAX	INTEGER
	ACCESS	read-only
	STATUS	mandatory
	DESCRIPTION
		" 0..96 previous intervals that valid data
		    were collected. This is 96 unless the CSU
		    device was brought on line within the last 24
		    hours. "
	::= { wfDs3ConfigEntry 3 }

wfDs3LineType OBJECT-TYPE
	SYNTAX	INTEGER {
		other(1),
		ds3cbitparity(4),
		ds3clearchannel(5)
	}
	ACCESS	read-only
	STATUS	mandatory
	DESCRIPTION
		" the variety of DS3 implementing this circuit "
	::= { wfDs3ConfigEntry 4 }

wfDs3ZeroCoding OBJECT-TYPE
	SYNTAX	INTEGER {
		ds3b3zs(2)
	}
	ACCESS	read-only
	STATUS	mandatory
	DESCRIPTION
		" the variety of Zero Code Suppression used on the link "
	::= { wfDs3ConfigEntry 5 }

wfDs3SendCode OBJECT-TYPE
	SYNTAX	INTEGER {
		ds3sendnocode(2)
	}
	ACCESS	read-only
	STATUS	mandatory
	DESCRIPTION
		" the type of code being sent across the DS3 circuit by
		    the CSU "
	::= { wfDs3ConfigEntry 6 }

wfDs3CircuitIdentifier OBJECT-TYPE
	SYNTAX	DisplayString
	ACCESS	read-only
	STATUS	mandatory
	DESCRIPTION
		" the transmission vendor's circuit identifier "
	::= { wfDs3ConfigEntry 7 }

wfDs3LoopbackConfig OBJECT-TYPE
	SYNTAX	INTEGER {
		ds3noloop(1),
		ds3mgrpayloadloop(2),
		ds3mgrlineloop(3),
		ds3netreqpayloadloop(4),
		ds3netreqlineloop(5),
		ds3otherloop(6)
	}
	ACCESS	read-only
	STATUS	mandatory
	DESCRIPTION
		" the loopback state of the CSU "
	::= { wfDs3ConfigEntry 8 }

wfDs3LineStatus OBJECT-TYPE
	SYNTAX	INTEGER {
		ds3noalarm(1),
		ds3farendalarm(2),
		ds3alarmindicationsignal(4),
		ds3lossofframe(8),
		ds3lossofsignal(16),
		ds3loopbackstate(32)
	}
	ACCESS	read-only
	STATUS	mandatory
	DESCRIPTION
		" the state of the DS3 line "
	::= { wfDs3ConfigEntry 9 }

wfDs3Current OBJECT-TYPE
	SYNTAX	SEQUENCE OF WfDs3CurrentEntry
	ACCESS	not-accessible
	STATUS	mandatory
	DESCRIPTION
		" The DS3 Current table "
	::= { wfDs3Group 2 }

wfDs3CurrentEntry OBJECT-TYPE
	SYNTAX	WfDs3CurrentEntry
	ACCESS	not-accessible
	STATUS	mandatory
	DESCRIPTION
		" per circuit DS3 current objects - wfDs3CurrentIndex
		    corresponds to Wellfleet circuit number "
	INDEX	{ wfDs3CurrentIndex }
	::= { wfDs3Current 1 }

WfDs3CurrentEntry ::= SEQUENCE {
	wfDs3CurrentIndex
		INTEGER,
	wfDs3CurrentESs
		Counter,
	wfDs3CurrentSESs
		Counter,
	wfDs3CurrentSEFs
		Counter,
	wfDs3CurrentUASs
		Counter,
	wfDs3CurrentBPVs
		Counter,
	wfDs3CurrentCVs
		Counter
}

wfDs3CurrentIndex OBJECT-TYPE
	SYNTAX	INTEGER {
		minimum(1),
		maximum(1024)
	}
	ACCESS	read-only
	STATUS	mandatory
	DESCRIPTION
		" this corresponds to the Wellfleet circuit number "
	::= { wfDs3CurrentEntry 1 }

wfDs3CurrentESs OBJECT-TYPE
	SYNTAX	Counter
	ACCESS	read-only
	STATUS	mandatory
	DESCRIPTION
		" the count of errored seconds in the current interval "
	::= { wfDs3CurrentEntry 2 }

wfDs3CurrentSESs OBJECT-TYPE
	SYNTAX	Counter
	ACCESS	read-only
	STATUS	mandatory
	DESCRIPTION
		" the count of severely errored seconds in the
		    current interval "
	::= { wfDs3CurrentEntry 3 }

wfDs3CurrentSEFs OBJECT-TYPE
	SYNTAX	Counter
	ACCESS	read-only
	STATUS	mandatory
	DESCRIPTION
		" the count of severely errored framing seconds in the current
		    interval "
	::= { wfDs3CurrentEntry 4 }

wfDs3CurrentUASs OBJECT-TYPE
	SYNTAX	Counter
	ACCESS	read-only
	STATUS	mandatory
	DESCRIPTION
		" the number of unavailable seconds in the current interval "
	::= { wfDs3CurrentEntry 5 }

wfDs3CurrentBPVs OBJECT-TYPE
	SYNTAX	Counter
	ACCESS	read-only
	STATUS	mandatory
	DESCRIPTION
		" the count of bipolar violations in the current interval "
	::= { wfDs3CurrentEntry 6 }

wfDs3CurrentCVs OBJECT-TYPE
	SYNTAX	Counter
	ACCESS	read-only
	STATUS	mandatory
	DESCRIPTION
		" the count of code violation error events in the
		    current interval "
	::= { wfDs3CurrentEntry 7 }

wfDs3Interval OBJECT-TYPE
	SYNTAX	SEQUENCE OF WfDs3IntervalEntry
	ACCESS	not-accessible
	STATUS	mandatory
	DESCRIPTION
		" The DS3 Interval table "
	::= { wfDs3Group 3 }

wfDs3IntervalEntry OBJECT-TYPE
	SYNTAX	WfDs3IntervalEntry
	ACCESS	not-accessible
	STATUS	mandatory
	DESCRIPTION
		" per circuit DS3 interval objects - wfDs3IntervalIndex
		    corresponds to Wellfleet circuit number, 
		    wfDs3IntervalNumber is the numbered previous
		    15-minute interval "
	INDEX	{ wfDs3IntervalIndex,
		wfDs3IntervalNumber }
	::= { wfDs3Interval 1 }

WfDs3IntervalEntry ::= SEQUENCE {
	wfDs3IntervalIndex
		INTEGER,
	wfDs3IntervalNumber
		INTEGER,
	wfDs3IntervalESs
		Gauge,
	wfDs3IntervalSESs
		Gauge,
	wfDs3IntervalSEFs
		Gauge,
	wfDs3IntervalUASs
		Gauge,
	wfDs3IntervalBPVs
		Gauge,
	wfDs3IntervalCVs
		Gauge
}

wfDs3IntervalIndex OBJECT-TYPE
	SYNTAX	INTEGER {
		minimum(1),
		maximum(1024)
	}
	ACCESS	read-only
	STATUS	mandatory
	DESCRIPTION
		" this corresponds to the Wellfleet circuit number "
	::= { wfDs3IntervalEntry 1 }

wfDs3IntervalNumber OBJECT-TYPE
	SYNTAX	INTEGER {
		minimum(1),
		maximum(96)
	}
	ACCESS	read-only
	STATUS	mandatory
	DESCRIPTION
		" 1..96 where 1 is the most recent 15-minute interval and 96 is
		    the least "
	::= { wfDs3IntervalEntry 2 }

wfDs3IntervalESs OBJECT-TYPE
	SYNTAX	Gauge
	ACCESS	read-only
	STATUS	mandatory
	DESCRIPTION
		" the count of errored seconds in the specified interval "
	::= { wfDs3IntervalEntry 3 }

wfDs3IntervalSESs OBJECT-TYPE
	SYNTAX	Gauge
	ACCESS	read-only
	STATUS	mandatory
	DESCRIPTION
		" the count of severely errored seconds in the specified
		    interval "
	::= { wfDs3IntervalEntry 4 }

wfDs3IntervalSEFs OBJECT-TYPE
	SYNTAX	Gauge
	ACCESS	read-only
	STATUS	mandatory
	DESCRIPTION
		" the count of severely errored framing seconds in the specified
		    interval "
	::= { wfDs3IntervalEntry 5 }

wfDs3IntervalUASs OBJECT-TYPE
	SYNTAX	Gauge
	ACCESS	read-only
	STATUS	mandatory
	DESCRIPTION
		" the number of unavailable seconds in the specified interval "
	::= { wfDs3IntervalEntry 6 }

wfDs3IntervalBPVs OBJECT-TYPE
	SYNTAX	Gauge
	ACCESS	read-only
	STATUS	mandatory
	DESCRIPTION
		" the count of bipolar violations in the specified interval "
	::= { wfDs3IntervalEntry 7 }

wfDs3IntervalCVs OBJECT-TYPE
	SYNTAX	Gauge
	ACCESS	read-only
	STATUS	mandatory
	DESCRIPTION
		" the count of code violation error events in the
		    specified interval "
	::= { wfDs3IntervalEntry 8 }

wfDs3Total OBJECT-TYPE
	SYNTAX	SEQUENCE OF WfDs3TotalEntry
	ACCESS	not-accessible
	STATUS	mandatory
	DESCRIPTION
		" The DS3 Total table "
	::= { wfDs3Group 4 }

wfDs3TotalEntry OBJECT-TYPE
	SYNTAX	WfDs3TotalEntry
	ACCESS	not-accessible
	STATUS	mandatory
	DESCRIPTION
		" per circuit DS3 total objects - wfDs3TotalIndex
		    corresponds to Wellfleet circuit number "
	INDEX	{ wfDs3TotalIndex }
	::= { wfDs3Total 1 }

WfDs3TotalEntry ::= SEQUENCE {
	wfDs3TotalIndex
		INTEGER,
	wfDs3TotalESs
		Gauge,
	wfDs3TotalSESs
		Gauge,
	wfDs3TotalSEFs
		Gauge,
	wfDs3TotalUASs
		Gauge,
	wfDs3TotalBPVs
		Gauge,
	wfDs3TotalCVs
		Gauge
}

wfDs3TotalIndex OBJECT-TYPE
	SYNTAX	INTEGER {
		minimum(1),
		maximum(1024)
	}
	ACCESS	read-only
	STATUS	mandatory
	DESCRIPTION
		" this corresponds to the Wellfleet circuit number "
	::= { wfDs3TotalEntry 1 }

wfDs3TotalESs OBJECT-TYPE
	SYNTAX	Gauge
	ACCESS	read-only
	STATUS	mandatory
	DESCRIPTION
		" total count of errored seconds "
	::= { wfDs3TotalEntry 2 }

wfDs3TotalSESs OBJECT-TYPE
	SYNTAX	Gauge
	ACCESS	read-only
	STATUS	mandatory
	DESCRIPTION
		" total count of severely errored seconds "
	::= { wfDs3TotalEntry 3 }

wfDs3TotalSEFs OBJECT-TYPE
	SYNTAX	Gauge
	ACCESS	read-only
	STATUS	mandatory
	DESCRIPTION
		" total count of severely errored framing seconds "
	::= { wfDs3TotalEntry 4 }

wfDs3TotalUASs OBJECT-TYPE
	SYNTAX	Gauge
	ACCESS	read-only
	STATUS	mandatory
	DESCRIPTION
		" total number of unavailable seconds "
	::= { wfDs3TotalEntry 5 }

wfDs3TotalBPVs OBJECT-TYPE
	SYNTAX	Gauge
	ACCESS	read-only
	STATUS	mandatory
	DESCRIPTION
		" total count of bipolar violations "
	::= { wfDs3TotalEntry 6 }

wfDs3TotalCVs OBJECT-TYPE
	SYNTAX	Gauge
	ACCESS	read-only
	STATUS	mandatory
	DESCRIPTION
		" total count of code violation error events "
	::= { wfDs3TotalEntry 7 }

wfDs3FeConfig OBJECT-TYPE
	SYNTAX	SEQUENCE OF WfDs3FeConfigEntry
	ACCESS	not-accessible
	STATUS	mandatory
	DESCRIPTION
		" The DS3 Far End Configuration table "
	::= { wfDs3Group 5 }

wfDs3FeConfigEntry OBJECT-TYPE
	SYNTAX	WfDs3FeConfigEntry
	ACCESS	not-accessible
	STATUS	mandatory
	DESCRIPTION
		" per circuit DS3 far end config objects -
		    wfDs3FeIntervalIndex corresponds to Wellfleet circuit
		    number "
	INDEX	{ wfDs3FeConfigIndex }
	::= { wfDs3FeConfig 1 }

WfDs3FeConfigEntry ::= SEQUENCE {
	wfDs3FeConfigIndex
		INTEGER,
	wfDs3FarEndEquipCode
		DisplayString,
	wfDs3FarEndLocationIDCode
		DisplayString,
	wfDs3FarEndFrameIDCode
		DisplayString,
	wfDs3FarEndUnitCode
		DisplayString,
	wfDs3FarEndFacilityIDCode
		DisplayString
}

wfDs3FeConfigIndex OBJECT-TYPE
	SYNTAX	INTEGER {
		minimum(1),
		maximum(1024)
	}
	ACCESS	read-only
	STATUS	mandatory
	DESCRIPTION
		" this corresponds to the Wellfleet circuit number "
	::= { wfDs3FeConfigEntry 1 }

wfDs3FarEndEquipCode OBJECT-TYPE
	SYNTAX	DisplayString
	ACCESS	read-write
	STATUS	mandatory
	DESCRIPTION
		" equipment description code - C-bit parity only "
	::= { wfDs3FeConfigEntry 2 }

wfDs3FarEndLocationIDCode OBJECT-TYPE
	SYNTAX	DisplayString
	ACCESS	read-write
	STATUS	mandatory
	DESCRIPTION
		" equipment location code - C-bit parity only "
	::= { wfDs3FeConfigEntry 3 }

wfDs3FarEndFrameIDCode OBJECT-TYPE
	SYNTAX	DisplayString
	ACCESS	read-write
	STATUS	mandatory
	DESCRIPTION
		" code for the equipment location within a building "
	::= { wfDs3FeConfigEntry 4 }

wfDs3FarEndUnitCode OBJECT-TYPE
	SYNTAX	DisplayString
	ACCESS	read-write
	STATUS	mandatory
	DESCRIPTION
		" code for the equipment location within a bay "
	::= { wfDs3FeConfigEntry 5 }

wfDs3FarEndFacilityIDCode OBJECT-TYPE
	SYNTAX	DisplayString
	ACCESS	read-write
	STATUS	mandatory
	DESCRIPTION
		" path identification code "
	::= { wfDs3FeConfigEntry 6 }

wfDs3FeCurrent OBJECT-TYPE
	SYNTAX	SEQUENCE OF WfDs3FeCurrentEntry
	ACCESS	not-accessible
	STATUS	mandatory
	DESCRIPTION
		" The DS3 Far End Current table "
	::= { wfDs3Group 6 }

wfDs3FeCurrentEntry OBJECT-TYPE
	SYNTAX	WfDs3FeCurrentEntry
	ACCESS	not-accessible
	STATUS	mandatory
	DESCRIPTION
		" per circuit DS3 far end current objects
		    wfDs3FeCurrentIndex corresponds to Wellfleet circuit
		    number "
	INDEX	{ wfDs3FeCurrentIndex }
	::= { wfDs3FeCurrent 1 }

WfDs3FeCurrentEntry ::= SEQUENCE {
	wfDs3FeCurrentIndex
		INTEGER,
	wfDs3FeCurrentESs
		Counter,
	wfDs3FeCurrentSESs
		Counter,
	wfDs3FeCurrentCVs
		Counter
}

wfDs3FeCurrentIndex OBJECT-TYPE
	SYNTAX	INTEGER {
		minimum(1),
		maximum(1024)
	}
	ACCESS	read-only
	STATUS	mandatory
	DESCRIPTION
		" this corresponds to the Wellfleet circuit number "
	::= { wfDs3FeCurrentEntry 1 }

wfDs3FeCurrentESs OBJECT-TYPE
	SYNTAX	Counter
	ACCESS	read-only
	STATUS	mandatory
	DESCRIPTION
		" the count of errored seconds in the current interval "
	::= { wfDs3FeCurrentEntry 2 }

wfDs3FeCurrentSESs OBJECT-TYPE
	SYNTAX	Counter
	ACCESS	read-only
	STATUS	mandatory
	DESCRIPTION
		" the count of severely errored seconds in the
		    current interval "
	::= { wfDs3FeCurrentEntry 3 }

wfDs3FeCurrentCVs OBJECT-TYPE
	SYNTAX	Counter
	ACCESS	read-only
	STATUS	mandatory
	DESCRIPTION
		" the count of code violation error events in the
		    current interval "
	::= { wfDs3FeCurrentEntry 4 }

wfDs3FeInterval OBJECT-TYPE
	SYNTAX	SEQUENCE OF WfDs3FeIntervalEntry
	ACCESS	not-accessible
	STATUS	mandatory
	DESCRIPTION
		" The DS3 Far End Interval table "
	::= { wfDs3Group 7 }

wfDs3FeIntervalEntry OBJECT-TYPE
	SYNTAX	WfDs3FeIntervalEntry
	ACCESS	not-accessible
	STATUS	mandatory
	DESCRIPTION
		" per circuit DS3 far end interval objects -
		    wfDs3FeIntervalIndex corresponds to Wellfleet circuit
		    number, wfDs3FeIntervalNumber is the numbered previous
		    15-minute interval "
	INDEX	{ wfDs3FeIntervalIndex,
		wfDs3FeIntervalNumber }
	::= { wfDs3FeInterval 1 }

WfDs3FeIntervalEntry ::= SEQUENCE {
	wfDs3FeIntervalIndex
		INTEGER,
	wfDs3FeIntervalNumber
		INTEGER,
	wfDs3FeIntervalESs
		Gauge,
	wfDs3FeIntervalSESs
		Gauge,
	wfDs3FeIntervalCVs
		Gauge
}

wfDs3FeIntervalIndex OBJECT-TYPE
	SYNTAX	INTEGER {
		minimum(1),
		maximum(1024)
	}
	ACCESS	read-only
	STATUS	mandatory
	DESCRIPTION
		" this corresponds to the Wellfleet circuit number "
	::= { wfDs3FeIntervalEntry 1 }

wfDs3FeIntervalNumber OBJECT-TYPE
	SYNTAX	INTEGER {
		minimum(1),
		maximum(96)
	}
	ACCESS	read-only
	STATUS	mandatory
	DESCRIPTION
		" 1..96 where 1 is the most recent 15-minute interval and 96 is
		    the least "
	::= { wfDs3FeIntervalEntry 2 }

wfDs3FeIntervalESs OBJECT-TYPE
	SYNTAX	Gauge
	ACCESS	read-only
	STATUS	mandatory
	DESCRIPTION
		" the count of errored seconds in the specified interval "
	::= { wfDs3FeIntervalEntry 3 }

wfDs3FeIntervalSESs OBJECT-TYPE
	SYNTAX	Gauge
	ACCESS	read-only
	STATUS	mandatory
	DESCRIPTION
		" the count of severely errored seconds in the
		    specified interval "
	::= { wfDs3FeIntervalEntry 4 }

wfDs3FeIntervalCVs OBJECT-TYPE
	SYNTAX	Gauge
	ACCESS	read-only
	STATUS	mandatory
	DESCRIPTION
		" the count of code violation error events in the
		    specified interval "
	::= { wfDs3FeIntervalEntry 5 }

wfDs3FeTotal OBJECT-TYPE
	SYNTAX	SEQUENCE OF WfDs3FeTotalEntry
	ACCESS	not-accessible
	STATUS	mandatory
	DESCRIPTION
		" The DS3 Far End Total table "
	::= { wfDs3Group 8 }

wfDs3FeTotalEntry OBJECT-TYPE
	SYNTAX	WfDs3FeTotalEntry
	ACCESS	not-accessible
	STATUS	mandatory
	DESCRIPTION
		" per circuit far end DS3 total objects - wfDs3FeTotalIndex
		    corresponds to Wellfleet circuit number "
	INDEX	{ wfDs3FeTotalIndex }
	::= { wfDs3FeTotal 1 }

WfDs3FeTotalEntry ::= SEQUENCE {
	wfDs3FeTotalIndex
		INTEGER,
	wfDs3FeTotalESs
		Gauge,
	wfDs3FeTotalSESs
		Gauge,
	wfDs3FeTotalCVs
		Gauge
}

wfDs3FeTotalIndex OBJECT-TYPE
	SYNTAX	INTEGER {
		minimum(1),
		maximum(1024)
	}
	ACCESS	read-only
	STATUS	mandatory
	DESCRIPTION
		" this corresponds to the Wellfleet circuit number "
	::= { wfDs3FeTotalEntry 1 }

wfDs3FeTotalESs OBJECT-TYPE
	SYNTAX	Gauge
	ACCESS	read-only
	STATUS	mandatory
	DESCRIPTION
		" total count of errored seconds "
	::= { wfDs3FeTotalEntry 2 }

wfDs3FeTotalSESs OBJECT-TYPE
	SYNTAX	Gauge
	ACCESS	read-only
	STATUS	mandatory
	DESCRIPTION
		" total count of severely errored seconds "
	::= { wfDs3FeTotalEntry 3 }

wfDs3FeTotalCVs OBJECT-TYPE
	SYNTAX	Gauge
	ACCESS	read-only
	STATUS	mandatory
	DESCRIPTION
		" total count of code violation error events "
	::= { wfDs3FeTotalEntry 4 }

wfE1Table OBJECT-TYPE
	SYNTAX	SEQUENCE OF WfE1Entry
	ACCESS	not-accessible
	STATUS	mandatory
	DESCRIPTION
		"
		   E1 line record
		 "
	::= { wfLine 11 }

wfE1Entry OBJECT-TYPE
	SYNTAX	WfE1Entry
	ACCESS	not-accessible
	STATUS	mandatory
	DESCRIPTION
		" An entry in the E1 table "
	INDEX	{ wfE1Slot,
		wfE1Connector }
	::= { wfE1Table 1 }

WfE1Entry ::= SEQUENCE {
	wfE1Delete
		INTEGER,
	wfE1Disable
		INTEGER,
	wfE1State
		INTEGER,
	wfE1Slot
		INTEGER,
	wfE1Connector
		INTEGER,
	wfE1Madr
		OCTET STRING,
	wfE1HDB3Support
		INTEGER,
	wfE1ClockMode
		INTEGER,
	wfE1MiniDacs
		DisplayString,
	wfE1BipolarVios
		Counter,
	wfE1FrameErrs
		Counter,
	wfE1RcvRemAlms
		Counter,
	wfE1RcvMfmAlms
		Counter,
	wfE1MfsErrs
		Counter,
	wfE1SyncLoss
		Counter,
	wfE1RcvSig1s
		Counter,
	wfE1RcvUnfrm1s
		Counter
}

wfE1Delete OBJECT-TYPE
	SYNTAX	INTEGER {
		created(1),
		deleted(2)
	}
	ACCESS	read-write
	STATUS	mandatory
	DESCRIPTION
		" create/delete parameter, dflt = created "
	DEFVAL	{ created }
	::= { wfE1Entry 1 }

wfE1Disable OBJECT-TYPE
	SYNTAX	INTEGER {
		enabled(1),
		disabled(2)
	}
	ACCESS	read-write
	STATUS	mandatory
	DESCRIPTION
		" enable/disable parameter, dflt = enabled "
	DEFVAL	{ enabled }
	::= { wfE1Entry 2 }

wfE1State OBJECT-TYPE
	SYNTAX	INTEGER {
		up(1),
		init(3),
		notpresent(4)
	}
	ACCESS	read-only
	STATUS	mandatory
	DESCRIPTION
		" line driver state variable, Not Present, Init, Up "
	DEFVAL	{ notpresent }
	::= { wfE1Entry 3 }

wfE1Slot OBJECT-TYPE
	SYNTAX	INTEGER {
		minimum(1),
		maximum(14)
	}
	ACCESS	read-only
	STATUS	mandatory
	DESCRIPTION
		" instance ID Slot, filled in by driver "
	::= { wfE1Entry 4 }

wfE1Connector OBJECT-TYPE
	SYNTAX	INTEGER {
		one(1),
		two(2)
	}
	ACCESS	read-only
	STATUS	mandatory
	DESCRIPTION
		" instance ID Connector, filled in by driver "
	::= { wfE1Entry 5 }

wfE1Madr OBJECT-TYPE
	SYNTAX	OCTET STRING
	ACCESS	read-only
	STATUS	mandatory
	DESCRIPTION
		" Line mac address, filled in by driver "
	::= { wfE1Entry 6 }

wfE1HDB3Support OBJECT-TYPE
	SYNTAX	INTEGER {
		enabled(1),
		disabled(2)
	}
	ACCESS	read-write
	STATUS	mandatory
	DESCRIPTION
		" HDB3 Support - Enables or disables high density bipolar coding "
	DEFVAL	{ disabled }
	::= { wfE1Entry 7 }

wfE1ClockMode OBJECT-TYPE
	SYNTAX	INTEGER {
		internal(1),
		slave(2),
		manual(4),
		default(1)
	}
	ACCESS	read-write
	STATUS	mandatory
	DESCRIPTION
		" Clock Mode - Specifies the source of the E1 transmit clock "
	DEFVAL	{ default }
	::= { wfE1Entry 8 }

wfE1MiniDacs OBJECT-TYPE
	SYNTAX	DisplayString
	ACCESS	read-write
	STATUS	mandatory
	DESCRIPTION
		" MiniDacs Configuration - assigns each E1 channel to a specific
		   function                                                       "
	::= { wfE1Entry 9 }

wfE1BipolarVios OBJECT-TYPE
	SYNTAX	Counter
	ACCESS	read-only
	STATUS	mandatory
	DESCRIPTION
		" Number of Bipolar Violations "
	::= { wfE1Entry 10 }

wfE1FrameErrs OBJECT-TYPE
	SYNTAX	Counter
	ACCESS	read-only
	STATUS	mandatory
	DESCRIPTION
		" Number of Frame errors "
	::= { wfE1Entry 11 }

wfE1RcvRemAlms OBJECT-TYPE
	SYNTAX	Counter
	ACCESS	read-only
	STATUS	mandatory
	DESCRIPTION
		" Number of remote alarms received "
	::= { wfE1Entry 12 }

wfE1RcvMfmAlms OBJECT-TYPE
	SYNTAX	Counter
	ACCESS	read-only
	STATUS	mandatory
	DESCRIPTION
		" Number of Multiframe Alarms Received "
	::= { wfE1Entry 13 }

wfE1MfsErrs OBJECT-TYPE
	SYNTAX	Counter
	ACCESS	read-only
	STATUS	mandatory
	DESCRIPTION
		" Number of instances of CAS Multiframe resync criteria met "
	::= { wfE1Entry 14 }

wfE1SyncLoss OBJECT-TYPE
	SYNTAX	Counter
	ACCESS	read-only
	STATUS	mandatory
	DESCRIPTION
		" Number of instances of sync loss  "
	::= { wfE1Entry 15 }

wfE1RcvSig1s OBJECT-TYPE
	SYNTAX	Counter
	ACCESS	read-only
	STATUS	mandatory
	DESCRIPTION
		" Number of instances of receive signalling all 1's  "
	::= { wfE1Entry 16 }

wfE1RcvUnfrm1s OBJECT-TYPE
	SYNTAX	Counter
	ACCESS	read-only
	STATUS	mandatory
	DESCRIPTION
		" Number of instances of Receive unframed all 1's  "
	::= { wfE1Entry 17 }

wfFakeEvent	OBJECT IDENTIFIER ::= { wfSnmpGroup 4 }

wfFakeEventString OBJECT-TYPE
	SYNTAX	DisplayString
	ACCESS	read-only
	STATUS	optional
	DESCRIPTION
		" A dummy display string. While no string will actually be kept here, the
		  full identifier (object id + attribute id + instance ID ) will be used to
		  wrap event strings passed from the system logger into an SNMP Trap message.
		 "
	::= { wfFakeEvent 1 }

wfFddiTable OBJECT-TYPE
	SYNTAX	SEQUENCE OF WfFddiEntry
	ACCESS	not-accessible
	STATUS	mandatory
	DESCRIPTION
		" FDDI line record "
	::= { wfLine 4 }

wfFddiEntry OBJECT-TYPE
	SYNTAX	WfFddiEntry
	ACCESS	not-accessible
	STATUS	mandatory
	DESCRIPTION
		" An entry in the FDDI table "
	INDEX	{ wfFDDISlot,
		wfFDDINode }
	::= { wfFddiTable 1 }

WfFddiEntry ::= SEQUENCE {
	wfFDDIDelete
		INTEGER,
	wfFDDIEnable
		INTEGER,
	wfFDDIState
		INTEGER,
	wfFDDISlot
		INTEGER,
	wfFDDINode
		INTEGER,
	wfFDDICct
		INTEGER,
	wfFDDIBofl
		INTEGER,
	wfFDDIBoflTmo
		INTEGER,
	wfFDDIMtu
		INTEGER,
	wfFDDIMadr
		OCTET STRING,
	wfFDDIOctetsRxOk
		Counter,
	wfFDDIFramesRxOk
		Counter,
	wfFDDIOctetsTxOk
		Counter,
	wfFDDIFramesTxOk
		Counter,
	wfFDDICrcErrRx
		Counter,
	wfFDDIOverrunRx
		Counter,
	wfFDDIParityErrRx
		Counter,
	wfFDDIMacErrRx
		Counter,
	wfFDDIRingErrRx
		Counter,
	wfFDDISmtRingErrRx
		Counter,
	wfFDDIRingOverrunRx
		Counter,
	wfFDDISmtRingOverrunRx
		Counter,
	wfFDDIAbortTx
		Counter,
	wfFDDIUnderrunTx
		Counter,
	wfFDDIParityErrTx
		Counter,
	wfFDDIRingErrTx
		Counter,
	wfFDDIPortOpErr
		Counter,
	wfFDDIInternOpErr
		Counter,
	wfFDDIHostErr
		Counter,
	wfFDDISmtConnectionPolicy
		INTEGER,
	wfFDDISmtTNotify
		INTEGER,
	wfFDDIMacTReq
		INTEGER,
	wfFDDIMacTMax
		INTEGER,
	wfFDDIMacTvxValue
		INTEGER,
	wfFDDIMacTMin
		INTEGER,
	wfFDDIHardwareFilter
		INTEGER,
	wfFDDISmtEnable
		INTEGER,
	wfFDDITxQueueLength
		INTEGER,
	wfFDDIRxQueueLength
		INTEGER,
	wfFDDITxClipFrames
		Counter,
	wfFDDIRxReplenMisses
		Counter
}

wfFDDIDelete OBJECT-TYPE
	SYNTAX	INTEGER {
		create(1),
		delete(2)
	}
	ACCESS	read-write
	STATUS	mandatory
	DESCRIPTION
		" create/delete parameter, default = created "
	DEFVAL	{ create }
	::= { wfFddiEntry 1 }

wfFDDIEnable OBJECT-TYPE
	SYNTAX	INTEGER {
		enable(1),
		disable(2)
	}
	ACCESS	read-write
	STATUS	mandatory
	DESCRIPTION
		" enable/disable parameter, default = enabled "
	DEFVAL	{ enable }
	::= { wfFddiEntry 2 }

wfFDDIState OBJECT-TYPE
	SYNTAX	INTEGER {
		up(1),
		down(2),
		init(3),
		notpresent(4)
	}
	ACCESS	read-only
	STATUS	mandatory
	DESCRIPTION
		" line driver state variable, not present, init, down, up "
	DEFVAL	{ notpresent }
	::= { wfFddiEntry 3 }

wfFDDISlot OBJECT-TYPE
	SYNTAX	INTEGER {
		minimum(1),
		maximum(14)
	}
	ACCESS	read-only
	STATUS	mandatory
	DESCRIPTION
		" instance ID slot - filled in by driver "
	::= { wfFddiEntry 4 }

wfFDDINode OBJECT-TYPE
	SYNTAX	INTEGER {
		one(1),
		two(2)
	}
	ACCESS	read-only
	STATUS	mandatory
	DESCRIPTION
		" instance ID Node - filled in by driver "
	DEFVAL	{ one }
	::= { wfFddiEntry 5 }

wfFDDICct OBJECT-TYPE
	SYNTAX	INTEGER {
		minimum(1),
		maximum(1023)
	}
	ACCESS	read-write
	STATUS	mandatory
	DESCRIPTION
		" cct number for this line instance "
	::= { wfFddiEntry 6 }

wfFDDIBofl OBJECT-TYPE
	SYNTAX	INTEGER {
		enable(1),
		disable(2)
	}
	ACCESS	read-write
	STATUS	mandatory
	DESCRIPTION
		" bofl parameter, default = enabled "
	DEFVAL	{ enable }
	::= { wfFddiEntry 7 }

wfFDDIBoflTmo OBJECT-TYPE
	SYNTAX	INTEGER {
		minimum(1),
		maximum(60),
		default(5)
	}
	ACCESS	read-write
	STATUS	mandatory
	DESCRIPTION
		" bofl parameter, default = 5 seconds "
	DEFVAL	{ default }
	::= { wfFddiEntry 8 }

wfFDDIMtu OBJECT-TYPE
	SYNTAX	INTEGER {
		default(4495)
	}
	ACCESS	read-only
	STATUS	mandatory
	DESCRIPTION
		" mtu parameter, fixed "
	DEFVAL	{ default }
	::= { wfFddiEntry 9 }

wfFDDIMadr OBJECT-TYPE
	SYNTAX	OCTET STRING
	ACCESS	read-only
	STATUS	mandatory
	DESCRIPTION
		" line MAC address, fixed - line driver fills in "
	::= { wfFddiEntry 10 }

wfFDDIOctetsRxOk OBJECT-TYPE
	SYNTAX	Counter
	ACCESS	read-only
	STATUS	mandatory
	DESCRIPTION
		" Number of bytes received without error "
	::= { wfFddiEntry 11 }

wfFDDIFramesRxOk OBJECT-TYPE
	SYNTAX	Counter
	ACCESS	read-only
	STATUS	mandatory
	DESCRIPTION
		" Number of frames received without error "
	::= { wfFddiEntry 12 }

wfFDDIOctetsTxOk OBJECT-TYPE
	SYNTAX	Counter
	ACCESS	read-only
	STATUS	mandatory
	DESCRIPTION
		" Number of bytes transmitted without error "
	::= { wfFddiEntry 13 }

wfFDDIFramesTxOk OBJECT-TYPE
	SYNTAX	Counter
	ACCESS	read-only
	STATUS	mandatory
	DESCRIPTION
		" Number of frames transmitted without error "
	::= { wfFddiEntry 14 }

wfFDDICrcErrRx OBJECT-TYPE
	SYNTAX	Counter
	ACCESS	read-only
	STATUS	mandatory
	DESCRIPTION
		" Number of frames received with CRC errors "
	::= { wfFddiEntry 15 }

wfFDDIOverrunRx OBJECT-TYPE
	SYNTAX	Counter
	ACCESS	read-only
	STATUS	mandatory
	DESCRIPTION
		" Number of frames received with internal overrun errors "
	::= { wfFddiEntry 16 }

wfFDDIParityErrRx OBJECT-TYPE
	SYNTAX	Counter
	ACCESS	read-only
	STATUS	mandatory
	DESCRIPTION
		" Number of frames received with parity errors "
	::= { wfFddiEntry 17 }

wfFDDIMacErrRx OBJECT-TYPE
	SYNTAX	Counter
	ACCESS	read-only
	STATUS	mandatory
	DESCRIPTION
		" Number of frames received with mac errors "
	::= { wfFddiEntry 18 }

wfFDDIRingErrRx OBJECT-TYPE
	SYNTAX	Counter
	ACCESS	read-only
	STATUS	mandatory
	DESCRIPTION
		" Number of receive ring error events "
	::= { wfFddiEntry 19 }

wfFDDISmtRingErrRx OBJECT-TYPE
	SYNTAX	Counter
	ACCESS	read-only
	STATUS	mandatory
	DESCRIPTION
		" Number of SMT receive ring error events "
	::= { wfFddiEntry 20 }

wfFDDIRingOverrunRx OBJECT-TYPE
	SYNTAX	Counter
	ACCESS	read-only
	STATUS	mandatory
	DESCRIPTION
		" Number of LLC receive ring overrun events "
	::= { wfFddiEntry 21 }

wfFDDISmtRingOverrunRx OBJECT-TYPE
	SYNTAX	Counter
	ACCESS	read-only
	STATUS	mandatory
	DESCRIPTION
		" Number of SMT receive ring overrun events "
	::= { wfFddiEntry 22 }

wfFDDIAbortTx OBJECT-TYPE
	SYNTAX	Counter
	ACCESS	read-only
	STATUS	mandatory
	DESCRIPTION
		" Number of transmit frames with internal abort errors "
	::= { wfFddiEntry 23 }

wfFDDIUnderrunTx OBJECT-TYPE
	SYNTAX	Counter
	ACCESS	read-only
	STATUS	mandatory
	DESCRIPTION
		" Number of transmit frames aborted with underrun errors "
	::= { wfFddiEntry 24 }

wfFDDIParityErrTx OBJECT-TYPE
	SYNTAX	Counter
	ACCESS	read-only
	STATUS	mandatory
	DESCRIPTION
		" Number of transmit frames aborted with parity errors "
	::= { wfFddiEntry 25 }

wfFDDIRingErrTx OBJECT-TYPE
	SYNTAX	Counter
	ACCESS	read-only
	STATUS	mandatory
	DESCRIPTION
		" Number of LLC/SMT transmit ring error events "
	::= { wfFddiEntry 26 }

wfFDDIPortOpErr OBJECT-TYPE
	SYNTAX	Counter
	ACCESS	read-only
	STATUS	mandatory
	DESCRIPTION
		" Number of port operation error events "
	::= { wfFddiEntry 27 }

wfFDDIInternOpErr OBJECT-TYPE
	SYNTAX	Counter
	ACCESS	read-only
	STATUS	mandatory
	DESCRIPTION
		" Number of internal operation error events "
	::= { wfFddiEntry 28 }

wfFDDIHostErr OBJECT-TYPE
	SYNTAX	Counter
	ACCESS	read-only
	STATUS	mandatory
	DESCRIPTION
		" Number of host error events "
	::= { wfFddiEntry 29 }

wfFDDISmtConnectionPolicy OBJECT-TYPE
	SYNTAX	INTEGER {
		default(65381)
	}
	ACCESS	read-write
	STATUS	mandatory
	DESCRIPTION
		" A value that indicates the connection policies
		   enforced at the station. A station sets the
		   corresponding policy for each of the connection
		   types that it rejects. The letter designations, X
		   and Y, in the 'rejectX-Y' names have the following
		   significance: X represents the PC-Type of the
		   local PORT and Y represents a PC-Neighbor in the
		   evaluation of Connection-Policy (PC-Type, PC-
		   Neighbor) that is done to determine the setting of
		   T-Val(3) in the PC-Signaling sequence.
		   The value is a sum. This value initially takes
		   the value zero, then for each of the connection
		   policies currently enforced on the node, 2 raised
		   to a power is added to the sum. The powers are
		   according to the following table:
		          Policy   Power
		       rejectA-A   0
		       rejectA-B   1
		       rejectA-S   2
		       rejectA-M   3
		       rejectB-A   4
		       rejectB-B   5
		       rejectB-S   6
		       rejectB-M   7
		       rejectS-A   8
		       rejectS-B   9
		       rejectS-S   10
		       rejectS-M   11
		       rejectM-A   12
		       rejectM-B   13
		       rejectM-S   14
		       rejectM-M   15 "
	DEFVAL	{ default }
	::= { wfFddiEntry 30 }

wfFDDISmtTNotify OBJECT-TYPE
	SYNTAX	INTEGER {
		min(2),
		default(22),
		max(30)
	}
	ACCESS	read-write
	STATUS	mandatory
	DESCRIPTION
		" The timer used in the Neighbor Notification
		   protocol, reported in seconds and ranging from 2
		   to 30 seconds. "
	DEFVAL	{ default }
	::= { wfFddiEntry 31 }

wfFDDIMacTReq OBJECT-TYPE
	SYNTAX	INTEGER {
		default(2062500)
	}
	ACCESS	read-write
	STATUS	mandatory
	DESCRIPTION
		" The requested Target Token Rotation Time (TTRT)
		   for a MAC's synchronous traffic represented in
		   unsigned integer specifying time in octet units
		   (80 nanoseconds). "
	DEFVAL	{ default }
	::= { wfFddiEntry 32 }

wfFDDIMacTMax OBJECT-TYPE
	SYNTAX	INTEGER {
		default(2097152)
	}
	ACCESS	read-only
	STATUS	mandatory
	DESCRIPTION
		" The requested maximum TTRT to be supported by a
		   MAC represented in unsigned integer specifying
		   time in octet units (80 nanoseconds). "
	DEFVAL	{ default }
	::= { wfFddiEntry 33 }

wfFDDIMacTvxValue OBJECT-TYPE
	SYNTAX	INTEGER {
		default(32768)
	}
	ACCESS	read-only
	STATUS	mandatory
	DESCRIPTION
		" The requested value of TvxValue represented in
		   unsigned integer specifying time in octet units
		   (80 nanoseconds). "
	DEFVAL	{ default }
	::= { wfFddiEntry 34 }

wfFDDIMacTMin OBJECT-TYPE
	SYNTAX	INTEGER {
		default(50000)
	}
	ACCESS	read-only
	STATUS	mandatory
	DESCRIPTION
		" The requested minimum TTRT to be requested by a
		   MAC represented in unsigned integer specifying
		   time in octet units (80 nanoseconds). "
	DEFVAL	{ default }
	::= { wfFddiEntry 35 }

wfFDDIHardwareFilter OBJECT-TYPE
	SYNTAX	INTEGER {
		enable(1),
		disable(2)
	}
	ACCESS	read-write
	STATUS	mandatory
	DESCRIPTION
		" Hardware filter (CAM) parameter. "
	DEFVAL	{ disable }
	::= { wfFddiEntry 36 }

wfFDDISmtEnable OBJECT-TYPE
	SYNTAX	INTEGER {
		enable(1),
		disable(2)
	}
	ACCESS	read-write
	STATUS	mandatory
	DESCRIPTION
		" "
	DEFVAL	{ enable }
	::= { wfFddiEntry 37 }

wfFDDITxQueueLength OBJECT-TYPE
	SYNTAX	INTEGER {
		minimum(1),
		maximum(255),
		default(127)
	}
	ACCESS	read-write
	STATUS	mandatory
	DESCRIPTION
		" Transmit Queue Length, values larger than the compiled ring size
		   are truncated to the compiled ring size.
		"
	DEFVAL	{ default }
	::= { wfFddiEntry 38 }

wfFDDIRxQueueLength OBJECT-TYPE
	SYNTAX	INTEGER {
		minimum(1),
		maximum(255),
		default(64)
	}
	ACCESS	read-write
	STATUS	mandatory
	DESCRIPTION
		" Receive Queue Length, values larger than the compiled ring size
		   are truncated to the compiled ring size.
		"
	DEFVAL	{ default }
	::= { wfFddiEntry 39 }

wfFDDITxClipFrames OBJECT-TYPE
	SYNTAX	Counter
	ACCESS	read-only
	STATUS	mandatory
	DESCRIPTION
		" Number of frames clipped in driver's transmit routine due to transmit
		   congestion.
		"
	::= { wfFddiEntry 40 }

wfFDDIRxReplenMisses OBJECT-TYPE
	SYNTAX	Counter
	ACCESS	read-only
	STATUS	mandatory
	DESCRIPTION
		" Number of packet buffer misses while attempting to replenish driver
		   receive ring.
		"
	::= { wfFddiEntry 41 }

wfFddiSmtTable OBJECT-TYPE
	SYNTAX	SEQUENCE OF WfFddiSmtEntry
	ACCESS	not-accessible
	STATUS	mandatory
	DESCRIPTION
		" A list of SMT entries. "
	::= { wfFddiSmtGroup 2 }

wfFddiSmtEntry OBJECT-TYPE
	SYNTAX	WfFddiSmtEntry
	ACCESS	not-accessible
	STATUS	mandatory
	DESCRIPTION
		" An SMT entry containing information common to a given SMT. "
	INDEX	{ wfFddiSmtSlot,
		wfFddiSmtNode }
	::= { wfFddiSmtTable 1 }

WfFddiSmtEntry ::= SEQUENCE {
	wfFddiSmtSlot
		INTEGER,
	wfFddiSmtNode
		INTEGER,
	wfFddiSmtCct
		INTEGER,
	wfFddiSmtStationId
		OCTET STRING,
	wfFddiSmtOpVersionId
		INTEGER,
	wfFddiSmtMacCt
		INTEGER,
	wfFddiSmtNonMasterCt
		INTEGER,
	wfFddiSmtEcmState
		INTEGER,
	wfFddiSmtCfState
		INTEGER
}

wfFddiSmtSlot OBJECT-TYPE
	SYNTAX	INTEGER
	ACCESS	read-only
	STATUS	mandatory
	DESCRIPTION
		" Slot number associated with an SMT entity. "
	::= { wfFddiSmtEntry 1 }

wfFddiSmtNode OBJECT-TYPE
	SYNTAX	INTEGER
	ACCESS	read-only
	STATUS	mandatory
	DESCRIPTION
		" Node/connector number associated with an SMT entity. "
	::= { wfFddiSmtEntry 2 }

wfFddiSmtCct OBJECT-TYPE
	SYNTAX	INTEGER
	ACCESS	read-only
	STATUS	mandatory
	DESCRIPTION
		" Circuit number associated with an SMT entity. "
	::= { wfFddiSmtEntry 3 }

wfFddiSmtStationId OBJECT-TYPE
	SYNTAX	OCTET STRING
	ACCESS	read-only
	STATUS	mandatory
	DESCRIPTION
		" Unique identifier of an FDDI station. "
	::= { wfFddiSmtEntry 4 }

wfFddiSmtOpVersionId OBJECT-TYPE
	SYNTAX	INTEGER
	ACCESS	read-only
	STATUS	mandatory
	DESCRIPTION
		" The version that this station is using for its
		   operation. "
	::= { wfFddiSmtEntry 5 }

wfFddiSmtMacCt OBJECT-TYPE
	SYNTAX	INTEGER
	ACCESS	read-only
	STATUS	mandatory
	DESCRIPTION
		" The number of MACs in the station or
		   concentrator. "
	::= { wfFddiSmtEntry 6 }

wfFddiSmtNonMasterCt OBJECT-TYPE
	SYNTAX	INTEGER
	ACCESS	read-only
	STATUS	mandatory
	DESCRIPTION
		" The number of Non Master PORTs (A, B, or S PORTs)
		   in the station or concentrator. "
	::= { wfFddiSmtEntry 7 }

wfFddiSmtEcmState OBJECT-TYPE
	SYNTAX	INTEGER {
		out(1),
		in(2),
		trace(3),
		leave(4),
		pathtest(5),
		insert(6),
		check(7),
		deinsert(8)
	}
	ACCESS	read-only
	STATUS	mandatory
	DESCRIPTION
		" Indicates the current state of the ECM state
		   machine. "
	::= { wfFddiSmtEntry 8 }

wfFddiSmtCfState OBJECT-TYPE
	SYNTAX	INTEGER {
		isolated(1),
		wraps(2),
		wrapa(3),
		wrapb(4),
		wrapab(5),
		thru(6)
	}
	ACCESS	read-only
	STATUS	mandatory
	DESCRIPTION
		" The attachment configuration for the station or
		   concentrator. "
	::= { wfFddiSmtEntry 9 }

wfFddiMacTable OBJECT-TYPE
	SYNTAX	SEQUENCE OF WfFddiMacEntry
	ACCESS	not-accessible
	STATUS	mandatory
	DESCRIPTION
		" A list of MAC entries. "
	::= { wfFddiMacGroup 2 }

wfFddiMacEntry OBJECT-TYPE
	SYNTAX	WfFddiMacEntry
	ACCESS	not-accessible
	STATUS	mandatory
	DESCRIPTION
		" A MAC entry containing information common to a given MAC. "
	INDEX	{ wfFddiMacSlot,
		wfFddiMacNode }
	::= { wfFddiMacTable 1 }

WfFddiMacEntry ::= SEQUENCE {
	wfFddiMacSlot
		INTEGER,
	wfFddiMacNode
		INTEGER,
	wfFddiMacCct
		INTEGER,
	wfFddiMacUpstreamNbr
		OCTET STRING,
	wfFddiMacDownstreamNbr
		OCTET STRING,
	wfFddiMacSmtAddress
		OCTET STRING,
	wfFddiMacTNeg
		INTEGER,
	wfFddiMacRmtState
		INTEGER
}

wfFddiMacSlot OBJECT-TYPE
	SYNTAX	INTEGER
	ACCESS	read-only
	STATUS	mandatory
	DESCRIPTION
		" Slot number associated with a MAC entity. "
	::= { wfFddiMacEntry 1 }

wfFddiMacNode OBJECT-TYPE
	SYNTAX	INTEGER
	ACCESS	read-only
	STATUS	mandatory
	DESCRIPTION
		" Node/connector number associated with a MAC entity. "
	::= { wfFddiMacEntry 2 }

wfFddiMacCct OBJECT-TYPE
	SYNTAX	INTEGER
	ACCESS	read-only
	STATUS	mandatory
	DESCRIPTION
		" Circuit number associated with a MAC entity. "
	::= { wfFddiMacEntry 3 }

wfFddiMacUpstreamNbr OBJECT-TYPE
	SYNTAX	OCTET STRING
	ACCESS	read-only
	STATUS	mandatory
	DESCRIPTION
		" The MAC's upstream neighbor's long individual MAC
		   address.  It may be determined by the Neighbor
		   Information Frame protocol. The value shall be
		   reported as '00 00 00 00 00 00' if it is unknown. "
	::= { wfFddiMacEntry 4 }

wfFddiMacDownstreamNbr OBJECT-TYPE
	SYNTAX	OCTET STRING
	ACCESS	read-only
	STATUS	mandatory
	DESCRIPTION
		" The MAC's downstream neighbor's long individual MAC
		   address.  It may be determined by the Neighbor
		   Information Frame protocol.  The value shall be
		   reported as '00 00 00 00 00 00' if it is unknown. "
	::= { wfFddiMacEntry 5 }

wfFddiMacSmtAddress OBJECT-TYPE
	SYNTAX	OCTET STRING
	ACCESS	read-only
	STATUS	mandatory
	DESCRIPTION
		" The 48 bit individual address of the MAC used for
		   SMT frames. "
	::= { wfFddiMacEntry 6 }

wfFddiMacTNeg OBJECT-TYPE
	SYNTAX	INTEGER
	ACCESS	read-only
	STATUS	mandatory
	DESCRIPTION
		" The negotiated TTRT during the claim process
		   represented in unsigned integer specifying
		   time in octet units (80 nanosecond). "
	::= { wfFddiMacEntry 7 }

wfFddiMacRmtState OBJECT-TYPE
	SYNTAX	INTEGER {
		isolated(1),
		nonop(2),
		ringop(4),
		detect(8),
		nonopdup(16),
		ringopdup(32),
		directed(64),
		trace(128)
	}
	ACCESS	read-only
	STATUS	mandatory
	DESCRIPTION
		" Indicates the current state of the Ring
		   Management state machine. "
	::= { wfFddiMacEntry 8 }

wfFddiPortTable OBJECT-TYPE
	SYNTAX	SEQUENCE OF WfFddiPortEntry
	ACCESS	not-accessible
	STATUS	mandatory
	DESCRIPTION
		" A list of PORT entries. The number of entries is given by the value of
		   wfFddiPortNumber. "
	::= { wfFddiPortGroup 2 }

wfFddiPortEntry OBJECT-TYPE
	SYNTAX	WfFddiPortEntry
	ACCESS	not-accessible
	STATUS	mandatory
	DESCRIPTION
		" A PORT entry containing information common to a given PORT. "
	INDEX	{ wfFddiPortSlot,
		wfFddiPortNode,
		wfFddiPortIndex }
	::= { wfFddiPortTable 1 }

WfFddiPortEntry ::= SEQUENCE {
	wfFddiPortSlot
		INTEGER,
	wfFddiPortNode
		INTEGER,
	wfFddiPortCct
		INTEGER,
	wfFddiPortIndex
		INTEGER,
	wfFddiPortPcType
		INTEGER,
	wfFddiPortPcNeighbor
		INTEGER,
	wfFddiPortPcmState
		INTEGER
}

wfFddiPortSlot OBJECT-TYPE
	SYNTAX	INTEGER
	ACCESS	read-only
	STATUS	mandatory
	DESCRIPTION
		" Slot number associated with a PORT entity. "
	::= { wfFddiPortEntry 1 }

wfFddiPortNode OBJECT-TYPE
	SYNTAX	INTEGER
	ACCESS	read-only
	STATUS	mandatory
	DESCRIPTION
		" Node/connector number associated with a PORT entity. "
	::= { wfFddiPortEntry 2 }

wfFddiPortCct OBJECT-TYPE
	SYNTAX	INTEGER
	ACCESS	read-only
	STATUS	mandatory
	DESCRIPTION
		" Circuit number associated with a PORT entity. "
	::= { wfFddiPortEntry 3 }

wfFddiPortIndex OBJECT-TYPE
	SYNTAX	INTEGER
	ACCESS	read-only
	STATUS	mandatory
	DESCRIPTION
		" A unique value for each PORT associated with each
		   slot/connector pair. "
	::= { wfFddiPortEntry 4 }

wfFddiPortPcType OBJECT-TYPE
	SYNTAX	INTEGER {
		a(1),
		b(2),
		s(3),
		m(4)
	}
	ACCESS	read-only
	STATUS	mandatory
	DESCRIPTION
		" PC_Type. "
	::= { wfFddiPortEntry 5 }

wfFddiPortPcNeighbor OBJECT-TYPE
	SYNTAX	INTEGER {
		a(1),
		b(2),
		s(3),
		m(4),
		unknown(5)
	}
	ACCESS	read-only
	STATUS	mandatory
	DESCRIPTION
		" The type (PC_Neighbor) of the remote PORT that is
		   determined in PC_Signaling in R_Val (1,2). "
	::= { wfFddiPortEntry 6 }

wfFddiPortPcmState OBJECT-TYPE
	SYNTAX	INTEGER {
		off(1),
		break(2),
		trace(3),
		connect(4),
		next(5),
		signal(6),
		join(7),
		verify(8),
		active(9),
		maint(10)
	}
	ACCESS	read-only
	STATUS	mandatory
	DESCRIPTION
		" State of Physical State Machine. "
	::= { wfFddiPortEntry 7 }

wfFrDlcmiTable OBJECT-TYPE
	SYNTAX	SEQUENCE OF WfFrDlcmiEntry
	ACCESS	not-accessible
	STATUS	mandatory
	DESCRIPTION
		"The Parameters for the Data Link Connection Management Interface "
	::= { wfFrameRelayGroup 1 }

wfFrDlcmiEntry OBJECT-TYPE
	SYNTAX	WfFrDlcmiEntry
	ACCESS	not-accessible
	STATUS	mandatory
	DESCRIPTION
		"The parameters for a particular Data Link Connection Management Interface"
	INDEX	{ wfFrDlcmiCircuit }
	::= { wfFrDlcmiTable 1 }

WfFrDlcmiEntry ::= SEQUENCE {
	wfFrDlcmiDelete
		INTEGER,
	wfFrDlcmiDisable
		INTEGER,
	wfFrDlcmiState
		INTEGER,
	wfFrDlcmiCircuit
		INTEGER,
	wfFrDlcmiManagementType
		INTEGER,
	wfFrDlcmiStatus
		INTEGER,
	wfFrDlcmiAddress
		INTEGER,
	wfFrDlcmiAddressLen
		INTEGER,
	wfFrDlcmiPollingInterval
		INTEGER,
	wfFrDlcmiFullEnquiryInterval
		INTEGER,
	wfFrDlcmiErrorThreshold
		INTEGER,
	wfFrDlcmiMonitoredEvents
		INTEGER,
	wfFrDlcmiMaxSupportedVCs
		INTEGER,
	wfFrDlcmiMulticast
		INTEGER,
	wfFrDlcmiSeqCount
		INTEGER,
	wfFrDlcmiLastReceived
		INTEGER,
	wfFrDlcmiPassiveSeqCount
		INTEGER,
	wfFrDlcmiPassiveReceived
		INTEGER,
	wfFrDlcmiPolls
		INTEGER,
	wfFrDlcmiAlarmTimer
		INTEGER,
	wfFrErrType
		INTEGER,
	wfFrErrData
		OCTET STRING,
	wfFrErrTime
		TimeTicks,
	wfFrErrDiscards
		Counter,
	wfFrErrDrops
		Counter
}

wfFrDlcmiDelete OBJECT-TYPE
	SYNTAX	INTEGER {
		created(1),
		deleted(2)
	}
	ACCESS	read-write
	STATUS	mandatory
	DESCRIPTION
		" Indication to delete this frame relay interface "
	DEFVAL	{ created }
	::= { wfFrDlcmiEntry 1 }

wfFrDlcmiDisable OBJECT-TYPE
	SYNTAX	INTEGER {
		enabled(1),
		disabled(2)
	}
	ACCESS	read-write
	STATUS	mandatory
	DESCRIPTION
		" Indicates when a dlcmi entry is to be enabled or disabled. "
	DEFVAL	{ enabled }
	::= { wfFrDlcmiEntry 2 }

wfFrDlcmiState OBJECT-TYPE
	SYNTAX	INTEGER {
		up(1),
		down(2),
		init(3),
		notpresent(4)
	}
	ACCESS	read-only
	STATUS	mandatory
	DESCRIPTION
		" The current state of Frame Relay. The not present state is not actually
		   valid except when the record is first added.  It is included for 
		   consistency. "
	DEFVAL	{ notpresent }
	::= { wfFrDlcmiEntry 3 }

wfFrDlcmiCircuit OBJECT-TYPE
	SYNTAX	INTEGER
	ACCESS	read-only
	STATUS	mandatory
	DESCRIPTION
		" Instance identifier.  The circuit number of this entry"
	::= { wfFrDlcmiEntry 4 }

wfFrDlcmiManagementType OBJECT-TYPE
	SYNTAX	INTEGER {
		none(1),
		lmi(2),
		t1617d(3),
		t1617b(4),
		annexa(5),
		lmiswitch(6),
		annexdswitch(7),
		annexaswitch(8)
	}
	ACCESS	read-write
	STATUS	mandatory
	DESCRIPTION
		" This variable indicates which Data Link Connection Management
		   scheme is active (and by implication, what DLCI it uses).  "
	DEFVAL	{ t1617d }
	::= { wfFrDlcmiEntry 5 }

wfFrDlcmiStatus OBJECT-TYPE
	SYNTAX	INTEGER {
		start(1),
		running(2),
		fault(3),
		recovered(4)
	}
	ACCESS	read-only
	STATUS	mandatory
	DESCRIPTION
		" Indicates the status of the interface.
		 FR_STATUS_START is the state during rebooting or initial 
		  start of circuit
		 FR_STATUS_RUNNING is the sate after the circuit is up (either LMI 
		  successful or there is no DLCMI and the system just comes up).
		 FR_STATUS_FAULT is a transient state indicating that errors have 
		  caused the circuit to be disabled until DLCMI recovery.
		 FR_STATUS_RECOVERED indicates that an the system has been in the 
		  FR_STATUS_FAULT mode before, but has since recovered.
		"
	DEFVAL	{ start }
	::= { wfFrDlcmiEntry 6 }

wfFrDlcmiAddress OBJECT-TYPE
	SYNTAX	INTEGER {
		q921(1),
		q922march90(2),
		q922november90(3),
		q922(4)
	}
	ACCESS	read-write
	STATUS	mandatory
	DESCRIPTION
		" This states which address format is in use on the FR interface.
		   The default is Q922 "
	DEFVAL	{ q922 }
	::= { wfFrDlcmiEntry 7 }

wfFrDlcmiAddressLen OBJECT-TYPE
	SYNTAX	INTEGER {
		twobyte(2),
		threebyte(3),
		fourbyte(4)
	}
	ACCESS	read-write
	STATUS	mandatory
	DESCRIPTION
		" This variable states the address length in octets. In the case
		   of Q922 format, the length indicates the entire length of the 
		   address includeding the control portion. "
	DEFVAL	{ twobyte }
	::= { wfFrDlcmiEntry 8 }

wfFrDlcmiPollingInterval OBJECT-TYPE
	SYNTAX	INTEGER {
		minimum(5),
		default(10),
		maximum(30)
	}
	ACCESS	read-write
	STATUS	mandatory
	DESCRIPTION
		" The number of seconds between successive status enquiry messages "
	DEFVAL	{ default }
	::= { wfFrDlcmiEntry 9 }

wfFrDlcmiFullEnquiryInterval OBJECT-TYPE
	SYNTAX	INTEGER {
		minimum(1),
		default(6),
		maximum(255)
	}
	ACCESS	read-write
	STATUS	mandatory
	DESCRIPTION
		" The number of status enquiry intervals that pass before issuance
		   of a full status enquiry message. "
	DEFVAL	{ default }
	::= { wfFrDlcmiEntry 10 }

wfFrDlcmiErrorThreshold OBJECT-TYPE
	SYNTAX	INTEGER
	ACCESS	read-write
	STATUS	mandatory
	DESCRIPTION
		"This is the maximum number of unanswered Status Enquiries the
		  equipment shall accept before declaring the interface down. "
	DEFVAL	{ 3 }
	::= { wfFrDlcmiEntry 11 }

wfFrDlcmiMonitoredEvents OBJECT-TYPE
	SYNTAX	INTEGER
	ACCESS	read-write
	STATUS	mandatory
	DESCRIPTION
		" This is the number of status polling intervals over
		   which the error threshold is counted.  For example, if 
		   within 'MonitoredEvents' number of events the station
		   receives 'ErrorThreshold' number of errors, the 
		   interface is marked as down. "
	DEFVAL	{ 4 }
	::= { wfFrDlcmiEntry 12 }

wfFrDlcmiMaxSupportedVCs OBJECT-TYPE
	SYNTAX	INTEGER
	ACCESS	read-only
	STATUS	mandatory
	DESCRIPTION
		" The maximum number of Virtual Circuits allowed for
		   this interface.  Usually dictated by the Frame Relay
		   network. The system sets this initially. "
	::= { wfFrDlcmiEntry 13 }

wfFrDlcmiMulticast OBJECT-TYPE
	SYNTAX	INTEGER {
		enabled(1),
		disabled(2)
	}
	ACCESS	read-write
	STATUS	mandatory
	DESCRIPTION
		" This indicates whether the frame relay provider offers a multicast "
	DEFVAL	{ disabled }
	::= { wfFrDlcmiEntry 14 }

wfFrDlcmiSeqCount OBJECT-TYPE
	SYNTAX	INTEGER {
		minimum(1),
		maximum(255)
	}
	ACCESS	read-only
	STATUS	mandatory
	DESCRIPTION
		" This station's sequence counter. It represents the next
		   value to send. "
	DEFVAL	{ minimum }
	::= { wfFrDlcmiEntry 15 }

wfFrDlcmiLastReceived OBJECT-TYPE
	SYNTAX	INTEGER {
		minimum(1),
		maximum(255)
	}
	ACCESS	read-only
	STATUS	mandatory
	DESCRIPTION
		" The sequence number just received from the switch. "
	DEFVAL	{ minimum }
	::= { wfFrDlcmiEntry 16 }

wfFrDlcmiPassiveSeqCount OBJECT-TYPE
	SYNTAX	INTEGER {
		minimum(1),
		maximum(255)
	}
	ACCESS	read-only
	STATUS	mandatory
	DESCRIPTION
		" This station's sequence counter for answering status enquiry. "
	DEFVAL	{ minimum }
	::= { wfFrDlcmiEntry 17 }

wfFrDlcmiPassiveReceived OBJECT-TYPE
	SYNTAX	INTEGER {
		minimum(1),
		maximum(255)
	}
	ACCESS	read-only
	STATUS	mandatory
	DESCRIPTION
		" The sequence number just received from the enquring station. "
	DEFVAL	{ minimum }
	::= { wfFrDlcmiEntry 18 }

wfFrDlcmiPolls OBJECT-TYPE
	SYNTAX	INTEGER
	ACCESS	read-only
	STATUS	mandatory
	DESCRIPTION
		" This is the counter of where we are in the polling cycle. "
	::= { wfFrDlcmiEntry 19 }

wfFrDlcmiAlarmTimer OBJECT-TYPE
	SYNTAX	INTEGER
	ACCESS	read-only
	STATUS	mandatory
	DESCRIPTION
		" This is a counter of 1/2 second timeouts. When it reaches
		   2 x the polling interval, an enquiry message is sent. "
	::= { wfFrDlcmiEntry 20 }

wfFrErrType OBJECT-TYPE
	SYNTAX	INTEGER {
		unknown(1),
		short(2),
		long(3),
		illegaldlci(4),
		unknowndlci(5),
		protoerr(6),
		unknownie(7),
		sequenceerr(8),
		unknownrpt(9),
		reset(10),
		cntrl(11)
	}
	ACCESS	read-only
	STATUS	mandatory
	DESCRIPTION
		" Indicate the type of the last specific monitored error. "
	::= { wfFrDlcmiEntry 21 }

wfFrErrData OBJECT-TYPE
	SYNTAX	OCTET STRING
	ACCESS	read-only
	STATUS	mandatory
	DESCRIPTION
		" Contains as much of the error packet as possible. "
	::= { wfFrDlcmiEntry 22 }

wfFrErrTime OBJECT-TYPE
	SYNTAX	TimeTicks
	ACCESS	read-only
	STATUS	mandatory
	DESCRIPTION
		" The time the last error occurred. "
	::= { wfFrDlcmiEntry 23 }

wfFrErrDiscards OBJECT-TYPE
	SYNTAX	Counter
	ACCESS	read-only
	STATUS	mandatory
	DESCRIPTION
		" The number of inbound frames dropped because of format or other
		   errors or because the VC was not known. "
	::= { wfFrDlcmiEntry 24 }

wfFrErrDrops OBJECT-TYPE
	SYNTAX	Counter
	ACCESS	read-only
	STATUS	mandatory
	DESCRIPTION
		" The number of outbound frames dropped. Usually this is due the
		   specified DLCI being unknown or a broadcast packet is too long  "
	::= { wfFrDlcmiEntry 25 }

wfFrCircuitTable OBJECT-TYPE
	SYNTAX	SEQUENCE OF WfFrCircuitEntry
	ACCESS	not-accessible
	STATUS	mandatory
	DESCRIPTION
		" Frame Relay Circuit table gives information about a virtual circuits. "
	::= { wfFrameRelayGroup 2 }

wfFrCircuitEntry OBJECT-TYPE
	SYNTAX	WfFrCircuitEntry
	ACCESS	not-accessible
	STATUS	mandatory
	DESCRIPTION
		" An entry in the Frame Relay Circuit table. "
	INDEX	{ wfFrCircuitNumber,
		wfFrCircuitDlci }
	::= { wfFrCircuitTable 1 }

WfFrCircuitEntry ::= SEQUENCE {
	wfFrCircuitDelete
		INTEGER,
	wfFrCircuitNumber
		INTEGER,
	wfFrCircuitDlci
		INTEGER,
	wfFrCircuitState
		INTEGER,
	wfFrCircuitStateSet
		INTEGER,
	wfFrCircuitReceivedFECNs
		Counter,
	wfFrCircuitReceivedBECNs
		Counter,
	wfFrCircuitSentFrames
		Counter,
	wfFrCircuitSentOctets
		Counter,
	wfFrCircuitReceivedFrames
		Counter,
	wfFrCircuitReceivedOctets
		Counter,
	wfFrCircuitCreationTime
		TimeTicks,
	wfFrCircuitLastTimeChange
		TimeTicks,
	wfFrCircuitCommittedBurst
		INTEGER,
	wfFrCircuitExcessBurst
		INTEGER,
	wfFrCircuitThroughput
		INTEGER,
	wfFrCircuitMulticast
		INTEGER,
	wfFrCircuitDiscards
		Counter,
	wfFrCircuitDrops
		Counter,
	wfFrCircuitSubCct
		INTEGER,
	wfFrCircuitMode
		INTEGER
}

wfFrCircuitDelete OBJECT-TYPE
	SYNTAX	INTEGER {
		created(1),
		deleted(2),
		system(3)
	}
	ACCESS	read-write
	STATUS	mandatory
	DESCRIPTION
		" Indication to delete this frame relay interface. "
	DEFVAL	{ created }
	::= { wfFrCircuitEntry 1 }

wfFrCircuitNumber OBJECT-TYPE
	SYNTAX	INTEGER
	ACCESS	read-only
	STATUS	mandatory
	DESCRIPTION
		" Instance identifier.  The circuit number of this interface. "
	::= { wfFrCircuitEntry 2 }

wfFrCircuitDlci OBJECT-TYPE
	SYNTAX	INTEGER {
		twobyteminimum(16),
		twobytemaximum(1007),
		threebyteminimum(1024),
		threebytemaximum(64511),
		fourbyteminimum(131072),
		fourbytemaximum(8257535)
	}
	ACCESS	read-only
	STATUS	mandatory
	DESCRIPTION
		" Instance identifier.  This indicates which virtual circuit. "
	::= { wfFrCircuitEntry 3 }

wfFrCircuitState OBJECT-TYPE
	SYNTAX	INTEGER {
		invalid(1),
		active(2),
		inactive(3),
		xoff(4),
		control(5)
	}
	ACCESS	read-only
	STATUS	mandatory
	DESCRIPTION
		" Indicates the state of the particular virtual circuit. "
	DEFVAL	{ invalid }
	::= { wfFrCircuitEntry 4 }

wfFrCircuitStateSet OBJECT-TYPE
	SYNTAX	INTEGER {
		invalid(1),
		active(2),
		inactive(3)
	}
	ACCESS	read-write
	STATUS	mandatory
	DESCRIPTION
		" User access for setting the state of a virtual circuit "
	DEFVAL	{ invalid }
	::= { wfFrCircuitEntry 5 }

wfFrCircuitReceivedFECNs OBJECT-TYPE
	SYNTAX	Counter
	ACCESS	read-only
	STATUS	mandatory
	DESCRIPTION
		" Number of frames received indicating forward congestion. "
	::= { wfFrCircuitEntry 6 }

wfFrCircuitReceivedBECNs OBJECT-TYPE
	SYNTAX	Counter
	ACCESS	read-only
	STATUS	mandatory
	DESCRIPTION
		" Number of frames received indicating backward congestion. "
	::= { wfFrCircuitEntry 7 }

wfFrCircuitSentFrames OBJECT-TYPE
	SYNTAX	Counter
	ACCESS	read-only
	STATUS	mandatory
	DESCRIPTION
		" The number of frames sent from this virtual circuit. "
	::= { wfFrCircuitEntry 8 }

wfFrCircuitSentOctets OBJECT-TYPE
	SYNTAX	Counter
	ACCESS	read-only
	STATUS	mandatory
	DESCRIPTION
		" The number of octets sent from this virtual circuit. "
	::= { wfFrCircuitEntry 9 }

wfFrCircuitReceivedFrames OBJECT-TYPE
	SYNTAX	Counter
	ACCESS	read-only
	STATUS	mandatory
	DESCRIPTION
		" The number of frames received from this virtual circuit.  "
	::= { wfFrCircuitEntry 10 }

wfFrCircuitReceivedOctets OBJECT-TYPE
	SYNTAX	Counter
	ACCESS	read-only
	STATUS	mandatory
	DESCRIPTION
		" The number of octets received from this virtual circuit. "
	::= { wfFrCircuitEntry 11 }

wfFrCircuitCreationTime OBJECT-TYPE
	SYNTAX	TimeTicks
	ACCESS	read-only
	STATUS	mandatory
	DESCRIPTION
		" The value of sysUpTime when the vc was created. "
	::= { wfFrCircuitEntry 12 }

wfFrCircuitLastTimeChange OBJECT-TYPE
	SYNTAX	TimeTicks
	ACCESS	read-only
	STATUS	mandatory
	DESCRIPTION
		" The value of sysUpTime when last there was a change in vc state. "
	::= { wfFrCircuitEntry 13 }

wfFrCircuitCommittedBurst OBJECT-TYPE
	SYNTAX	INTEGER
	ACCESS	read-write
	STATUS	mandatory
	DESCRIPTION
		" Indicates the maximum amount of data, in bits, that the network
		   agrees to transfer under normal conditions, during the measurement
		   interval.  Wellfleet does not presently support this. "
	::= { wfFrCircuitEntry 14 }

wfFrCircuitExcessBurst OBJECT-TYPE
	SYNTAX	INTEGER
	ACCESS	read-write
	STATUS	mandatory
	DESCRIPTION
		" Indicates teh maximum amount of uncommitted data bits that the network
		   will attempt to deliver over the measurement interval.  Wellfleet
		   does not presently support this.  "
	::= { wfFrCircuitEntry 15 }

wfFrCircuitThroughput OBJECT-TYPE
	SYNTAX	INTEGER
	ACCESS	read-write
	STATUS	mandatory
	DESCRIPTION
		" This is the average number of 'Frame Relay Information Field'
		   bits transferred per second across a user network interface in one
		   direction, measured over the measurement interval.  Wellfleet
		   does not presently support this.  "
	::= { wfFrCircuitEntry 16 }

wfFrCircuitMulticast OBJECT-TYPE
	SYNTAX	INTEGER {
		multicast(1),
		unicast(2)
	}
	ACCESS	read-write
	STATUS	mandatory
	DESCRIPTION
		" Indicates whether this DLCI is used for multicast or single destination. "
	DEFVAL	{ unicast }
	::= { wfFrCircuitEntry 17 }

wfFrCircuitDiscards OBJECT-TYPE
	SYNTAX	Counter
	ACCESS	read-only
	STATUS	mandatory
	DESCRIPTION
		" The number of inbound frames discarded because of format errors,
		   because the VC is inactive or because the protocol was not registered
		   for this circuit.  "
	::= { wfFrCircuitEntry 18 }

wfFrCircuitDrops OBJECT-TYPE
	SYNTAX	Counter
	ACCESS	read-only
	STATUS	mandatory
	DESCRIPTION
		" Indicates how many outbound frames were dropped. Usually these are
		   dropped because the VC is not active.  "
	::= { wfFrCircuitEntry 19 }

wfFrCircuitSubCct OBJECT-TYPE
	SYNTAX	INTEGER
	ACCESS	read-write
	STATUS	mandatory
	DESCRIPTION
		" Circuit number to use for this VC when configured in hybrid
		   (for bridging) or direct access (VC as a circuit) mode. "
	::= { wfFrCircuitEntry 20 }

wfFrCircuitMode OBJECT-TYPE
	SYNTAX	INTEGER {
		group(1),
		hybrid(2),
		direct(3)
	}
	ACCESS	read-write
	STATUS	mandatory
	DESCRIPTION
		" The mode of the given VC.
		 GROUP - treats the VC as one of many vc's on a circuit.
		 HYBRID - treats the VC as one of many vc's on a circuit for
		   protocol traffic, but as a separate circuit for bridging.
		 DIRECT - treats the VC as a separate circuit for all applications. "
	DEFVAL	{ group }
	::= { wfFrCircuitEntry 21 }

wfKernelTable OBJECT-TYPE
	SYNTAX	SEQUENCE OF WfKernelEntry
	ACCESS	not-accessible
	STATUS	mandatory
	DESCRIPTION
		" Table of kernel statistics, indexed by slot number "
	::= { wfGameGroup 1 }

wfKernelEntry OBJECT-TYPE
	SYNTAX	WfKernelEntry
	ACCESS	not-accessible
	STATUS	mandatory
	DESCRIPTION
		" A particular interface "
	INDEX	{ wfKernelSlot }
	::= { wfKernelTable 1 }

WfKernelEntry ::= SEQUENCE {
	wfKernelSlot
		INTEGER,
	wfKernelMemorySize
		INTEGER,
	wfKernelMemoryFree
		INTEGER,
	wfKernelMemorySegsTotal
		INTEGER,
	wfKernelMemorySegsFree
		INTEGER,
	wfKernelMemoryMaxSegFree
		INTEGER,
	wfKernelBuffersTotal
		INTEGER,
	wfKernelBuffersFree
		INTEGER,
	wfKernelTasksTotal
		INTEGER,
	wfKernelTasksInQueue
		INTEGER,
	wfKernelTimersTotal
		INTEGER,
	wfKernelTimersActive
		INTEGER,
	wfKernelBufOwnerTask1
		DisplayString,
	wfKernelBufOwnerTask1Bufs
		INTEGER,
	wfKernelBufOwnerTask2
		DisplayString,
	wfKernelBufOwnerTask2Bufs
		INTEGER,
	wfKernelBufOwnerTask3
		DisplayString,
	wfKernelBufOwnerTask3Bufs
		INTEGER,
	wfKernelBufOwnerTask4
		DisplayString,
	wfKernelBufOwnerTask4Bufs
		INTEGER,
	wfKernelBufOwnerTask5
		DisplayString,
	wfKernelBufOwnerTask5Bufs
		INTEGER,
	wfKernelBufOwnerTask6
		DisplayString,
	wfKernelBufOwnerTask6Bufs
		INTEGER,
	wfKernelBufOwnerTask7
		DisplayString,
	wfKernelBufOwnerTask7Bufs
		INTEGER,
	wfKernelBufOwnerTask8
		DisplayString,
	wfKernelBufOwnerTask8Bufs
		INTEGER,
	wfKernelBufOwnerTask9
		DisplayString,
	wfKernelBufOwnerTask9Bufs
		INTEGER,
	wfKernelBufOwnerTask10
		DisplayString,
	wfKernelBufOwnerTask10Bufs
		INTEGER,
	wfKernelMemOwnerTask1
		DisplayString,
	wfKernelMemOwnerTask1Size
		INTEGER,
	wfKernelMemOwnerTask2
		DisplayString,
	wfKernelMemOwnerTask2Size
		INTEGER,
	wfKernelMemOwnerTask3
		DisplayString,
	wfKernelMemOwnerTask3Size
		INTEGER,
	wfKernelMemOwnerTask4
		DisplayString,
	wfKernelMemOwnerTask4Size
		INTEGER,
	wfKernelMemOwnerTask5
		DisplayString,
	wfKernelMemOwnerTask5Size
		INTEGER,
	wfKernelMemOwnerTask6
		DisplayString,
	wfKernelMemOwnerTask6Size
		INTEGER,
	wfKernelMemOwnerTask7
		DisplayString,
	wfKernelMemOwnerTask7Size
		INTEGER,
	wfKernelMemOwnerTask8
		DisplayString,
	wfKernelMemOwnerTask8Size
		INTEGER,
	wfKernelMemOwnerTask9
		DisplayString,
	wfKernelMemOwnerTask9Size
		INTEGER,
	wfKernelMemOwnerTask10
		DisplayString,
	wfKernelMemOwnerTask10Size
		INTEGER
}

wfKernelSlot OBJECT-TYPE
	SYNTAX	INTEGER
	ACCESS	read-only
	STATUS	mandatory
	DESCRIPTION
		" The slot number indexes the kernel statistics table "
	::= { wfKernelEntry 1 }

wfKernelMemorySize OBJECT-TYPE
	SYNTAX	INTEGER
	ACCESS	read-only
	STATUS	mandatory
	DESCRIPTION
		" The total size of allocatable memory, in bytes "
	::= { wfKernelEntry 2 }

wfKernelMemoryFree OBJECT-TYPE
	SYNTAX	INTEGER
	ACCESS	read-only
	STATUS	mandatory
	DESCRIPTION
		" The amount of memory which hasn't been allocated yet, in bytes "
	::= { wfKernelEntry 3 }

wfKernelMemorySegsTotal OBJECT-TYPE
	SYNTAX	INTEGER
	ACCESS	read-only
	STATUS	mandatory
	DESCRIPTION
		" Total number of memory segments in the kernel "
	::= { wfKernelEntry 4 }

wfKernelMemorySegsFree OBJECT-TYPE
	SYNTAX	INTEGER
	ACCESS	read-only
	STATUS	mandatory
	DESCRIPTION
		" Total number of unallocated memory segments in the kernel "
	::= { wfKernelEntry 5 }

wfKernelMemoryMaxSegFree OBJECT-TYPE
	SYNTAX	INTEGER
	ACCESS	read-only
	STATUS	mandatory
	DESCRIPTION
		" Size of the largest unallocated memory segment "
	::= { wfKernelEntry 6 }

wfKernelBuffersTotal OBJECT-TYPE
	SYNTAX	INTEGER
	ACCESS	read-only
	STATUS	mandatory
	DESCRIPTION
		" Total number of packet buffers "
	::= { wfKernelEntry 7 }

wfKernelBuffersFree OBJECT-TYPE
	SYNTAX	INTEGER
	ACCESS	read-only
	STATUS	mandatory
	DESCRIPTION
		" Number of packet buffers in the free pool "
	::= { wfKernelEntry 8 }

wfKernelTasksTotal OBJECT-TYPE
	SYNTAX	INTEGER
	ACCESS	read-only
	STATUS	mandatory
	DESCRIPTION
		" Number of tasks running "
	::= { wfKernelEntry 9 }

wfKernelTasksInQueue OBJECT-TYPE
	SYNTAX	INTEGER
	ACCESS	read-only
	STATUS	mandatory
	DESCRIPTION
		" Number of tasks awaiting scheduling "
	::= { wfKernelEntry 10 }

wfKernelTimersTotal OBJECT-TYPE
	SYNTAX	INTEGER
	ACCESS	read-only
	STATUS	mandatory
	DESCRIPTION
		" Total number of timers available "
	::= { wfKernelEntry 11 }

wfKernelTimersActive OBJECT-TYPE
	SYNTAX	INTEGER
	ACCESS	read-only
	STATUS	mandatory
	DESCRIPTION
		" Total number of timers in use by tasks "
	::= { wfKernelEntry 12 }

wfKernelBufOwnerTask1 OBJECT-TYPE
	SYNTAX	DisplayString
	ACCESS	read-only
	STATUS	mandatory
	DESCRIPTION
		" Activation address of task which owns many buffers "
	::= { wfKernelEntry 13 }

wfKernelBufOwnerTask1Bufs OBJECT-TYPE
	SYNTAX	INTEGER
	ACCESS	read-only
	STATUS	mandatory
	DESCRIPTION
		" Number of buffers owned by the task "
	::= { wfKernelEntry 14 }

wfKernelBufOwnerTask2 OBJECT-TYPE
	SYNTAX	DisplayString
	ACCESS	read-only
	STATUS	mandatory
	DESCRIPTION
		" Activation address of task which owns many buffers "
	::= { wfKernelEntry 15 }

wfKernelBufOwnerTask2Bufs OBJECT-TYPE
	SYNTAX	INTEGER
	ACCESS	read-only
	STATUS	mandatory
	DESCRIPTION
		" Number of buffers owned by the task "
	::= { wfKernelEntry 16 }

wfKernelBufOwnerTask3 OBJECT-TYPE
	SYNTAX	DisplayString
	ACCESS	read-only
	STATUS	mandatory
	DESCRIPTION
		" Activation address of task which owns many buffers "
	::= { wfKernelEntry 17 }

wfKernelBufOwnerTask3Bufs OBJECT-TYPE
	SYNTAX	INTEGER
	ACCESS	read-only
	STATUS	mandatory
	DESCRIPTION
		" Number of buffers owned by the task "
	::= { wfKernelEntry 18 }

wfKernelBufOwnerTask4 OBJECT-TYPE
	SYNTAX	DisplayString
	ACCESS	read-only
	STATUS	mandatory
	DESCRIPTION
		" Activation address of task which owns many buffers "
	::= { wfKernelEntry 19 }

wfKernelBufOwnerTask4Bufs OBJECT-TYPE
	SYNTAX	INTEGER
	ACCESS	read-only
	STATUS	mandatory
	DESCRIPTION
		" Number of buffers owned by the task "
	::= { wfKernelEntry 20 }

wfKernelBufOwnerTask5 OBJECT-TYPE
	SYNTAX	DisplayString
	ACCESS	read-only
	STATUS	mandatory
	DESCRIPTION
		" Activation address of task which owns many buffers "
	::= { wfKernelEntry 21 }

wfKernelBufOwnerTask5Bufs OBJECT-TYPE
	SYNTAX	INTEGER
	ACCESS	read-only
	STATUS	mandatory
	DESCRIPTION
		" Number of buffers owned by the task "
	::= { wfKernelEntry 22 }

wfKernelBufOwnerTask6 OBJECT-TYPE
	SYNTAX	DisplayString
	ACCESS	read-only
	STATUS	mandatory
	DESCRIPTION
		" Activation address of task which owns many buffers "
	::= { wfKernelEntry 23 }

wfKernelBufOwnerTask6Bufs OBJECT-TYPE
	SYNTAX	INTEGER
	ACCESS	read-only
	STATUS	mandatory
	DESCRIPTION
		" Number of buffers owned by the task "
	::= { wfKernelEntry 24 }

wfKernelBufOwnerTask7 OBJECT-TYPE
	SYNTAX	DisplayString
	ACCESS	read-only
	STATUS	mandatory
	DESCRIPTION
		" Activation address of task which owns many buffers "
	::= { wfKernelEntry 25 }

wfKernelBufOwnerTask7Bufs OBJECT-TYPE
	SYNTAX	INTEGER
	ACCESS	read-only
	STATUS	mandatory
	DESCRIPTION
		" Number of buffers owned by the task "
	::= { wfKernelEntry 26 }

wfKernelBufOwnerTask8 OBJECT-TYPE
	SYNTAX	DisplayString
	ACCESS	read-only
	STATUS	mandatory
	DESCRIPTION
		" Activation address of task which owns many buffers "
	::= { wfKernelEntry 27 }

wfKernelBufOwnerTask8Bufs OBJECT-TYPE
	SYNTAX	INTEGER
	ACCESS	read-only
	STATUS	mandatory
	DESCRIPTION
		" Number of buffers owned by the task "
	::= { wfKernelEntry 28 }

wfKernelBufOwnerTask9 OBJECT-TYPE
	SYNTAX	DisplayString
	ACCESS	read-only
	STATUS	mandatory
	DESCRIPTION
		" Activation address of task which owns many buffers "
	::= { wfKernelEntry 29 }

wfKernelBufOwnerTask9Bufs OBJECT-TYPE
	SYNTAX	INTEGER
	ACCESS	read-only
	STATUS	mandatory
	DESCRIPTION
		" Number of buffers owned by the task "
	::= { wfKernelEntry 30 }

wfKernelBufOwnerTask10 OBJECT-TYPE
	SYNTAX	DisplayString
	ACCESS	read-only
	STATUS	mandatory
	DESCRIPTION
		" Activation address of task which owns many buffers "
	::= { wfKernelEntry 31 }

wfKernelBufOwnerTask10Bufs OBJECT-TYPE
	SYNTAX	INTEGER
	ACCESS	read-only
	STATUS	mandatory
	DESCRIPTION
		" Number of buffers owned by the task "
	::= { wfKernelEntry 32 }

wfKernelMemOwnerTask1 OBJECT-TYPE
	SYNTAX	DisplayString
	ACCESS	read-only
	STATUS	mandatory
	DESCRIPTION
		" Activation address of task which owns a sizable amount of memory "
	::= { wfKernelEntry 33 }

wfKernelMemOwnerTask1Size OBJECT-TYPE
	SYNTAX	INTEGER
	ACCESS	read-only
	STATUS	mandatory
	DESCRIPTION
		" Amount of memory owned by the task "
	::= { wfKernelEntry 34 }

wfKernelMemOwnerTask2 OBJECT-TYPE
	SYNTAX	DisplayString
	ACCESS	read-only
	STATUS	mandatory
	DESCRIPTION
		" Activation address of task which owns a sizable amount of memory "
	::= { wfKernelEntry 35 }

wfKernelMemOwnerTask2Size OBJECT-TYPE
	SYNTAX	INTEGER
	ACCESS	read-only
	STATUS	mandatory
	DESCRIPTION
		" Amount of memory owned by the task "
	::= { wfKernelEntry 36 }

wfKernelMemOwnerTask3 OBJECT-TYPE
	SYNTAX	DisplayString
	ACCESS	read-only
	STATUS	mandatory
	DESCRIPTION
		" Activation address of task which owns a sizable amount of memory "
	::= { wfKernelEntry 37 }

wfKernelMemOwnerTask3Size OBJECT-TYPE
	SYNTAX	INTEGER
	ACCESS	read-only
	STATUS	mandatory
	DESCRIPTION
		" Amount of memory owned by the task "
	::= { wfKernelEntry 38 }

wfKernelMemOwnerTask4 OBJECT-TYPE
	SYNTAX	DisplayString
	ACCESS	read-only
	STATUS	mandatory
	DESCRIPTION
		" Activation address of task which owns a sizable amount of memory "
	::= { wfKernelEntry 39 }

wfKernelMemOwnerTask4Size OBJECT-TYPE
	SYNTAX	INTEGER
	ACCESS	read-only
	STATUS	mandatory
	DESCRIPTION
		" Amount of memory owned by the task "
	::= { wfKernelEntry 40 }

wfKernelMemOwnerTask5 OBJECT-TYPE
	SYNTAX	DisplayString
	ACCESS	read-only
	STATUS	mandatory
	DESCRIPTION
		" Activation address of task which owns a sizable amount of memory "
	::= { wfKernelEntry 41 }

wfKernelMemOwnerTask5Size OBJECT-TYPE
	SYNTAX	INTEGER
	ACCESS	read-only
	STATUS	mandatory
	DESCRIPTION
		" Amount of memory owned by the task "
	::= { wfKernelEntry 42 }

wfKernelMemOwnerTask6 OBJECT-TYPE
	SYNTAX	DisplayString
	ACCESS	read-only
	STATUS	mandatory
	DESCRIPTION
		" Activation address of task which owns a sizable amount of memory "
	::= { wfKernelEntry 43 }

wfKernelMemOwnerTask6Size OBJECT-TYPE
	SYNTAX	INTEGER
	ACCESS	read-only
	STATUS	mandatory
	DESCRIPTION
		" Amount of memory owned by the task "
	::= { wfKernelEntry 44 }

wfKernelMemOwnerTask7 OBJECT-TYPE
	SYNTAX	DisplayString
	ACCESS	read-only
	STATUS	mandatory
	DESCRIPTION
		" Activation address of task which owns a sizable amount of memory "
	::= { wfKernelEntry 45 }

wfKernelMemOwnerTask7Size OBJECT-TYPE
	SYNTAX	INTEGER
	ACCESS	read-only
	STATUS	mandatory
	DESCRIPTION
		" Amount of memory owned by the task "
	::= { wfKernelEntry 46 }

wfKernelMemOwnerTask8 OBJECT-TYPE
	SYNTAX	DisplayString
	ACCESS	read-only
	STATUS	mandatory
	DESCRIPTION
		" Activation address of task which owns a sizable amount of memory "
	::= { wfKernelEntry 47 }

wfKernelMemOwnerTask8Size OBJECT-TYPE
	SYNTAX	INTEGER
	ACCESS	read-only
	STATUS	mandatory
	DESCRIPTION
		" Amount of memory owned by the task "
	::= { wfKernelEntry 48 }

wfKernelMemOwnerTask9 OBJECT-TYPE
	SYNTAX	DisplayString
	ACCESS	read-only
	STATUS	mandatory
	DESCRIPTION
		" Activation address of task which owns a sizable amount of memory "
	::= { wfKernelEntry 49 }

wfKernelMemOwnerTask9Size OBJECT-TYPE
	SYNTAX	INTEGER
	ACCESS	read-only
	STATUS	mandatory
	DESCRIPTION
		" Amount of memory owned by the task "
	::= { wfKernelEntry 50 }

wfKernelMemOwnerTask10 OBJECT-TYPE
	SYNTAX	DisplayString
	ACCESS	read-only
	STATUS	mandatory
	DESCRIPTION
		" Activation address of task which owns a sizable amount of memory "
	::= { wfKernelEntry 51 }

wfKernelMemOwnerTask10Size OBJECT-TYPE
	SYNTAX	INTEGER
	ACCESS	read-only
	STATUS	mandatory
	DESCRIPTION
		" Amount of memory owned by the task "
	::= { wfKernelEntry 52 }

wfHwBase	OBJECT IDENTIFIER ::= { wfHardwareConfig 1 }

wfHwBpIdOpt OBJECT-TYPE
	SYNTAX	INTEGER {
		acefn(1),
		aceln(2),
		acecn(3),
		fns(4),
		in(5),
		freln(16640),
		frecn(16896)
	}
	ACCESS	read-only
	STATUS	mandatory
	DESCRIPTION
		" The BackPlane identification number.
		  "
	::= { wfHwBase 1 }

wfHwBpRev OBJECT-TYPE
	SYNTAX	OCTET STRING
	ACCESS	read-only
	STATUS	mandatory
	DESCRIPTION
		" The revision level of the BackPlane. High byte is in upper 2 bytes.
		  "
	::= { wfHwBase 2 }

wfHwBpSerialNumber OBJECT-TYPE
	SYNTAX	OCTET STRING
	ACCESS	read-only
	STATUS	mandatory
	DESCRIPTION
		" The serial number of the BackPlane.
		  "
	::= { wfHwBase 3 }

wfBCNPwrSupply1 OBJECT-TYPE
	SYNTAX	INTEGER {
		ok(1),
		fail(2),
		notpresent(3)
	}
	ACCESS	read-only
	STATUS	mandatory
	DESCRIPTION
		" Status of BCN Hot-Swappable Power Supply 1
		  "
	DEFVAL	{ notpresent }
	::= { wfHwBase 4 }

wfBCNPwrSupply2 OBJECT-TYPE
	SYNTAX	INTEGER {
		ok(1),
		fail(2),
		notpresent(3)
	}
	ACCESS	read-only
	STATUS	mandatory
	DESCRIPTION
		" Status of BCN Hot-Swappable Power Supply 2
		  "
	DEFVAL	{ notpresent }
	::= { wfHwBase 5 }

wfBCNPwrSupply3 OBJECT-TYPE
	SYNTAX	INTEGER {
		ok(1),
		fail(2),
		notpresent(3)
	}
	ACCESS	read-only
	STATUS	mandatory
	DESCRIPTION
		" Status of BCN Hot-Swappable Power Supply 3
		  "
	DEFVAL	{ notpresent }
	::= { wfHwBase 6 }

wfBCNPwrSupply4 OBJECT-TYPE
	SYNTAX	INTEGER {
		ok(1),
		fail(2),
		notpresent(3)
	}
	ACCESS	read-only
	STATUS	mandatory
	DESCRIPTION
		" Status of BCN Hot-Swappable Power Supply 4
		  "
	DEFVAL	{ notpresent }
	::= { wfHwBase 7 }

wfBCNFanStatus OBJECT-TYPE
	SYNTAX	INTEGER {
		ok(1),
		fail(2),
		notpresent(3)
	}
	ACCESS	read-only
	STATUS	mandatory
	DESCRIPTION
		" Status of BCN Fan Tray
		  "
	DEFVAL	{ notpresent }
	::= { wfHwBase 8 }

wfBCNTemperature OBJECT-TYPE
	SYNTAX	INTEGER {
		ok(1),
		caution(2),
		notpresent(3)
	}
	ACCESS	read-only
	STATUS	mandatory
	DESCRIPTION
		" Status of BCN Fan Tray
		  "
	DEFVAL	{ notpresent }
	::= { wfHwBase 9 }

wfHwTable OBJECT-TYPE
	SYNTAX	SEQUENCE OF WfHwEntry
	ACCESS	not-accessible
	STATUS	mandatory
	DESCRIPTION
		" Hardware Table  - indexed by slot number "
	::= { wfHardwareConfig 2 }

wfHwEntry OBJECT-TYPE
	SYNTAX	WfHwEntry
	ACCESS	not-accessible
	STATUS	mandatory
	DESCRIPTION
		" Hardware specific information about a slot. "
	INDEX	{ wfHwSlot }
	::= { wfHwTable 1 }

WfHwEntry ::= SEQUENCE {
	wfHwSlot
		INTEGER,
	wfHwModIdOpt
		INTEGER,
	wfHwModRev
		OCTET STRING,
	wfHwModSerialNumber
		OCTET STRING,
	wfHwMotherBdIdOpt
		INTEGER,
	wfHwMotherBdRev
		OCTET STRING,
	wfHwMotherBdSerialNumber
		OCTET STRING,
	wfHwDaughterBdIdOpt
		INTEGER,
	wfHwDaughterBdRev
		OCTET STRING,
	wfHwDaughterBdSerialNumber
		OCTET STRING,
	wfHwBabyBdIdOpt
		INTEGER,
	wfHwBabyBdRev
		OCTET STRING,
	wfHwBabyBdSerialNumber
		OCTET STRING,
	wfHwDiagPromRev
		OCTET STRING,
	wfHwDiagPromDate
		DisplayString,
	wfHwDiagPromSource
		DisplayString,
	wfHwBootPromRev
		OCTET STRING,
	wfHwBootPromDate
		DisplayString,
	wfHwBootPromSource
		DisplayString,
	wfHwSparePromRev
		OCTET STRING,
	wfHwSparePromDate
		DisplayString,
	wfHwSparePromSource
		DisplayString,
	wfHwFileSysPresent
		INTEGER
}

wfHwSlot OBJECT-TYPE
	SYNTAX	INTEGER
	ACCESS	read-only
	STATUS	mandatory
	DESCRIPTION
		" A unique value for each slot.
		  Its value ranges between 1 and 14.
		  There are products in this family that contain 1, 5, and 14 slots.
		  "
	::= { wfHwEntry 1 }

wfHwModIdOpt OBJECT-TYPE
	SYNTAX	INTEGER {
		enet1(1),
		enet2(8),
		sync1(16),
		sync1a(17),
		t11(24),
		dse1(32),
		dse1a(33),
		dst416(40),
		sst416a(41),
		dst4(42),
		sst4a(43),
		sst416(44),
		stok416(45),
		sst4(46),
		stok4(47),
		floppy(48),
		t12(56),
		t12a(57),
		st1(58),
		t156k(60),
		e1(61),
		st156k(62),
		se1(63),
		t12n(64),
		st1n(65),
		t156kn(66),
		st156kn(67),
		e1n(68),
		se1n(69),
		sync(80),
		sync2a(81),
		cmcfddi(88),
		iphfddi(89),
		dt(104),
		dsde1(112),
		dsde1a(113),
		enet(114),
		dse2(116),
		dse2a(117),
		sse(118),
		ssea(119),
		dsde10bt(120),
		enet3(132),
		dsde2(156),
		oldqenf(160),
		denf(161),
		qenf(162),
		qef(164),
		def(165),
		mct1(168),
		dtok(176),
		mce1(184),
		wffddi2m(192),
		wffddi1m(193),
		wffddi2s(194),
		wffddi1s(195),
		wffddi2mf(196),
		wffddi1mf(197),
		wffddi2sf(198),
		wffddi1sf(199),
		fnsdse(208),
		fnsdsdt(216),
		fnsdst(217),
		dhssi(224),
		shssi(225),
		srml(8448)
	}
	ACCESS	read-only
	STATUS	mandatory
	DESCRIPTION
		" The module identification number.
		 
		      Port Configurations
		  HWStat Name  Enet Sync Async Token Framer Fiber
		  ------ ------------ ------ ---- ----- ----- ------ -----
		     1 ENET-1  2 0 0 0 0 0
		     8 ENET-2  2 0 0 0 0 0
		 
		    16 SYNC-1  0 4 1 0 0 0
		    17 SYNC-1 [1] 0 4 1 0 0 0
		 
		    24 T1-1  0 2 1 0 2 0
		 
		    32 DSE-1  1 2 1 0 0 0
		    33 DSE-1  [1] 1 2 1 0 0 0
		 
		    40 DST-4/16 0 2 1 1 0 0
		    41 SST-4/16  [1] 0 1 1 1 0 0
		    42 DST-4  0 2 1 1 0 0
		    43 SST-4   [1] 0 1 1 1 0 0
		    44 SST-4/16 0 1 1 1 0 0
		    45 STOK-4/16 [3] 0 0 0 1 0 0
		    46 SST-4  0 1 1 1 0 0
		    47 STOK-4   [3] 0 0 0 1 0 0
		 
		    48 FLOPPY    0 0 0 0 0 0
		 
		    56 T1-2  0 2 1 0 2 0
		    57 T1-2  0 2 1 0 2 0
		    58 ST1  0 1 1 0 1 0
		    60 T1-56K  0 1 1 0 1 0
		    61 E1 [3] 0 2 0 0 2 0
		    62 ST1-56K  0 1 1 0 1 0
		    63 SE1 [3] 0 1 0 0 1 0
		 
		    64 T1-2n  0 2 1 0 2 0
		    65 ST1n  0 1 1 0 1 0
		    66 T1-56Kn  0 1 1 0 1 0
		    67 ST1-56Kn 0 1 1 0 1 0
		    68 E1n [3] 0 2 0 0 2 0
		    69 SE1n [3] 0 1 0 0 1 0
		    80 SYNC-2  0 4 1 0 0 0
		    81 SYNC-2  [1] 0 4 1 0 0 0
		 
		    88 CMC-FDDI    [6] 0 0 0 0 0 1
		    89 IPHASE-FDDI [6] 0 0 0 0 0 1
		 
		   104 DT  0 0 0 2 0 0
		 
		   112 DSDE-1  2 2 1 0 0 0
		   113 DSDE-1  [1] 2 2 1 0 0 0
		   114 ENET  2 0 0 0 0 0
		   116 DSE-2  1 2 1 0 0 0
		   117 DSE-2   [1] 1 2 1 0 0 0
		   118 SSE  1 1 1 0 0 0
		   119 SSE     [1] 1 1 1 0 0 0
		 
		       120    DSDE10BT        2       2       0       0       0       0
		 
		   132 ENET-3 [2] 2 0 0 0 0 0
		   156 DSDE-2 [2] 2 2 1 0 0 0
		 
		   160 QE/NF  4 0 0 0 0 0
		   161 DE/NF [5] 2 0 0 0 0 0
		   162 QE/NF  4 0 0 0 0 0
		   164 QE/F [4] 4 0 0 0 0 0
		   165 DE/F [4,5] 2 0 0 0 0 0
		 
		       168    MCT1            0    2 Munich   0       0       2       0
		 
		   176 DTOK  0 0 0 2 0 0
		 
		       168    MCE1            0    2 Munich   0       0       2       0
		 
		   192 WF_FDDI_2M 0 0 0 0 0 1
		   193 WF_FDDI_1M 0 0 0 0 0 1
		   194 WF_FDDI_2S 0 0 0 0 0 1
		   195 WF_FDDI_1S 0 0 0 0 0 1
		   196 WF_FDDI_2MF 0 0 0 0 0 1
		   197 WF_FDDI_1MF 0 0 0 0 0 1
		   198 WF_FDDI_2SF 0 0 0 0 0 1
		   199 WF_FDDI_1SF 0 0 0 0 0 1
		 
		   208 FNSDSE   [7] 1 2 0 0 0 0
		   216 FNSDSDT  [7] 0 2 0 2 0 0
		   217 FNSDST   [7] 0 2 0 1 0 0
		 
		       224    DHSSI           0    2 hssi     0       0       0       0
		       225    SHSSI           0    1 hssi     0       0       0       0
		 
		  8448 SRML  0 0 0 0 0 0
		 
		 
		  NOTES:
		   [1] Indicates Module has COM Port 1 configured for ASYNC.
		    The AM8530's port B is configured for COM1.
		  
		   [2] This Module contains the DEFA - Hardware Filtering.  CAMS
		    must be programmed (can contain 2 - 6 CAMS onboard).
		  
		   [3] The AM8530 has been removed (depopulated) from this module.
		    Programming this device should not be performed.
		  
		   [4] Contains Dual Defa hardware. (Can be depopulated)
		  
		   [5] Depop'd two ports of hardware to make Dual Ethernet module.
		  
		   [6] These are FDDI modules.  The ID cannot be read from the Link
		    module I/O space.
		 
		      [7] These are FNS Platform Integrated 'Modules' - Cannot be detached
		              or be used by any other platform.
		 
		  "
	::= { wfHwEntry 2 }

wfHwModRev OBJECT-TYPE
	SYNTAX	OCTET STRING
	ACCESS	read-only
	STATUS	mandatory
	DESCRIPTION
		" The revision level of the module. High byte is in upper 2 bytes.
		  "
	::= { wfHwEntry 3 }

wfHwModSerialNumber OBJECT-TYPE
	SYNTAX	OCTET STRING
	ACCESS	read-only
	STATUS	mandatory
	DESCRIPTION
		" The serial number of the module.
		  "
	::= { wfHwEntry 4 }

wfHwMotherBdIdOpt OBJECT-TYPE
	SYNTAX	INTEGER {
		sysctrl(1),
		ace12(2),
		ace25(3),
		ace32(4),
		fns(5),
		in(6),
		fre(256),
		srmf(8704)
	}
	ACCESS	read-only
	STATUS	mandatory
	DESCRIPTION
		" The mother board identification number.
		  "
	::= { wfHwEntry 5 }

wfHwMotherBdRev OBJECT-TYPE
	SYNTAX	OCTET STRING
	ACCESS	read-only
	STATUS	mandatory
	DESCRIPTION
		" The revision level of the mother board. High byte is in upper 2 bytes.
		  "
	::= { wfHwEntry 6 }

wfHwMotherBdSerialNumber OBJECT-TYPE
	SYNTAX	OCTET STRING
	ACCESS	read-only
	STATUS	mandatory
	DESCRIPTION
		" The serial number of the mother board.
		  "
	::= { wfHwEntry 7 }

wfHwDaughterBdIdOpt OBJECT-TYPE
	SYNTAX	INTEGER {
		sysctrl(1),
		ace68020mhz12(2),
		ace68020mhz25(3),
		ace68030mhz32(4),
		fre68040mhz25(4352),
		fre68040mhz33(4608)
	}
	ACCESS	read-only
	STATUS	mandatory
	DESCRIPTION
		" The daughter board identification number.
		  "
	::= { wfHwEntry 8 }

wfHwDaughterBdRev OBJECT-TYPE
	SYNTAX	OCTET STRING
	ACCESS	read-only
	STATUS	mandatory
	DESCRIPTION
		" The revision level of the daughter board. High byte is in upper 2 bytes.
		  "
	::= { wfHwEntry 9 }

wfHwDaughterBdSerialNumber OBJECT-TYPE
	SYNTAX	OCTET STRING
	ACCESS	read-only
	STATUS	mandatory
	DESCRIPTION
		" The serial number of the daughter board.
		  "
	::= { wfHwEntry 10 }

wfHwBabyBdIdOpt OBJECT-TYPE
	SYNTAX	INTEGER
	ACCESS	read-only
	STATUS	mandatory
	DESCRIPTION
		" The baby board identification number.
		  "
	::= { wfHwEntry 11 }

wfHwBabyBdRev OBJECT-TYPE
	SYNTAX	OCTET STRING
	ACCESS	read-only
	STATUS	mandatory
	DESCRIPTION
		" The revision level of the baby board. High byte is in upper 2 bytes.
		  "
	::= { wfHwEntry 12 }

wfHwBabyBdSerialNumber OBJECT-TYPE
	SYNTAX	OCTET STRING
	ACCESS	read-only
	STATUS	mandatory
	DESCRIPTION
		" The serial number of the baby board.
		  "
	::= { wfHwEntry 13 }

wfHwDiagPromRev OBJECT-TYPE
	SYNTAX	OCTET STRING
	ACCESS	read-only
	STATUS	mandatory
	DESCRIPTION
		" The revision level of the Diagnostic PROM. Major revision level
		  is in the upper 2 bytes, minor revision level in the lower 2 bytes. "
	::= { wfHwEntry 14 }

wfHwDiagPromDate OBJECT-TYPE
	SYNTAX	DisplayString
	ACCESS	read-only
	STATUS	mandatory
	DESCRIPTION
		" The creation date of the Diagnostic PROM "
	::= { wfHwEntry 15 }

wfHwDiagPromSource OBJECT-TYPE
	SYNTAX	DisplayString
	ACCESS	read-only
	STATUS	mandatory
	DESCRIPTION
		" The origin of the Diagnostic PROM contents "
	::= { wfHwEntry 16 }

wfHwBootPromRev OBJECT-TYPE
	SYNTAX	OCTET STRING
	ACCESS	read-only
	STATUS	mandatory
	DESCRIPTION
		" The revision level of the BOOT PROM. Major revision level
		  is in the upper 2 bytes, minor revision level in the lower 2 bytes. "
	::= { wfHwEntry 17 }

wfHwBootPromDate OBJECT-TYPE
	SYNTAX	DisplayString
	ACCESS	read-only
	STATUS	mandatory
	DESCRIPTION
		" The creation date of the Boot PROM "
	::= { wfHwEntry 18 }

wfHwBootPromSource OBJECT-TYPE
	SYNTAX	DisplayString
	ACCESS	read-only
	STATUS	mandatory
	DESCRIPTION
		" The origin of the Boot PROM contents "
	::= { wfHwEntry 19 }

wfHwSparePromRev OBJECT-TYPE
	SYNTAX	OCTET STRING
	ACCESS	read-only
	STATUS	mandatory
	DESCRIPTION
		" The revision level of the BOOT PROM. Major revision level
		  is in the upper 2 bytes, minor revision level in the lower 2 bytes. "
	::= { wfHwEntry 20 }

wfHwSparePromDate OBJECT-TYPE
	SYNTAX	DisplayString
	ACCESS	read-only
	STATUS	mandatory
	DESCRIPTION
		" The creation date of the Spare PROM "
	::= { wfHwEntry 21 }

wfHwSparePromSource OBJECT-TYPE
	SYNTAX	DisplayString
	ACCESS	read-only
	STATUS	mandatory
	DESCRIPTION
		" The origin of the Spare PROM contents "
	::= { wfHwEntry 22 }

wfHwFileSysPresent OBJECT-TYPE
	SYNTAX	INTEGER {
		filesys(1),
		nofilesys(2)
	}
	ACCESS	read-only
	STATUS	mandatory
	DESCRIPTION
		" Flag indicating presence of File System on this slot.
		  "
	DEFVAL	{ nofilesys }
	::= { wfHwEntry 23 }

wfHssiTable OBJECT-TYPE
	SYNTAX	SEQUENCE OF WfHssiEntry
	ACCESS	not-accessible
	STATUS	mandatory
	DESCRIPTION
		"
		    HSSI line record
		 "
	::= { wfLine 7 }

wfHssiEntry OBJECT-TYPE
	SYNTAX	WfHssiEntry
	ACCESS	not-accessible
	STATUS	mandatory
	DESCRIPTION
		" An entry in the HSSI table "
	INDEX	{ wfHssiSlot,
		wfHssiConnector }
	::= { wfHssiTable 1 }

WfHssiEntry ::= SEQUENCE {
	wfHssiDelete
		INTEGER,
	wfHssiDisable
		INTEGER,
	wfHssiState
		INTEGER,
	wfHssiSlot
		INTEGER,
	wfHssiConnector
		INTEGER,
	wfHssiCct
		INTEGER,
	wfHssiBofl
		INTEGER,
	wfHssiBoflTmo
		INTEGER,
	wfHssiMtu
		INTEGER,
	wfHssiMadr
		OCTET STRING,
	wfHssiService
		INTEGER,
	wfHssiWanProtocol
		INTEGER,
	wfHssiTransmissionInterface
		INTEGER,
	wfHssiExternalClkSpeed
		INTEGER,
	wfHssiCrcSize
		INTEGER,
	wfHssiInternalClkTestMode
		INTEGER,
	wfHssiRxOctets
		Counter,
	wfHssiRxFrames
		Counter,
	wfHssiTxOctets
		Counter,
	wfHssiTxFrames
		Counter,
	wfHssiInDiscards
		Counter,
	wfHssiInErrors
		Counter,
	wfHssiOutDiscards
		Counter,
	wfHssiOutErrors
		Counter,
	wfHssiRxLongFrames
		Counter,
	wfHssiTxClipFrames
		Counter,
	wfHssiRxReplenMisses
		Counter,
	wfHssiLastRxErrorCtrl
		INTEGER,
	wfHssiRxCrcErrors
		Counter,
	wfHssiRxOverruns
		Counter,
	wfHssiRxAborts
		Counter,
	wfHssiLastTxErrorCtrl
		INTEGER,
	wfHssiTxAborts
		Counter,
	wfHssiTxUnderruns
		Counter,
	wfHssiRxRingErrors
		Counter,
	wfHssiLastRxRingState
		INTEGER,
	wfHssiRxRingOverruns
		Counter,
	wfHssiTxRingErrors
		Counter,
	wfHssiLastTxRingState
		INTEGER,
	wfHssiPortOpErrors
		Counter,
	wfHssiInternOpErrors
		Counter,
	wfHssiHostErrors
		Counter,
	wfHssiRxProcessings
		Counter,
	wfHssiTxProcessings
		Counter,
	wfHssiTxCmplProcessings
		Counter,
	wfHssiIntrProcessings
		Counter,
	wfHssiBoflNum
		INTEGER,
	wfHssiBoflLen
		INTEGER,
	wfHssiRxBufferLength
		INTEGER,
	wfHssiMemPageLength
		INTEGER,
	wfHssiRxRingLength
		INTEGER,
	wfHssiTxRingLength
		INTEGER,
	wfHssiRxFifoWatermark
		INTEGER,
	wfHssiTxFifoWatermark
		INTEGER,
	wfHssiMaxRxMemory
		INTEGER,
	wfHssiLinkInterface
		INTEGER,
	wfHssiTurboBofl
		INTEGER
}

wfHssiDelete OBJECT-TYPE
	SYNTAX	INTEGER {
		created(1),
		deleted(2)
	}
	ACCESS	read-write
	STATUS	mandatory
	DESCRIPTION
		" Create/Delete parameter "
	DEFVAL	{ created }
	::= { wfHssiEntry 1 }

wfHssiDisable OBJECT-TYPE
	SYNTAX	INTEGER {
		enabled(1),
		disabled(2)
	}
	ACCESS	read-write
	STATUS	mandatory
	DESCRIPTION
		" Enable/Disable parameter "
	DEFVAL	{ enabled }
	::= { wfHssiEntry 2 }

wfHssiState OBJECT-TYPE
	SYNTAX	INTEGER {
		up(1),
		lmiwait(2),
		boflwait(3),
		cawait(4),
		init(5),
		notpresent(6)
	}
	ACCESS	read-only
	STATUS	mandatory
	DESCRIPTION
		" Line Driver state variable, Not Present, Init, Down, Up "
	DEFVAL	{ notpresent }
	::= { wfHssiEntry 3 }

wfHssiSlot OBJECT-TYPE
	SYNTAX	INTEGER {
		minimum(1),
		maximum(14)
	}
	ACCESS	read-only
	STATUS	mandatory
	DESCRIPTION
		" Instance ID Slot, filled in by driver "
	::= { wfHssiEntry 4 }

wfHssiConnector OBJECT-TYPE
	SYNTAX	INTEGER {
		one(1),
		two(2),
		three(3),
		four(4)
	}
	ACCESS	read-only
	STATUS	mandatory
	DESCRIPTION
		" Instance ID Connector, filled in by driver "
	::= { wfHssiEntry 5 }

wfHssiCct OBJECT-TYPE
	SYNTAX	INTEGER {
		minimum(1),
		maximum(1023)
	}
	ACCESS	read-write
	STATUS	mandatory
	DESCRIPTION
		" CCT number for this line instance "
	::= { wfHssiEntry 6 }

wfHssiBofl OBJECT-TYPE
	SYNTAX	INTEGER {
		enabled(1),
		disabled(2)
	}
	ACCESS	read-write
	STATUS	mandatory
	DESCRIPTION
		" breath of life parameter "
	DEFVAL	{ enabled }
	::= { wfHssiEntry 7 }

wfHssiBoflTmo OBJECT-TYPE
	SYNTAX	INTEGER {
		minimum(1),
		maximum(60),
		default(1)
	}
	ACCESS	read-write
	STATUS	mandatory
	DESCRIPTION
		" breath of life frequency in seconds "
	DEFVAL	{ default }
	::= { wfHssiEntry 8 }

wfHssiMtu OBJECT-TYPE
	SYNTAX	INTEGER {
		minimum(3),
		maximum(4500),
		default(4495)
	}
	ACCESS	read-write
	STATUS	mandatory
	DESCRIPTION
		" MTU parameter, this is buffer size for HSSI media, fixed "
	DEFVAL	{ default }
	::= { wfHssiEntry 9 }

wfHssiMadr OBJECT-TYPE
	SYNTAX	OCTET STRING
	ACCESS	read-only
	STATUS	mandatory
	DESCRIPTION
		" Line MAC address, fixed - line driver fills in from the 48 bit
		   address stored in the serial number prom for this connector.   "
	::= { wfHssiEntry 10 }

wfHssiService OBJECT-TYPE
	SYNTAX	INTEGER {
		transparent(1),
		undefined(2)
	}
	ACCESS	read-write
	STATUS	mandatory
	DESCRIPTION
		" Service type for this circuit. Transparent is raw HDLC mode, and is the
		   only service provided on the current HSSI product "
	DEFVAL	{ transparent }
	::= { wfHssiEntry 11 }

wfHssiWanProtocol OBJECT-TYPE
	SYNTAX	INTEGER {
		standard(1),
		passthru(2),
		ppp(3),
		smds(4),
		framerelay(5)
	}
	ACCESS	read-write
	STATUS	mandatory
	DESCRIPTION
		" WAN protocol selection is provided via this parameter. The
		   supported protocols can be selected per interface. "
	DEFVAL	{ standard }
	::= { wfHssiEntry 12 }

wfHssiTransmissionInterface OBJECT-TYPE
	SYNTAX	INTEGER {
		dsone(1),
		dsthree(3)
	}
	ACCESS	read-write
	STATUS	mandatory
	DESCRIPTION
		" T1 or T3,  in the future OC1, OC3 and OC12.  Used for MIB selection "
	DEFVAL	{ dsthree }
	::= { wfHssiEntry 13 }

wfHssiExternalClkSpeed OBJECT-TYPE
	SYNTAX	INTEGER {
		minimum(307200),
		maximum(52638515),
		default(46359642)
	}
	ACCESS	read-write
	STATUS	mandatory
	DESCRIPTION
		" External Clock Speed, Used in the future for route selection "
	DEFVAL	{ default }
	::= { wfHssiEntry 14 }

wfHssiCrcSize OBJECT-TYPE
	SYNTAX	INTEGER {
		crc16bit(1),
		crc32bit(2)
	}
	ACCESS	read-write
	STATUS	mandatory
	DESCRIPTION
		" CRC size parameter, 16 bit standard CCITT or extended 32 bit CRC "
	DEFVAL	{ crc32bit }
	::= { wfHssiEntry 15 }

wfHssiInternalClkTestMode OBJECT-TYPE
	SYNTAX	INTEGER {
		enabled(1),
		disabled(2)
	}
	ACCESS	read-write
	STATUS	mandatory
	DESCRIPTION
		" Enables internal transmit clock generation. Should NEVER be enabled for
		   normal operation. "
	DEFVAL	{ disabled }
	::= { wfHssiEntry 16 }

wfHssiRxOctets OBJECT-TYPE
	SYNTAX	Counter
	ACCESS	read-only
	STATUS	mandatory
	DESCRIPTION
		" Number of bytes received without error "
	::= { wfHssiEntry 17 }

wfHssiRxFrames OBJECT-TYPE
	SYNTAX	Counter
	ACCESS	read-only
	STATUS	mandatory
	DESCRIPTION
		" Number of frames received without error "
	::= { wfHssiEntry 18 }

wfHssiTxOctets OBJECT-TYPE
	SYNTAX	Counter
	ACCESS	read-only
	STATUS	mandatory
	DESCRIPTION
		" Number of bytes transmitted without error "
	::= { wfHssiEntry 19 }

wfHssiTxFrames OBJECT-TYPE
	SYNTAX	Counter
	ACCESS	read-only
	STATUS	mandatory
	DESCRIPTION
		" Number of frames transmitted without error "
	::= { wfHssiEntry 20 }

wfHssiInDiscards OBJECT-TYPE
	SYNTAX	Counter
	ACCESS	read-only
	STATUS	mandatory
	DESCRIPTION
		" Number of error-free inbound packets discarded. Usually due to lack of
		   memory resources. "
	::= { wfHssiEntry 21 }

wfHssiInErrors OBJECT-TYPE
	SYNTAX	Counter
	ACCESS	read-only
	STATUS	mandatory
	DESCRIPTION
		" Number of inbound packets not delivered to higher-layer protocol because
		   of errors. "
	::= { wfHssiEntry 22 }

wfHssiOutDiscards OBJECT-TYPE
	SYNTAX	Counter
	ACCESS	read-only
	STATUS	mandatory
	DESCRIPTION
		" Number of error-free outbound packets discarded. Usually due to lack of
		   transmission bandwidth. "
	::= { wfHssiEntry 23 }

wfHssiOutErrors OBJECT-TYPE
	SYNTAX	Counter
	ACCESS	read-only
	STATUS	mandatory
	DESCRIPTION
		" Number of outbound packets that could not be transmitted because of
		   errors. "
	::= { wfHssiEntry 24 }

wfHssiRxLongFrames OBJECT-TYPE
	SYNTAX	Counter
	ACCESS	read-only
	STATUS	mandatory
	DESCRIPTION
		" Number of Long frames dropped on receive because of length "
	::= { wfHssiEntry 25 }

wfHssiTxClipFrames OBJECT-TYPE
	SYNTAX	Counter
	ACCESS	read-only
	STATUS	mandatory
	DESCRIPTION
		" Number of frames clipped in the transmit routine "
	::= { wfHssiEntry 26 }

wfHssiRxReplenMisses OBJECT-TYPE
	SYNTAX	Counter
	ACCESS	read-only
	STATUS	mandatory
	DESCRIPTION
		" Number of failed attempts by the line driver to aquire a packet buffer "
	::= { wfHssiEntry 27 }

wfHssiLastRxErrorCtrl OBJECT-TYPE
	SYNTAX	INTEGER
	ACCESS	read-only
	STATUS	mandatory
	DESCRIPTION
		" Last errored receive descriptor's control field "
	::= { wfHssiEntry 28 }

wfHssiRxCrcErrors OBJECT-TYPE
	SYNTAX	Counter
	ACCESS	read-only
	STATUS	mandatory
	DESCRIPTION
		" Number of frames received with CRC errors "
	::= { wfHssiEntry 29 }

wfHssiRxOverruns OBJECT-TYPE
	SYNTAX	Counter
	ACCESS	read-only
	STATUS	mandatory
	DESCRIPTION
		" Number of frames received with fifo overrun errors "
	::= { wfHssiEntry 30 }

wfHssiRxAborts OBJECT-TYPE
	SYNTAX	Counter
	ACCESS	read-only
	STATUS	mandatory
	DESCRIPTION
		" Number of frames received with abort status "
	::= { wfHssiEntry 31 }

wfHssiLastTxErrorCtrl OBJECT-TYPE
	SYNTAX	INTEGER
	ACCESS	read-only
	STATUS	mandatory
	DESCRIPTION
		" Last errored transmit descriptor's control field "
	::= { wfHssiEntry 32 }

wfHssiTxAborts OBJECT-TYPE
	SYNTAX	Counter
	ACCESS	read-only
	STATUS	mandatory
	DESCRIPTION
		" Number of transmit frames with internal abort errors "
	::= { wfHssiEntry 33 }

wfHssiTxUnderruns OBJECT-TYPE
	SYNTAX	Counter
	ACCESS	read-only
	STATUS	mandatory
	DESCRIPTION
		" Number of transmit frames aborted with underrun errors "
	::= { wfHssiEntry 34 }

wfHssiRxRingErrors OBJECT-TYPE
	SYNTAX	Counter
	ACCESS	read-only
	STATUS	mandatory
	DESCRIPTION
		" Number of receive ring error events "
	::= { wfHssiEntry 35 }

wfHssiLastRxRingState OBJECT-TYPE
	SYNTAX	INTEGER
	ACCESS	read-only
	STATUS	mandatory
	DESCRIPTION
		" Last 8 bit value from the recv ring state register "
	::= { wfHssiEntry 36 }

wfHssiRxRingOverruns OBJECT-TYPE
	SYNTAX	Counter
	ACCESS	read-only
	STATUS	mandatory
	DESCRIPTION
		" Number of receive ring overrun events "
	::= { wfHssiEntry 37 }

wfHssiTxRingErrors OBJECT-TYPE
	SYNTAX	Counter
	ACCESS	read-only
	STATUS	mandatory
	DESCRIPTION
		" Number of transmit ring error events "
	::= { wfHssiEntry 38 }

wfHssiLastTxRingState OBJECT-TYPE
	SYNTAX	INTEGER
	ACCESS	read-only
	STATUS	mandatory
	DESCRIPTION
		" Last 8 bit value from the transmit ring state register "
	::= { wfHssiEntry 39 }

wfHssiPortOpErrors OBJECT-TYPE
	SYNTAX	Counter
	ACCESS	read-only
	STATUS	mandatory
	DESCRIPTION
		" Number of port operation error events "
	::= { wfHssiEntry 40 }

wfHssiInternOpErrors OBJECT-TYPE
	SYNTAX	Counter
	ACCESS	read-only
	STATUS	mandatory
	DESCRIPTION
		" Number of internal operation error events "
	::= { wfHssiEntry 41 }

wfHssiHostErrors OBJECT-TYPE
	SYNTAX	Counter
	ACCESS	read-only
	STATUS	mandatory
	DESCRIPTION
		" Number of parity errs on host accesses to directly accessable registers. "
	::= { wfHssiEntry 42 }

wfHssiRxProcessings OBJECT-TYPE
	SYNTAX	Counter
	ACCESS	read-only
	STATUS	mandatory
	DESCRIPTION
		" Number of receive frame processings (RINT) "
	::= { wfHssiEntry 43 }

wfHssiTxProcessings OBJECT-TYPE
	SYNTAX	Counter
	ACCESS	read-only
	STATUS	mandatory
	DESCRIPTION
		" Number of transmit processings, invokations of transmit routine "
	::= { wfHssiEntry 44 }

wfHssiTxCmplProcessings OBJECT-TYPE
	SYNTAX	Counter
	ACCESS	read-only
	STATUS	mandatory
	DESCRIPTION
		" Number of transmit complete processings (TINT) "
	::= { wfHssiEntry 45 }

wfHssiIntrProcessings OBJECT-TYPE
	SYNTAX	Counter
	ACCESS	read-only
	STATUS	mandatory
	DESCRIPTION
		" Number of Interrupt processings,  invokations of intr routine "
	::= { wfHssiEntry 46 }

wfHssiBoflNum OBJECT-TYPE
	SYNTAX	INTEGER {
		minimum(1),
		maximum(127),
		default(5)
	}
	ACCESS	read-write
	STATUS	mandatory
	DESCRIPTION
		" Number of breath of life packets per breath of life "
	DEFVAL	{ default }
	::= { wfHssiEntry 47 }

wfHssiBoflLen OBJECT-TYPE
	SYNTAX	INTEGER {
		minimum(22),
		maximum(4450),
		default(100)
	}
	ACCESS	read-write
	STATUS	mandatory
	DESCRIPTION
		" breath of life packet length "
	DEFVAL	{ default }
	::= { wfHssiEntry 48 }

wfHssiRxBufferLength OBJECT-TYPE
	SYNTAX	INTEGER {
		length4k(64),
		length8k(128)
	}
	ACCESS	read-write
	STATUS	mandatory
	DESCRIPTION
		" Performance tunning parameter controls Receive buffer size. "
	DEFVAL	{ length4k }
	::= { wfHssiEntry 49 }

wfHssiMemPageLength OBJECT-TYPE
	SYNTAX	INTEGER {
		length32(1),
		length256(3)
	}
	ACCESS	read-write
	STATUS	mandatory
	DESCRIPTION
		" Performance tunning parameter controls device memory access burst length. "
	DEFVAL	{ length32 }
	::= { wfHssiEntry 50 }

wfHssiRxRingLength OBJECT-TYPE
	SYNTAX	INTEGER {
		minimum(1),
		maximum(255),
		default(64)
	}
	ACCESS	read-write
	STATUS	mandatory
	DESCRIPTION
		" Performance tunning parameter controls the receive queue length.
		   Receive Queue Length, values larger than the compiled ring size
		   are truncated to the compiled ring size.
		"
	DEFVAL	{ default }
	::= { wfHssiEntry 51 }

wfHssiTxRingLength OBJECT-TYPE
	SYNTAX	INTEGER {
		minimum(1),
		maximum(255),
		default(127)
	}
	ACCESS	read-write
	STATUS	mandatory
	DESCRIPTION
		" Performance tunning parameter controls the transmit queue length.
		   Transmit Queue Length, values larger than the compiled ring size
		   are truncated to the compiled ring size.
		"
	DEFVAL	{ default }
	::= { wfHssiEntry 52 }

wfHssiRxFifoWatermark OBJECT-TYPE
	SYNTAX	INTEGER {
		minimum(2),
		maximum(255),
		default(2)
	}
	ACCESS	read-write
	STATUS	mandatory
	DESCRIPTION
		" Performance tunning parameter controls the receive watermark. "
	DEFVAL	{ default }
	::= { wfHssiEntry 53 }

wfHssiTxFifoWatermark OBJECT-TYPE
	SYNTAX	INTEGER {
		minimum(2),
		maximum(255),
		default(16)
	}
	ACCESS	read-write
	STATUS	mandatory
	DESCRIPTION
		" Performance tunning parameter controls the transmit watermark. "
	DEFVAL	{ default }
	::= { wfHssiEntry 54 }

wfHssiMaxRxMemory OBJECT-TYPE
	SYNTAX	INTEGER {
		minimum(1),
		maximum(255),
		default(1)
	}
	ACCESS	read-write
	STATUS	mandatory
	DESCRIPTION
		" Performance tunning parameter controls fifo area allowed for receive. "
	DEFVAL	{ default }
	::= { wfHssiEntry 55 }

wfHssiLinkInterface OBJECT-TYPE
	SYNTAX	INTEGER {
		default(1),
		ace25(2),
		ace32(3)
	}
	ACCESS	read-write
	STATUS	mandatory
	DESCRIPTION
		" Only for DEBUG. "
	DEFVAL	{ default }
	::= { wfHssiEntry 56 }

wfHssiTurboBofl OBJECT-TYPE
	SYNTAX	INTEGER {
		enabled(1),
		disabled(2)
	}
	ACCESS	read-write
	STATUS	mandatory
	DESCRIPTION
		" Only for DEBUG, Turbo breath of life parameter "
	DEFVAL	{ disabled }
	::= { wfHssiEntry 57 }

wfHwfTable OBJECT-TYPE
	SYNTAX	SEQUENCE OF WfHwfEntry
	ACCESS	not-accessible
	STATUS	mandatory
	DESCRIPTION
		" The following table will contain information about a collection of
		   Hardware Filter (HWF) driver records.
		   Only one HWF driver may be spawned, by the loader, on a given slot.
		   Hence, only the slot number is used as the instance identifier into
		   the table. "
	::= { wfHwFGroup 1 }

wfHwfEntry OBJECT-TYPE
	SYNTAX	WfHwfEntry
	ACCESS	not-accessible
	STATUS	mandatory
	DESCRIPTION
		" Slot number used as instance identifier. "
	INDEX	{ wfHwfSlot }
	::= { wfHwfTable 1 }

WfHwfEntry ::= SEQUENCE {
	wfHwfDelete
		INTEGER,
	wfHwfEnable
		INTEGER,
	wfHwfState
		INTEGER,
	wfHwfSlot
		INTEGER,
	wfHwfAvailableLines
		INTEGER
}

wfHwfDelete OBJECT-TYPE
	SYNTAX	INTEGER {
		created(1),
		deleted(2)
	}
	ACCESS	read-write
	STATUS	mandatory
	DESCRIPTION
		" Create/delete parameter. "
	DEFVAL	{ created }
	::= { wfHwfEntry 1 }

wfHwfEnable OBJECT-TYPE
	SYNTAX	INTEGER {
		enabled(1),
		disabled(2)
	}
	ACCESS	read-write
	STATUS	mandatory
	DESCRIPTION
		" Enable/disable parameter. "
	DEFVAL	{ enabled }
	::= { wfHwfEntry 2 }

wfHwfState OBJECT-TYPE
	SYNTAX	INTEGER {
		up(1),
		down(2),
		init(3),
		notpresent(4)
	}
	ACCESS	read-only
	STATUS	mandatory
	DESCRIPTION
		" Driver state variable. "
	DEFVAL	{ notpresent }
	::= { wfHwfEntry 3 }

wfHwfSlot OBJECT-TYPE
	SYNTAX	INTEGER {
		minimum(1),
		maximum(14)
	}
	ACCESS	read-only
	STATUS	mandatory
	DESCRIPTION
		" Slot number -- instance ID. "
	::= { wfHwfEntry 4 }

wfHwfAvailableLines OBJECT-TYPE
	SYNTAX	INTEGER
	ACCESS	read-only
	STATUS	mandatory
	DESCRIPTION
		" Number of available lines on module. "
	::= { wfHwfEntry 5 }

wfHwfLineTable OBJECT-TYPE
	SYNTAX	SEQUENCE OF WfHwfLineEntry
	ACCESS	not-accessible
	STATUS	mandatory
	DESCRIPTION
		" The following table will contain information about a collection of
		   Hardware Filter (HWF) line records. "
	::= { wfHwFGroup 2 }

wfHwfLineEntry OBJECT-TYPE
	SYNTAX	WfHwfLineEntry
	ACCESS	not-accessible
	STATUS	mandatory
	DESCRIPTION
		" Slot number and line number used as instance identifier. "
	INDEX	{ wfHwfLineSlot,
		wfHwfLineNumber }
	::= { wfHwfLineTable 1 }

WfHwfLineEntry ::= SEQUENCE {
	wfHwfLineState
		INTEGER,
	wfHwfLineSlot
		INTEGER,
	wfHwfLineNumber
		INTEGER,
	wfHwfLineCct
		INTEGER,
	wfHwfLineCapableMaxTblSize
		INTEGER,
	wfHwfLineCurrentTblSize
		INTEGER,
	wfHwfLineCurrentUsedEntries
		INTEGER,
	wfHwfLineDroppedFrames
		INTEGER
}

wfHwfLineState OBJECT-TYPE
	SYNTAX	INTEGER {
		operational(1),
		disabled(2),
		full(3)
	}
	ACCESS	read-only
	STATUS	mandatory
	DESCRIPTION
		" State of filtering hardware on a per line basis. "
	DEFVAL	{ disabled }
	::= { wfHwfLineEntry 1 }

wfHwfLineSlot OBJECT-TYPE
	SYNTAX	INTEGER
	ACCESS	read-only
	STATUS	mandatory
	DESCRIPTION
		" Slot number -- instance ID. "
	::= { wfHwfLineEntry 2 }

wfHwfLineNumber OBJECT-TYPE
	SYNTAX	INTEGER {
		one(1),
		two(2),
		three(3),
		four(4)
	}
	ACCESS	read-only
	STATUS	mandatory
	DESCRIPTION
		" Line number -- instance ID. "
	::= { wfHwfLineEntry 3 }

wfHwfLineCct OBJECT-TYPE
	SYNTAX	INTEGER
	ACCESS	read-only
	STATUS	mandatory
	DESCRIPTION
		" Circuit number associated with a line. "
	::= { wfHwfLineEntry 4 }

wfHwfLineCapableMaxTblSize OBJECT-TYPE
	SYNTAX	INTEGER
	ACCESS	read-only
	STATUS	mandatory
	DESCRIPTION
		" This attribute specifies the maximum number of table entries
		   capable of being used by a line based upon actual hardware
		   filter devices present and available. "
	::= { wfHwfLineEntry 5 }

wfHwfLineCurrentTblSize OBJECT-TYPE
	SYNTAX	INTEGER
	ACCESS	read-only
	STATUS	mandatory
	DESCRIPTION
		" Current capacity of the hardware filter table. Hardware filter
		   table resources are dynamically allocated (in increments of 256)
		   on an as-needed basis up to the available table size. "
	::= { wfHwfLineEntry 6 }

wfHwfLineCurrentUsedEntries OBJECT-TYPE
	SYNTAX	INTEGER
	ACCESS	read-only
	STATUS	mandatory
	DESCRIPTION
		" Number of hardware filter table entries used. "
	::= { wfHwfLineEntry 7 }

wfHwfLineDroppedFrames OBJECT-TYPE
	SYNTAX	INTEGER
	ACCESS	read-only
	STATUS	mandatory
	DESCRIPTION
		" Number of frames dropped because of hardware filter match. "
	::= { wfHwfLineEntry 8 }

wfMod		OBJECT IDENTIFIER ::= { wfHardwareConfig 3 }

wfModState OBJECT-TYPE
	SYNTAX	INTEGER {
		init(1)
	}
	ACCESS	not-accessible
	STATUS	mandatory
	DESCRIPTION
		" State of this record "
	::= { wfMod 1 }

wfModSlot OBJECT-TYPE
	SYNTAX	INTEGER
	ACCESS	not-accessible
	STATUS	mandatory
	DESCRIPTION
		" Instance of this record "
	::= { wfMod 2 }

wfModIdOpt OBJECT-TYPE
	SYNTAX	INTEGER
	ACCESS	not-accessible
	STATUS	mandatory
	DESCRIPTION
		" actual module ID and Option "
	::= { wfMod 3 }

wfModRev OBJECT-TYPE
	SYNTAX	INTEGER
	ACCESS	not-accessible
	STATUS	mandatory
	DESCRIPTION
		" actual module Revision "
	::= { wfMod 4 }

wfModProm OBJECT-TYPE
	SYNTAX	INTEGER
	ACCESS	not-accessible
	STATUS	mandatory
	DESCRIPTION
		"  module PROM "
	::= { wfMod 5 }

wfModMidr OBJECT-TYPE
	SYNTAX	INTEGER
	ACCESS	not-accessible
	STATUS	mandatory
	DESCRIPTION
		"  module ID register "
	::= { wfMod 6 }

wfModMled OBJECT-TYPE
	SYNTAX	INTEGER
	ACCESS	not-accessible
	STATUS	mandatory
	DESCRIPTION
		"  module LED register "
	::= { wfMod 7 }

wfModMisr OBJECT-TYPE
	SYNTAX	INTEGER
	ACCESS	not-accessible
	STATUS	mandatory
	DESCRIPTION
		"  module MISR register "
	::= { wfMod 8 }

wfModSnprom OBJECT-TYPE
	SYNTAX	INTEGER
	ACCESS	not-accessible
	STATUS	mandatory
	DESCRIPTION
		"  module SNPROM "
	::= { wfMod 9 }

wfModMadr1 OBJECT-TYPE
	SYNTAX	OCTET STRING
	ACCESS	not-accessible
	STATUS	mandatory
	DESCRIPTION
		" SNPROM MAC address connector 1 "
	::= { wfMod 10 }

wfModMadr2 OBJECT-TYPE
	SYNTAX	OCTET STRING
	ACCESS	not-accessible
	STATUS	mandatory
	DESCRIPTION
		" SNPROM MAC address connector 2 "
	::= { wfMod 11 }

wfModMadr3 OBJECT-TYPE
	SYNTAX	OCTET STRING
	ACCESS	not-accessible
	STATUS	mandatory
	DESCRIPTION
		" SNPROM MAC address connector 3 "
	::= { wfMod 12 }

wfModMadr4 OBJECT-TYPE
	SYNTAX	OCTET STRING
	ACCESS	not-accessible
	STATUS	mandatory
	DESCRIPTION
		" SNPROM MAC address connector 4 "
	::= { wfMod 13 }

wfModLance1 OBJECT-TYPE
	SYNTAX	INTEGER
	ACCESS	not-accessible
	STATUS	mandatory
	DESCRIPTION
		"  LANCE line 1 "
	::= { wfMod 14 }

wfModLance2 OBJECT-TYPE
	SYNTAX	INTEGER
	ACCESS	not-accessible
	STATUS	mandatory
	DESCRIPTION
		"  LANCE line 2 "
	::= { wfMod 15 }

wfModMk50251 OBJECT-TYPE
	SYNTAX	INTEGER
	ACCESS	not-accessible
	STATUS	mandatory
	DESCRIPTION
		"  MK5025 line 1 "
	::= { wfMod 16 }

wfModMk50252 OBJECT-TYPE
	SYNTAX	INTEGER
	ACCESS	not-accessible
	STATUS	mandatory
	DESCRIPTION
		"  MK5025 line 2 "
	::= { wfMod 17 }

wfModMk50253 OBJECT-TYPE
	SYNTAX	INTEGER
	ACCESS	not-accessible
	STATUS	mandatory
	DESCRIPTION
		"  MK5025 line 3 "
	::= { wfMod 18 }

wfModMk50254 OBJECT-TYPE
	SYNTAX	INTEGER
	ACCESS	not-accessible
	STATUS	mandatory
	DESCRIPTION
		"  MK5025 line 4 "
	::= { wfMod 19 }

wfModSicr OBJECT-TYPE
	SYNTAX	INTEGER
	ACCESS	not-accessible
	STATUS	mandatory
	DESCRIPTION
		"  SYNC interface control register "
	::= { wfMod 20 }

wfModSbrr OBJECT-TYPE
	SYNTAX	INTEGER
	ACCESS	not-accessible
	STATUS	mandatory
	DESCRIPTION
		"  SYNC baudrate register "
	::= { wfMod 21 }

wfMod8530 OBJECT-TYPE
	SYNTAX	INTEGER
	ACCESS	not-accessible
	STATUS	mandatory
	DESCRIPTION
		"  8530 DUART "
	::= { wfMod 22 }

wfModCar OBJECT-TYPE
	SYNTAX	INTEGER
	ACCESS	not-accessible
	STATUS	mandatory
	DESCRIPTION
		"  CAM assembly register "
	::= { wfMod 23 }

wfModDefaA OBJECT-TYPE
	SYNTAX	INTEGER
	ACCESS	not-accessible
	STATUS	mandatory
	DESCRIPTION
		"  DEFA A chip "
	::= { wfMod 24 }

wfModCamALock OBJECT-TYPE
	SYNTAX	INTEGER
	ACCESS	not-accessible
	STATUS	mandatory
	DESCRIPTION
		"  CAM A lock "
	::= { wfMod 25 }

wfModCamAUnlock OBJECT-TYPE
	SYNTAX	INTEGER
	ACCESS	not-accessible
	STATUS	mandatory
	DESCRIPTION
		"  CAM A unlock "
	::= { wfMod 26 }

wfModDefaB OBJECT-TYPE
	SYNTAX	INTEGER
	ACCESS	not-accessible
	STATUS	mandatory
	DESCRIPTION
		"  DEFA B chip "
	::= { wfMod 27 }

wfModCamBLock OBJECT-TYPE
	SYNTAX	INTEGER
	ACCESS	not-accessible
	STATUS	mandatory
	DESCRIPTION
		"  CAM B lock "
	::= { wfMod 28 }

wfModCamBUnlock OBJECT-TYPE
	SYNTAX	INTEGER
	ACCESS	not-accessible
	STATUS	mandatory
	DESCRIPTION
		"  CAM B unlock "
	::= { wfMod 29 }

wfModIlacc1 OBJECT-TYPE
	SYNTAX	INTEGER
	ACCESS	not-accessible
	STATUS	mandatory
	DESCRIPTION
		"  ILACC line 1 "
	::= { wfMod 30 }

wfModIlacc2 OBJECT-TYPE
	SYNTAX	INTEGER
	ACCESS	not-accessible
	STATUS	mandatory
	DESCRIPTION
		"  ILACC line 2 "
	::= { wfMod 31 }

wfModIlacc3 OBJECT-TYPE
	SYNTAX	INTEGER
	ACCESS	not-accessible
	STATUS	mandatory
	DESCRIPTION
		"  ILACC line 3 "
	::= { wfMod 32 }

wfModIlacc4 OBJECT-TYPE
	SYNTAX	INTEGER
	ACCESS	not-accessible
	STATUS	mandatory
	DESCRIPTION
		"  ILACC line 4 "
	::= { wfMod 33 }

wfModTms3801 OBJECT-TYPE
	SYNTAX	INTEGER
	ACCESS	not-accessible
	STATUS	mandatory
	DESCRIPTION
		"  TOKEN ring chip line 1 "
	::= { wfMod 34 }

wfModTms3802 OBJECT-TYPE
	SYNTAX	INTEGER
	ACCESS	not-accessible
	STATUS	mandatory
	DESCRIPTION
		"  TOKEN ring chip line 2 "
	::= { wfMod 35 }

wfModTocr OBJECT-TYPE
	SYNTAX	INTEGER
	ACCESS	not-accessible
	STATUS	mandatory
	DESCRIPTION
		"  TOKEN control register "
	::= { wfMod 36 }

wfModTsra OBJECT-TYPE
	SYNTAX	INTEGER
	ACCESS	not-accessible
	STATUS	mandatory
	DESCRIPTION
		"  TOKEN source route accelerator "
	::= { wfMod 37 }

wfModMuxram1 OBJECT-TYPE
	SYNTAX	INTEGER
	ACCESS	not-accessible
	STATUS	mandatory
	DESCRIPTION
		"  T1 mux RAM active "
	::= { wfMod 38 }

wfModMuxram2 OBJECT-TYPE
	SYNTAX	INTEGER
	ACCESS	not-accessible
	STATUS	mandatory
	DESCRIPTION
		"  T1 mux RAM inactive "
	::= { wfMod 39 }

wfModTicr OBJECT-TYPE
	SYNTAX	INTEGER
	ACCESS	not-accessible
	STATUS	mandatory
	DESCRIPTION
		"  T1 interface control register "
	::= { wfMod 40 }

wfModFramer1 OBJECT-TYPE
	SYNTAX	INTEGER
	ACCESS	not-accessible
	STATUS	mandatory
	DESCRIPTION
		"  T1 framer line 1 "
	::= { wfMod 41 }

wfModFramer2 OBJECT-TYPE
	SYNTAX	INTEGER
	ACCESS	not-accessible
	STATUS	mandatory
	DESCRIPTION
		"  T1 framer line 2 "
	::= { wfMod 42 }

wfModFsi1 OBJECT-TYPE
	SYNTAX	INTEGER
	ACCESS	not-accessible
	STATUS	mandatory
	DESCRIPTION
		"  FDDI FSI line 1 "
	::= { wfMod 43 }

wfModMac1 OBJECT-TYPE
	SYNTAX	INTEGER
	ACCESS	not-accessible
	STATUS	mandatory
	DESCRIPTION
		"  FDDI MAC line 1 "
	::= { wfMod 44 }

wfModElmA1 OBJECT-TYPE
	SYNTAX	INTEGER
	ACCESS	not-accessible
	STATUS	mandatory
	DESCRIPTION
		"  FDDI ELM A line 1 "
	::= { wfMod 45 }

wfModElmB1 OBJECT-TYPE
	SYNTAX	INTEGER
	ACCESS	not-accessible
	STATUS	mandatory
	DESCRIPTION
		"  FDDI ELM B line 1 "
	::= { wfMod 46 }

wfModMcr1 OBJECT-TYPE
	SYNTAX	INTEGER
	ACCESS	not-accessible
	STATUS	mandatory
	DESCRIPTION
		"  FDDI Module control register line 1 "
	::= { wfMod 47 }

wfModHssiFsi1 OBJECT-TYPE
	SYNTAX	INTEGER
	ACCESS	not-accessible
	STATUS	mandatory
	DESCRIPTION
		"  HSSI FSI line 1 "
	::= { wfMod 48 }

wfModHssiFsi2 OBJECT-TYPE
	SYNTAX	INTEGER
	ACCESS	not-accessible
	STATUS	mandatory
	DESCRIPTION
		"  HSSI FSI line 2 "
	::= { wfMod 49 }

wfModHssiUga1 OBJECT-TYPE
	SYNTAX	INTEGER
	ACCESS	not-accessible
	STATUS	mandatory
	DESCRIPTION
		"  HSSI UGA-330-2 line 1 "
	::= { wfMod 50 }

wfModHssiUga2 OBJECT-TYPE
	SYNTAX	INTEGER
	ACCESS	not-accessible
	STATUS	mandatory
	DESCRIPTION
		"  HSSI UGA-330-2 line 2 "
	::= { wfMod 51 }

wfModHicr OBJECT-TYPE
	SYNTAX	INTEGER
	ACCESS	not-accessible
	STATUS	mandatory
	DESCRIPTION
		"  HSSI Control Register address "
	::= { wfMod 52 }

wfModHicrData OBJECT-TYPE
	SYNTAX	INTEGER
	ACCESS	not-accessible
	STATUS	mandatory
	DESCRIPTION
		"  HSSI Last value written to the HICR "
	::= { wfMod 53 }

wfModHlsr OBJECT-TYPE
	SYNTAX	INTEGER
	ACCESS	not-accessible
	STATUS	mandatory
	DESCRIPTION
		"  HSSI Line Status Register address "
	::= { wfMod 54 }

wfModHlsrData OBJECT-TYPE
	SYNTAX	INTEGER
	ACCESS	not-accessible
	STATUS	mandatory
	DESCRIPTION
		"  HSSI Last value read from HLSR "
	::= { wfMod 55 }

wfIf		OBJECT IDENTIFIER ::= { wfIfGroup 1 }

wfIfNumber OBJECT-TYPE
	SYNTAX	INTEGER
	ACCESS	read-only
	STATUS	mandatory
	DESCRIPTION
		" Total number of possible active interfaces "
	::= { wfIf 1 }

wfIfTable OBJECT-TYPE
	SYNTAX	SEQUENCE OF WfIfEntry
	ACCESS	not-accessible
	STATUS	mandatory
	DESCRIPTION
		" A table containing active interfaces "
	::= { wfIfGroup 2 }

wfIfEntry OBJECT-TYPE
	SYNTAX	WfIfEntry
	ACCESS	not-accessible
	STATUS	mandatory
	DESCRIPTION
		" A particular interface "
	INDEX	{ wfIfIndex }
	::= { wfIfTable 1 }

WfIfEntry ::= SEQUENCE {
	wfIfIndex
		INTEGER,
	wfIfDescr
		DisplayString,
	wfIfType
		INTEGER,
	wfIfMtu
		INTEGER,
	wfIfSpeed
		Gauge,
	wfIfPhysAddress
		OCTET STRING,
	wfIfAdminStatus
		INTEGER,
	wfIfOperStatus
		INTEGER,
	wfIfLastChange
		TimeTicks,
	wfIfInOctets
		Counter,
	wfIfInUcastPkts
		Counter,
	wfIfInNUCastPkts
		Counter,
	wfIfInDiscards
		Counter,
	wfIfInErrors
		Counter,
	wfIfInUnknownProtos
		Counter,
	wfIfOutOctets
		Counter,
	wfIfOutUcastPkts
		Counter,
	wfIfOutNUcastPkts
		Counter,
	wfIfOutDiscards
		Counter,
	wfIfOutErrors
		Counter,
	wfIfOutQLen
		Gauge,
	wfIfSpecific
		OBJECT IDENTIFIER
}

wfIfIndex OBJECT-TYPE
	SYNTAX	INTEGER
	ACCESS	read-only
	STATUS	mandatory
	DESCRIPTION
		" Corresponds to same attribute of MIB-II's ifTable "
	::= { wfIfEntry 1 }

wfIfDescr OBJECT-TYPE
	SYNTAX	DisplayString
	ACCESS	read-only
	STATUS	mandatory
	DESCRIPTION
		" Corresponds to same attribute of MIB-II's ifTable "
	::= { wfIfEntry 2 }

wfIfType OBJECT-TYPE
	SYNTAX	INTEGER
	ACCESS	read-only
	STATUS	mandatory
	DESCRIPTION
		" Corresponds to same attribute of MIB-II's ifTable "
	::= { wfIfEntry 3 }

wfIfMtu OBJECT-TYPE
	SYNTAX	INTEGER
	ACCESS	read-only
	STATUS	mandatory
	DESCRIPTION
		" Corresponds to same attribute of MIB-II's ifTable "
	::= { wfIfEntry 4 }

wfIfSpeed OBJECT-TYPE
	SYNTAX	Gauge
	ACCESS	read-only
	STATUS	mandatory
	DESCRIPTION
		" Corresponds to same attribute of MIB-II's ifTable "
	::= { wfIfEntry 5 }

wfIfPhysAddress OBJECT-TYPE
	SYNTAX	OCTET STRING
	ACCESS	read-only
	STATUS	mandatory
	DESCRIPTION
		" Corresponds to same attribute of MIB-II's ifTable "
	::= { wfIfEntry 6 }

wfIfAdminStatus OBJECT-TYPE
	SYNTAX	INTEGER
	ACCESS	read-only
	STATUS	mandatory
	DESCRIPTION
		" Corresponds to same attribute of MIB-II's ifTable "
	::= { wfIfEntry 7 }

wfIfOperStatus OBJECT-TYPE
	SYNTAX	INTEGER
	ACCESS	read-only
	STATUS	mandatory
	DESCRIPTION
		" Corresponds to same attribute of MIB-II's ifTable "
	::= { wfIfEntry 8 }

wfIfLastChange OBJECT-TYPE
	SYNTAX	TimeTicks
	ACCESS	read-only
	STATUS	mandatory
	DESCRIPTION
		" Corresponds to same attribute of MIB-II's ifTable "
	::= { wfIfEntry 9 }

wfIfInOctets OBJECT-TYPE
	SYNTAX	Counter
	ACCESS	read-only
	STATUS	mandatory
	DESCRIPTION
		" Corresponds to same attribute of MIB-II's ifTable "
	::= { wfIfEntry 10 }

wfIfInUcastPkts OBJECT-TYPE
	SYNTAX	Counter
	ACCESS	read-only
	STATUS	mandatory
	DESCRIPTION
		" Corresponds to same attribute of MIB-II's ifTable "
	::= { wfIfEntry 11 }

wfIfInNUCastPkts OBJECT-TYPE
	SYNTAX	Counter
	ACCESS	read-only
	STATUS	mandatory
	DESCRIPTION
		" Corresponds to same attribute of MIB-II's ifTable "
	::= { wfIfEntry 12 }

wfIfInDiscards OBJECT-TYPE
	SYNTAX	Counter
	ACCESS	read-only
	STATUS	mandatory
	DESCRIPTION
		" Corresponds to same attribute of MIB-II's ifTable "
	::= { wfIfEntry 13 }

wfIfInErrors OBJECT-TYPE
	SYNTAX	Counter
	ACCESS	read-only
	STATUS	mandatory
	DESCRIPTION
		" Corresponds to same attribute of MIB-II's ifTable "
	::= { wfIfEntry 14 }

wfIfInUnknownProtos OBJECT-TYPE
	SYNTAX	Counter
	ACCESS	read-only
	STATUS	mandatory
	DESCRIPTION
		" Corresponds to same attribute of MIB-II's ifTable "
	::= { wfIfEntry 15 }

wfIfOutOctets OBJECT-TYPE
	SYNTAX	Counter
	ACCESS	read-only
	STATUS	mandatory
	DESCRIPTION
		" Corresponds to same attribute of MIB-II's ifTable "
	::= { wfIfEntry 16 }

wfIfOutUcastPkts OBJECT-TYPE
	SYNTAX	Counter
	ACCESS	read-only
	STATUS	mandatory
	DESCRIPTION
		" Corresponds to same attribute of MIB-II's ifTable "
	::= { wfIfEntry 17 }

wfIfOutNUcastPkts OBJECT-TYPE
	SYNTAX	Counter
	ACCESS	read-only
	STATUS	mandatory
	DESCRIPTION
		" Corresponds to same attribute of MIB-II's ifTable "
	::= { wfIfEntry 18 }

wfIfOutDiscards OBJECT-TYPE
	SYNTAX	Counter
	ACCESS	read-only
	STATUS	mandatory
	DESCRIPTION
		" Corresponds to same attribute of MIB-II's ifTable "
	::= { wfIfEntry 19 }

wfIfOutErrors OBJECT-TYPE
	SYNTAX	Counter
	ACCESS	read-only
	STATUS	mandatory
	DESCRIPTION
		" Corresponds to same attribute of MIB-II's ifTable "
	::= { wfIfEntry 20 }

wfIfOutQLen OBJECT-TYPE
	SYNTAX	Gauge
	ACCESS	read-only
	STATUS	mandatory
	DESCRIPTION
		" Corresponds to same attribute of MIB-II's ifTable "
	::= { wfIfEntry 21 }

wfIfSpecific OBJECT-TYPE
	SYNTAX	OBJECT IDENTIFIER
	ACCESS	read-only
	STATUS	mandatory
	DESCRIPTION
		" Corresponds to same attribute of MIB-II's ifTable "
	::= { wfIfEntry 22 }

wfIpBase	OBJECT IDENTIFIER ::= { wfIpGroup 1 }

wfIpBaseCreate OBJECT-TYPE
	SYNTAX	INTEGER {
		created(1),
		deleted(2)
	}
	ACCESS	read-write
	STATUS	mandatory
	DESCRIPTION
		"Create/Delete parameter. Default is created.
		     Users perform a set operation on this
		     object in order to create/delete IP."
	DEFVAL	{ created }
	::= { wfIpBase 1 }

wfIpBaseEnable OBJECT-TYPE
	SYNTAX	INTEGER {
		enabled(1),
		disabled(2)
	}
	ACCESS	read-write
	STATUS	mandatory
	DESCRIPTION
		"Enable/Disable parameter. Default is enabled.
		     Users perform a set operation on this
		     object in order to enable/disable IP."
	DEFVAL	{ enabled }
	::= { wfIpBase 2 }

wfIpBaseState OBJECT-TYPE
	SYNTAX	INTEGER {
		up(1),
		down(2),
		init(3),
		notpres(4)
	}
	ACCESS	read-only
	STATUS	mandatory
	DESCRIPTION
		"The current state of the entire IP."
	DEFVAL	{ notpres }
	::= { wfIpBase 3 }

wfIpBaseForwarding OBJECT-TYPE
	SYNTAX	INTEGER {
		forwarding(1),
		notforwarding(2)
	}
	ACCESS	read-write
	STATUS	mandatory
	DESCRIPTION
		"The indication of whether this entity is acting
		     as an IP gateway in respect to the forwarding of
		     datagrams received by, but not addressed to, this
		     entity.  IP gateways forward datagrams.  IP hosts
		     do not (except those source-routed via the host).
		     Note that for some managed nodes, this object may
		     take on only a subset of the values possible.
		     Accordingly, it is appropriate for an agent to
		     return a `badValue' response if a management
		     station attempts to change this object to an
		     inappropriate value."
	DEFVAL	{ forwarding }
	::= { wfIpBase 4 }

wfIpBaseDefaultTTL OBJECT-TYPE
	SYNTAX	INTEGER {
		default(30),
		ttlmax(255)
	}
	ACCESS	read-write
	STATUS	mandatory
	DESCRIPTION
		"The default value inserted into the Time-To-Live
		     field of the IP header of datagrams originated at
		     this entity, whenever a TTL value is not supplied
		     by the transport layer protocol. "
	DEFVAL	{ default }
	::= { wfIpBase 5 }

wfIpBaseRipDiameter OBJECT-TYPE
	SYNTAX	INTEGER {
		dflt(15),
		maximum(15)
	}
	ACCESS	read-write
	STATUS	mandatory
	DESCRIPTION
		" The Diameter of the RIP network.  1 less than 'infinity' "
	DEFVAL	{ dflt }
	::= { wfIpBase 6 }

wfIpBaseRtEntryTable OBJECT-TYPE
	SYNTAX	SEQUENCE OF WfIpBaseRtEntry
	ACCESS	not-accessible
	STATUS	mandatory
	DESCRIPTION
		" The list of elements in IP's routing table "
	::= { wfIpGroup 2 }

wfIpBaseRtEntry OBJECT-TYPE
	SYNTAX	WfIpBaseRtEntry
	ACCESS	not-accessible
	STATUS	mandatory
	DESCRIPTION
		" A description of a route "
	INDEX	{ wfIpBaseRouteDest }
	::= { wfIpBaseRtEntryTable 1 }

WfIpBaseRtEntry ::= SEQUENCE {
	wfIpBaseRouteDest
		IpAddress,
	wfIpBaseRouteIfIndex
		INTEGER,
	wfIpBaseRouteMetric1
		INTEGER,
	wfIpBaseRouteMetric2
		INTEGER,
	wfIpBaseRouteMetric3
		INTEGER,
	wfIpBaseRouteMetric4
		INTEGER,
	wfIpBaseRouteNextHop
		IpAddress,
	wfIpBaseRouteType
		INTEGER,
	wfIpBaseRouteProto
		INTEGER,
	wfIpBaseRouteAge
		INTEGER,
	wfIpBaseRouteMask
		IpAddress,
	wfIpBaseRouteMetric5
		INTEGER,
	wfIpBaseRouteInfo
		OBJECT IDENTIFIER
}

wfIpBaseRouteDest OBJECT-TYPE
	SYNTAX	IpAddress
	ACCESS	read-only
	STATUS	mandatory
	DESCRIPTION
		" The destination IP address of this route. An
		     entry with a value of 0.0.0.0 is considered a
		     default route.  Multiple routes to a single
		     destination can appear in the table, but access to
		     such multiple entries is dependent on the table-
		     access mechanisms defined by the network
		     management protocol in use."
	::= { wfIpBaseRtEntry 1 }

wfIpBaseRouteIfIndex OBJECT-TYPE
	SYNTAX	INTEGER
	ACCESS	read-only
	STATUS	mandatory
	DESCRIPTION
		"The index value which uniquely identifies the
		     local interface through which the next hop of this
		     route should be reached.  The interface identified
		     by a particular value of this index is the same
		     interface as identified by the same value of
		     ifIndex."
	::= { wfIpBaseRtEntry 2 }

wfIpBaseRouteMetric1 OBJECT-TYPE
	SYNTAX	INTEGER
	ACCESS	read-only
	STATUS	mandatory
	DESCRIPTION
		"The primary routing metric for this route. The
		     semantics of this metric are determined by the
		     routing-protocol specified in the route's
		     ipRouteProto value.  If this metric is not used,
		     its value should be set to -1."
	::= { wfIpBaseRtEntry 3 }

wfIpBaseRouteMetric2 OBJECT-TYPE
	SYNTAX	INTEGER
	ACCESS	read-only
	STATUS	mandatory
	DESCRIPTION
		"An alternate routing metric for this route. The
		     semantics of this metric are determined by the
		     routing-protocol specified in the route's
		     ipRouteProto value.  If this metric is not used,
		     its value should be set to -1."
	::= { wfIpBaseRtEntry 4 }

wfIpBaseRouteMetric3 OBJECT-TYPE
	SYNTAX	INTEGER
	ACCESS	read-only
	STATUS	mandatory
	DESCRIPTION
		"An alternate routing metric for this route. The
		     semantics of this metric are determined by the
		     routing-protocol specified in the route's
		     ipRouteProto value.  If this metric is not used,
		     its value should be set to -1."
	::= { wfIpBaseRtEntry 5 }

wfIpBaseRouteMetric4 OBJECT-TYPE
	SYNTAX	INTEGER
	ACCESS	read-only
	STATUS	mandatory
	DESCRIPTION
		"An alternate routing metric for this route. The
		     semantics of this metric are determined by the
		     routing-protocol specified in the route's
		     ipRouteProto value.  If this metric is not used,
		     its value should be set to -1."
	::= { wfIpBaseRtEntry 6 }

wfIpBaseRouteNextHop OBJECT-TYPE
	SYNTAX	IpAddress
	ACCESS	read-only
	STATUS	mandatory
	DESCRIPTION
		"The IP address of the next hop of this route.
		     (In the case of a route bound to an interface
		     which is realized via a broadcast media, the value
		     of this field is the agent's IP address on that
		     interface.)"
	::= { wfIpBaseRtEntry 7 }

wfIpBaseRouteType OBJECT-TYPE
	SYNTAX	INTEGER {
		other(1),
		invalid(2),
		direct(3),
		indirect(4)
	}
	ACCESS	read-only
	STATUS	mandatory
	DESCRIPTION
		"The type of route. Note that the values
		     direct(3) and indirect(4) refer to the notion of
		     direct and indirect routing in the IP
		     architecture.
		     Setting this object to the value invalid(2) has
		     the effect of invalidating the corresponding entry
		     in the ipRouteTable object.  That is, it
		     effectively dissasociates the destination
		     identified with said entry from the route
		     identified with said entry.  It is an
		     implementation-specific matter as to whether the
		     agent removes an invalidated entry from the table.
		     nagement stations must be prepared
		     to receive tabular information from agents that
		     corresponds to entries not currently in use.
		     Proper interpretation of such entries requires
		     examination of the relevant ipRouteType object."
	::= { wfIpBaseRtEntry 8 }

wfIpBaseRouteProto OBJECT-TYPE
	SYNTAX	INTEGER {
		other(1),
		local(2),
		netmgmt(3),
		icmp(4),
		egp(5),
		ggp(6),
		hello(7),
		rip(8),
		is(9),
		ospf(13),
		bgp(14)
	}
	ACCESS	read-only
	STATUS	mandatory
	DESCRIPTION
		"The routing mechanism via which this route was
		     learned.  Inclusion of values for gateway routing
		     protocols is not intended to imply that hosts
		     should support those protocols."
	::= { wfIpBaseRtEntry 9 }

wfIpBaseRouteAge OBJECT-TYPE
	SYNTAX	INTEGER
	ACCESS	read-only
	STATUS	mandatory
	DESCRIPTION
		"The number of seconds since this route was last
		     updated or otherwise determined to be correct.
		     Note that no semantics of `too old' can be implied
		     except through knowledge of the routing protocol
		     by which the route was learned."
	::= { wfIpBaseRtEntry 10 }

wfIpBaseRouteMask OBJECT-TYPE
	SYNTAX	IpAddress
	ACCESS	read-only
	STATUS	mandatory
	DESCRIPTION
		"Indicate the mask to be logical-ANDed with the
		     destination address before being compared to the
		     value in the ipRouteDest field.  For those systems
		     that do not support arbitrary subnet masks, an
		     agent constructs the value of the ipRouteMask by
		     determining whether the value of the correspondent
		     ipRouteDest field belong to a class-A, B, or C
		     network, and then using one of:
		          mask           network
		          255.0.0.0      class-A
		          255.255.0.0    class-B
		          255.255.255.0  class-C
		     If the value of the ipRouteDest is 0.0.0.0 (a
		     default route), then the mask value is also
		     0.0.0.0.  It should be noted that all IP routing
		     subsystems implicitly use this mechanism."
	::= { wfIpBaseRtEntry 11 }

wfIpBaseRouteMetric5 OBJECT-TYPE
	SYNTAX	INTEGER
	ACCESS	read-only
	STATUS	mandatory
	DESCRIPTION
		"An alternate routing metric for this route. The
		     semantics of this metric are determined by the
		     routing-protocol specified in the route's
		     ipRouteProto value.  If this metric is not used,
		     its value should be set to -1."
	::= { wfIpBaseRtEntry 12 }

wfIpBaseRouteInfo OBJECT-TYPE
	SYNTAX	OBJECT IDENTIFIER
	ACCESS	read-only
	STATUS	mandatory
	DESCRIPTION
		" A user-defined string which describes this Route entry "
	::= { wfIpBaseRtEntry 13 }

wfIpBaseHostEntryTable OBJECT-TYPE
	SYNTAX	SEQUENCE OF WfIpBaseHostEntry
	ACCESS	not-accessible
	STATUS	mandatory
	DESCRIPTION
		" The list of elements in IP's host table "
	::= { wfIpGroup 3 }

wfIpBaseHostEntry OBJECT-TYPE
	SYNTAX	WfIpBaseHostEntry
	ACCESS	not-accessible
	STATUS	mandatory
	DESCRIPTION
		" A description of a resolved host "
	INDEX	{ wfIpBaseNetToMediaNetAddress }
	::= { wfIpBaseHostEntryTable 1 }

WfIpBaseHostEntry ::= SEQUENCE {
	wfIpBaseNetToMediaIfIndex
		INTEGER,
	wfIpBaseNetToMediaPhysAddress
		OCTET STRING,
	wfIpBaseNetToMediaNetAddress
		IpAddress,
	wfIpBaseNetToMediaType
		INTEGER
}

wfIpBaseNetToMediaIfIndex OBJECT-TYPE
	SYNTAX	INTEGER
	ACCESS	read-only
	STATUS	mandatory
	DESCRIPTION
		"The interface on which this entry's equivalence
		     is effective.  The interface identified by a
		     particular value of this index is the same
		     interface as identified by the same value of
		     ifIndex."
	::= { wfIpBaseHostEntry 1 }

wfIpBaseNetToMediaPhysAddress OBJECT-TYPE
	SYNTAX	OCTET STRING
	ACCESS	read-only
	STATUS	mandatory
	DESCRIPTION
		"The media-dependent `physical' address."
	::= { wfIpBaseHostEntry 2 }

wfIpBaseNetToMediaNetAddress OBJECT-TYPE
	SYNTAX	IpAddress
	ACCESS	read-only
	STATUS	mandatory
	DESCRIPTION
		"The IpAddress corresponding to the media-dependent `physical' address."
	::= { wfIpBaseHostEntry 3 }

wfIpBaseNetToMediaType OBJECT-TYPE
	SYNTAX	INTEGER {
		other(1),
		invalid(2),
		dynamic(3),
		static(4)
	}
	ACCESS	read-write
	STATUS	mandatory
	DESCRIPTION
		"The type of mapping.
		     Setting this object to the value invalid(2) has
		     the effect of invalidating the corresponding entry
		     in the ipNetToMediaTable.  That is, it effectively
		     dissasociates the interface identified with said
		     entry from the mapping identified with said entry.
		     It is an implementation-specific matter as to
		     whether the agent removes an invalidated entry
		     from the table.  Accordingly, management stations
		     must be prepared to receive tabular information
		     from agents that corresponds to entries not
		     currently in use.  Proper interpretation of such
		     entries requires examination of the relevant
		     ipNetToMediaType object. "
	::= { wfIpBaseHostEntry 4 }

wfIpInterfaceTable OBJECT-TYPE
	SYNTAX	SEQUENCE OF WfIpInterfaceEntry
	ACCESS	not-accessible
	STATUS	mandatory
	DESCRIPTION
		" The list of configured IP interface "
	::= { wfIpGroup 4 }

wfIpInterfaceEntry OBJECT-TYPE
	SYNTAX	WfIpInterfaceEntry
	ACCESS	not-accessible
	STATUS	mandatory
	DESCRIPTION
		" An IP interface description "
	INDEX	{ wfIpInterfaceAddr,
		wfIpInterfaceCircuit }
	::= { wfIpInterfaceTable 1 }

WfIpInterfaceEntry ::= SEQUENCE {
	wfIpInterfaceCreate
		INTEGER,
	wfIpInterfaceEnable
		INTEGER,
	wfIpInterfaceState
		INTEGER,
	wfIpInterfaceAddr
		IpAddress,
	wfIpInterfaceCircuit
		INTEGER,
	wfIpInterfaceMask
		IpAddress,
	wfIpInterfaceCost
		INTEGER,
	wfIpInterfaceCfgBcastAddr
		IpAddress,
	wfIpInterfaceBcastAddr
		IpAddress,
	wfIpInterfaceMTUDiscovery
		INTEGER,
	wfIpInterfaceAMR
		INTEGER,
	wfIpInterfaceASB
		INTEGER,
	wfIpInterfaceAddressResolutionType
		INTEGER,
	wfIpInterfaceProxy
		INTEGER,
	wfIpInterfaceHostCache
		INTEGER,
	wfIpInterfaceUdpXsumOn
		INTEGER,
	wfIpInterfaceCfgMacAddress
		OCTET STRING,
	wfIpInterfaceMacAddress
		OCTET STRING,
	wfIpInterfaceReasmMaxSize
		INTEGER,
	wfIpInterfaceMaxInfo
		INTEGER,
	wfIpInterfaceInReceives
		Counter,
	wfIpInterfaceInHdrErrors
		Counter,
	wfIpInterfaceInAddrErrors
		Counter,
	wfIpInterfaceForwDatagrams
		Counter,
	wfIpInterfaceInUnknownProtos
		Counter,
	wfIpInterfaceInDiscards
		Counter,
	wfIpInterfaceInDelivers
		Counter,
	wfIpInterfaceOutRequests
		Counter,
	wfIpInterfaceOutDiscards
		Counter,
	wfIpInterfaceOutNoRoutes
		Counter,
	wfIpInterfaceReasmTimeout
		INTEGER,
	wfIpInterfaceReasmReqds
		Counter,
	wfIpInterfaceReasmOKs
		Counter,
	wfIpInterfaceReasmFails
		Counter,
	wfIpInterfaceFragOKs
		Counter,
	wfIpInterfaceFragFails
		Counter,
	wfIpInterfaceFragCreates
		Counter,
	wfIpInterfaceIcmpInMsgs
		Counter,
	wfIpInterfaceIcmpInErrors
		Counter,
	wfIpInterfaceIcmpInDestUnreachs
		Counter,
	wfIpInterfaceIcmpInTimeExcds
		Counter,
	wfIpInterfaceIcmpInParmProbs
		Counter,
	wfIpInterfaceIcmpInSrcQuenchs
		Counter,
	wfIpInterfaceIcmpInRedirects
		Counter,
	wfIpInterfaceIcmpInEchos
		Counter,
	wfIpInterfaceIcmpInEchoReps
		Counter,
	wfIpInterfaceIcmpInTimestamps
		Counter,
	wfIpInterfaceIcmpInTimestampReps
		Counter,
	wfIpInterfaceIcmpInAddrMasks
		Counter,
	wfIpInterfaceIcmpInAddrMaskReps
		Counter,
	wfIpInterfaceIcmpOutMsgs
		Counter,
	wfIpInterfaceIcmpOutErrors
		Counter,
	wfIpInterfaceIcmpOutDestUnreachs
		Counter,
	wfIpInterfaceIcmpOutTimeExcds
		Counter,
	wfIpInterfaceIcmpOutParmProbs
		Counter,
	wfIpInterfaceIcmpOutSrcQuenchs
		Counter,
	wfIpInterfaceIcmpOutRedirects
		Counter,
	wfIpInterfaceIcmpOutEchos
		Counter,
	wfIpInterfaceIcmpOutEchoReps
		Counter,
	wfIpInterfaceIcmpOutTimestamps
		Counter,
	wfIpInterfaceIcmpOutTimestampReps
		Counter,
	wfIpInterfaceIcmpOutAddrMasks
		Counter,
	wfIpInterfaceIcmpOutAddrMaskReps
		Counter,
	wfIpInterfaceTrEndStation
		INTEGER,
	wfIpInterfaceSMDSGroupAddress
		OCTET STRING,
	wfIpInterfaceSMDSArpReqAddress
		OCTET STRING,
	wfIpInterfaceFRBcastDlci
		INTEGER,
	wfIpInterfaceFRMcast1Dlci
		INTEGER,
	wfIpInterfaceFRMcast2Dlci
		INTEGER,
	wfIpInterfaceRedirect
		INTEGER,
	wfIpInterfaceEnetArpEncaps
		INTEGER
}

wfIpInterfaceCreate OBJECT-TYPE
	SYNTAX	INTEGER {
		create(1),
		delete(2)
	}
	ACCESS	read-write
	STATUS	mandatory
	DESCRIPTION
		"Create/Delete parameter. Default is created.
		     Users perform a set operation on this
		     object in order to create/delete an IP interface."
	DEFVAL	{ create }
	::= { wfIpInterfaceEntry 1 }

wfIpInterfaceEnable OBJECT-TYPE
	SYNTAX	INTEGER {
		enable(1),
		disable(2)
	}
	ACCESS	read-write
	STATUS	mandatory
	DESCRIPTION
		"Enable/Disable parameter. Default is enabled.
		     Users perform a set operation on this
		     object in order to enable/disable an IP interface."
	DEFVAL	{ enable }
	::= { wfIpInterfaceEntry 2 }

wfIpInterfaceState OBJECT-TYPE
	SYNTAX	INTEGER {
		up(1),
		down(2),
		init(3),
		invalid(4),
		notpres(5)
	}
	ACCESS	read-only
	STATUS	mandatory
	DESCRIPTION
		" INvalid indicates an error in processing the cfg record "
	DEFVAL	{ notpres }
	::= { wfIpInterfaceEntry 3 }

wfIpInterfaceAddr OBJECT-TYPE
	SYNTAX	IpAddress
	ACCESS	read-only
	STATUS	mandatory
	DESCRIPTION
		" The IP Address to which this entry's addressing information
		       pertains "
	::= { wfIpInterfaceEntry 4 }

wfIpInterfaceCircuit OBJECT-TYPE
	SYNTAX	INTEGER
	ACCESS	read-only
	STATUS	mandatory
	DESCRIPTION
		" The Circuit Number that this interface runs over"
	::= { wfIpInterfaceEntry 5 }

wfIpInterfaceMask OBJECT-TYPE
	SYNTAX	IpAddress
	ACCESS	read-write
	STATUS	mandatory
	DESCRIPTION
		"The subnet mask associated with the IP address of
		     this entry.  The value of the mask is an IP
		     address with all the network bits set to 1 and all
		     the hosts bits set to 0."
	::= { wfIpInterfaceEntry 6 }

wfIpInterfaceCost OBJECT-TYPE
	SYNTAX	INTEGER
	ACCESS	read-write
	STATUS	mandatory
	DESCRIPTION
		" The Cost metric associated with the IP Address of this entry "
	DEFVAL	{ 1 }
	::= { wfIpInterfaceEntry 7 }

wfIpInterfaceCfgBcastAddr OBJECT-TYPE
	SYNTAX	IpAddress
	ACCESS	read-write
	STATUS	mandatory
	DESCRIPTION
		" The user can specifcy a broadcast address for a NWIF "
	::= { wfIpInterfaceEntry 8 }

wfIpInterfaceBcastAddr OBJECT-TYPE
	SYNTAX	IpAddress
	ACCESS	read-only
	STATUS	mandatory
	DESCRIPTION
		"The value of the broadcast address used for sending datagrams on
		     the (logical) interface associated with the IP
		     address of this entry. This value applies to
		     both the subnet and network broadcasts addresses
		     used by the entity on this (logical) interface.
		     This is value used by the software "
	::= { wfIpInterfaceEntry 9 }

wfIpInterfaceMTUDiscovery OBJECT-TYPE
	SYNTAX	INTEGER {
		on(1),
		off(2)
	}
	ACCESS	read-write
	STATUS	mandatory
	DESCRIPTION
		" Whether MTU discovery option is on/off "
	DEFVAL	{ off }
	::= { wfIpInterfaceEntry 10 }

wfIpInterfaceAMR OBJECT-TYPE
	SYNTAX	INTEGER {
		on(1),
		off(2)
	}
	ACCESS	read-write
	STATUS	mandatory
	DESCRIPTION
		" Whether Address Mask Reply is ON/OFF "
	DEFVAL	{ off }
	::= { wfIpInterfaceEntry 11 }

wfIpInterfaceASB OBJECT-TYPE
	SYNTAX	INTEGER {
		on(1),
		off(2)
	}
	ACCESS	read-write
	STATUS	mandatory
	DESCRIPTION
		" Whether All-Subnet Broadcasts Are excepted and Sent out this NWIF "
	DEFVAL	{ off }
	::= { wfIpInterfaceEntry 12 }

wfIpInterfaceAddressResolutionType OBJECT-TYPE
	SYNTAX	INTEGER {
		arp(1),
		probe(2),
		ddn(3),
		pdn(4),
		inarp(5),
		arpinarp(6)
	}
	ACCESS	read-write
	STATUS	mandatory
	DESCRIPTION
		" Indicates which Address Resolution Type to use "
	DEFVAL	{ arp }
	::= { wfIpInterfaceEntry 13 }

wfIpInterfaceProxy OBJECT-TYPE
	SYNTAX	INTEGER {
		on(1),
		off(2)
	}
	ACCESS	read-write
	STATUS	mandatory
	DESCRIPTION
		" Indicates Whether Proxy is on this Interface or not "
	DEFVAL	{ off }
	::= { wfIpInterfaceEntry 14 }

wfIpInterfaceHostCache OBJECT-TYPE
	SYNTAX	INTEGER {
		cacheoff(1),
		cache120(120),
		cache180(180),
		cache240(240),
		cache300(300),
		cache600(600),
		cache900(900),
		cache1200(1200)
	}
	ACCESS	read-write
	STATUS	mandatory
	DESCRIPTION
		" Whether the Host Cache (Address Aging) is on or not.
		       A Range of discrete values is specified as well as a
		       value meaning  don't age "
	DEFVAL	{ cacheoff }
	::= { wfIpInterfaceEntry 15 }

wfIpInterfaceUdpXsumOn OBJECT-TYPE
	SYNTAX	INTEGER {
		on(1),
		off(2)
	}
	ACCESS	read-write
	STATUS	mandatory
	DESCRIPTION
		" Whether to turn UDP checksum verification on
		       for UDP packets recieved and transmitted by
		       this router "
	DEFVAL	{ on }
	::= { wfIpInterfaceEntry 16 }

wfIpInterfaceCfgMacAddress OBJECT-TYPE
	SYNTAX	OCTET STRING
	ACCESS	read-write
	STATUS	mandatory
	DESCRIPTION
		" The desired mac set by the user "
	::= { wfIpInterfaceEntry 17 }

wfIpInterfaceMacAddress OBJECT-TYPE
	SYNTAX	OCTET STRING
	ACCESS	read-only
	STATUS	mandatory
	DESCRIPTION
		" The MAC Address for this Interface- actual one used "
	::= { wfIpInterfaceEntry 18 }

wfIpInterfaceReasmMaxSize OBJECT-TYPE
	SYNTAX	INTEGER
	ACCESS	read-only
	STATUS	mandatory
	DESCRIPTION
		"The size of the largest IP datagram which this
		     entity can re-assemble from incoming IP fragmented
		     datagrams received on this interface."
	::= { wfIpInterfaceEntry 19 }

wfIpInterfaceMaxInfo OBJECT-TYPE
	SYNTAX	INTEGER
	ACCESS	read-only
	STATUS	mandatory
	DESCRIPTION
		"The maximum size of the INFO (non-MAC) field that
		     this port will receive or transmit."
	::= { wfIpInterfaceEntry 20 }

wfIpInterfaceInReceives OBJECT-TYPE
	SYNTAX	Counter
	ACCESS	read-only
	STATUS	mandatory
	DESCRIPTION
		"The total number of input datagrams received from interfaces,
		      including those received in error."
	::= { wfIpInterfaceEntry 21 }

wfIpInterfaceInHdrErrors OBJECT-TYPE
	SYNTAX	Counter
	ACCESS	read-only
	STATUS	mandatory
	DESCRIPTION
		"The number of input datagrams discarded due to
		     errors in their IP headers, including bad
		     checksums, version number mismatch, other format
		     errors, time-to-live exceeded, errors discovered
		     in processing their IP options, etc."
	::= { wfIpInterfaceEntry 22 }

wfIpInterfaceInAddrErrors OBJECT-TYPE
	SYNTAX	Counter
	ACCESS	read-only
	STATUS	mandatory
	DESCRIPTION
		"The number of input datagrams discarded because
		     the IP address in their IP header's destination
		     field was not a valid address to be received at
		     this entity.  This count includes invalid
		     addresses (e.g., 0.0.0.0) and addresses of
		     unsupported Classes (e.g., Class E).  For entities
		     which are not IP Gateways and therefore do not
		     forward datagrams, this counter includes datagrams
		     discarded because the destination address was not
		     a local address."
	::= { wfIpInterfaceEntry 23 }

wfIpInterfaceForwDatagrams OBJECT-TYPE
	SYNTAX	Counter
	ACCESS	read-only
	STATUS	mandatory
	DESCRIPTION
		"The number of input datagrams for which this
		     entity was not their final IP destination, as a
		     result of which an attempt was made to find a
		     route to forward them to that final destination.
		     In entities which do not act as IP Gateways, this
		     counter will include only those packets which were
		     Source-Routed via this entity, and the Source-
		     Route option processing was successful."
	::= { wfIpInterfaceEntry 24 }

wfIpInterfaceInUnknownProtos OBJECT-TYPE
	SYNTAX	Counter
	ACCESS	read-only
	STATUS	mandatory
	DESCRIPTION
		"The number of locally-addressed datagrams
		     received successfully but discarded because of an
		     unknown or unsupported protocol."
	::= { wfIpInterfaceEntry 25 }

wfIpInterfaceInDiscards OBJECT-TYPE
	SYNTAX	Counter
	ACCESS	read-only
	STATUS	mandatory
	DESCRIPTION
		"The number of input IP datagrams for which no
		     problems were encountered to prevent their
		     continued processing, but which were discarded
		     (e.g., for lack of buffer space).  Note that this
		     counter does not include any datagrams discarded
		     while awaiting re-assembly."
	::= { wfIpInterfaceEntry 26 }

wfIpInterfaceInDelivers OBJECT-TYPE
	SYNTAX	Counter
	ACCESS	read-only
	STATUS	mandatory
	DESCRIPTION
		"The total number of input datagrams successfully
		     delivered to IP user-protocols (including ICMP)."
	::= { wfIpInterfaceEntry 27 }

wfIpInterfaceOutRequests OBJECT-TYPE
	SYNTAX	Counter
	ACCESS	read-only
	STATUS	mandatory
	DESCRIPTION
		"The total number of IP datagrams which local IP
		     user-protocols (including ICMP) supplied to IP in
		     requests for transmission.  Note that this counter
		     does not include any datagrams counted in
		     ipForwDatagrams."
	::= { wfIpInterfaceEntry 28 }

wfIpInterfaceOutDiscards OBJECT-TYPE
	SYNTAX	Counter
	ACCESS	read-only
	STATUS	mandatory
	DESCRIPTION
		"The number of output IP datagrams for which no
		     problem was encountered to prevent their
		     transmission to their destination, but which were
		     discarded (e.g., for lack of buffer space).  Note
		     that this counter would include datagrams counted
		     in ipForwDatagrams if any such packets met this
		     (discretionary) discard criterion."
	::= { wfIpInterfaceEntry 29 }

wfIpInterfaceOutNoRoutes OBJECT-TYPE
	SYNTAX	Counter
	ACCESS	read-only
	STATUS	mandatory
	DESCRIPTION
		"The number of IP datagrams discarded because no
		     route could be found to transmit them to their
		     destination.  Note that this counter includes any
		     packets counted in ipForwDatagrams which meet this
		     `no-route' criterion.  Note that this includes any
		     datagarms which a host cannot route because all of
		     its default gateways are down."
	::= { wfIpInterfaceEntry 30 }

wfIpInterfaceReasmTimeout OBJECT-TYPE
	SYNTAX	INTEGER
	ACCESS	read-only
	STATUS	mandatory
	DESCRIPTION
		"The maximum number of seconds which received
		     fragments are held while they are awaiting
		     reassembly at this entity."
	::= { wfIpInterfaceEntry 31 }

wfIpInterfaceReasmReqds OBJECT-TYPE
	SYNTAX	Counter
	ACCESS	read-only
	STATUS	mandatory
	DESCRIPTION
		"The number of IP fragments received which needed
		     to be reassembled at this entity."
	::= { wfIpInterfaceEntry 32 }

wfIpInterfaceReasmOKs OBJECT-TYPE
	SYNTAX	Counter
	ACCESS	read-only
	STATUS	mandatory
	DESCRIPTION
		"The number of IP datagrams successfully reassembled."
	::= { wfIpInterfaceEntry 33 }

wfIpInterfaceReasmFails OBJECT-TYPE
	SYNTAX	Counter
	ACCESS	read-only
	STATUS	mandatory
	DESCRIPTION
		"The number of failures detected by the IP re-
		     assembly algorithm (for whatever reason: timed
		     out, errors, etc).  Note that this is not
		     necessarily a count of discarded IP fragments
		     since some algorithms (notably the algorithm in
		     RFC 815) can lose track of the number of fragments
		     by combining them as they are received."
	::= { wfIpInterfaceEntry 34 }

wfIpInterfaceFragOKs OBJECT-TYPE
	SYNTAX	Counter
	ACCESS	read-only
	STATUS	mandatory
	DESCRIPTION
		"The number of IP datagrams that have been
		      successfully fragmented at this entity."
	::= { wfIpInterfaceEntry 35 }

wfIpInterfaceFragFails OBJECT-TYPE
	SYNTAX	Counter
	ACCESS	read-only
	STATUS	mandatory
	DESCRIPTION
		"The number of IP datagrams that have been
		     discarded because they needed to be fragmented at
		     this entity but could not be, e.g., because their
		     Don't Fragment flag was set."
	::= { wfIpInterfaceEntry 36 }

wfIpInterfaceFragCreates OBJECT-TYPE
	SYNTAX	Counter
	ACCESS	read-only
	STATUS	mandatory
	DESCRIPTION
		"The number of IP datagram fragments that have
		     been generated as a result of fragmentation at
		     this entity."
	::= { wfIpInterfaceEntry 37 }

wfIpInterfaceIcmpInMsgs OBJECT-TYPE
	SYNTAX	Counter
	ACCESS	read-only
	STATUS	mandatory
	DESCRIPTION
		"The total number of ICMP messages which includes
		      all those counted by wfIpInterfaceIcmpInErrors."
	::= { wfIpInterfaceEntry 38 }

wfIpInterfaceIcmpInErrors OBJECT-TYPE
	SYNTAX	Counter
	ACCESS	read-only
	STATUS	mandatory
	DESCRIPTION
		"The number of ICMP messages which the entity
		     received but determined as having ICMP-specific
		     errors (bad ICMP checksums, bad length, etc.)."
	::= { wfIpInterfaceEntry 39 }

wfIpInterfaceIcmpInDestUnreachs OBJECT-TYPE
	SYNTAX	Counter
	ACCESS	read-only
	STATUS	mandatory
	DESCRIPTION
		"The number of ICMP Destination Unreachable messages received."
	::= { wfIpInterfaceEntry 40 }

wfIpInterfaceIcmpInTimeExcds OBJECT-TYPE
	SYNTAX	Counter
	ACCESS	read-only
	STATUS	mandatory
	DESCRIPTION
		"The number of ICMP Time Exceeded messages received."
	::= { wfIpInterfaceEntry 41 }

wfIpInterfaceIcmpInParmProbs OBJECT-TYPE
	SYNTAX	Counter
	ACCESS	read-only
	STATUS	mandatory
	DESCRIPTION
		"The number of ICMP Parameter Problem messages received."
	::= { wfIpInterfaceEntry 42 }

wfIpInterfaceIcmpInSrcQuenchs OBJECT-TYPE
	SYNTAX	Counter
	ACCESS	read-only
	STATUS	mandatory
	DESCRIPTION
		"The number of ICMP Source Quench messages received."
	::= { wfIpInterfaceEntry 43 }

wfIpInterfaceIcmpInRedirects OBJECT-TYPE
	SYNTAX	Counter
	ACCESS	read-only
	STATUS	mandatory
	DESCRIPTION
		"The number of ICMP Redirect messages received."
	::= { wfIpInterfaceEntry 44 }

wfIpInterfaceIcmpInEchos OBJECT-TYPE
	SYNTAX	Counter
	ACCESS	read-only
	STATUS	mandatory
	DESCRIPTION
		"The number of ICMP Echo (request) messages received."
	::= { wfIpInterfaceEntry 45 }

wfIpInterfaceIcmpInEchoReps OBJECT-TYPE
	SYNTAX	Counter
	ACCESS	read-only
	STATUS	mandatory
	DESCRIPTION
		"The number of ICMP Echo Reply messages received."
	::= { wfIpInterfaceEntry 46 }

wfIpInterfaceIcmpInTimestamps OBJECT-TYPE
	SYNTAX	Counter
	ACCESS	read-only
	STATUS	mandatory
	DESCRIPTION
		"The number of ICMP Timestamp (request) messages received."
	::= { wfIpInterfaceEntry 47 }

wfIpInterfaceIcmpInTimestampReps OBJECT-TYPE
	SYNTAX	Counter
	ACCESS	read-only
	STATUS	mandatory
	DESCRIPTION
		"The number of ICMP Timestamp Reply messages received."
	::= { wfIpInterfaceEntry 48 }

wfIpInterfaceIcmpInAddrMasks OBJECT-TYPE
	SYNTAX	Counter
	ACCESS	read-only
	STATUS	mandatory
	DESCRIPTION
		"The number of ICMP Address Mask Request messages received."
	::= { wfIpInterfaceEntry 49 }

wfIpInterfaceIcmpInAddrMaskReps OBJECT-TYPE
	SYNTAX	Counter
	ACCESS	read-only
	STATUS	mandatory
	DESCRIPTION
		"The number of ICMP Address Mask Reply messages received."
	::= { wfIpInterfaceEntry 50 }

wfIpInterfaceIcmpOutMsgs OBJECT-TYPE
	SYNTAX	Counter
	ACCESS	read-only
	STATUS	mandatory
	DESCRIPTION
		"The total number of ICMP messages which this
		     entity attempted to send.  Note that this counter
		     includes all those counted by icmpOutErrors."
	::= { wfIpInterfaceEntry 51 }

wfIpInterfaceIcmpOutErrors OBJECT-TYPE
	SYNTAX	Counter
	ACCESS	read-only
	STATUS	mandatory
	DESCRIPTION
		"The number of ICMP messages which this entity did
		     not send due to problems discovered within ICMP
		     such as a lack of buffers.  This value should not
		     include errors discovered outside the ICMP layer
		     such as the inability of IP to route the resultant
		     datagram.  In some implementations there may be no
		     types of error which contribute to this counter's
		     value."
	::= { wfIpInterfaceEntry 52 }

wfIpInterfaceIcmpOutDestUnreachs OBJECT-TYPE
	SYNTAX	Counter
	ACCESS	read-only
	STATUS	mandatory
	DESCRIPTION
		"The number of ICMP Destination Unreachable messages sent."
	::= { wfIpInterfaceEntry 53 }

wfIpInterfaceIcmpOutTimeExcds OBJECT-TYPE
	SYNTAX	Counter
	ACCESS	read-only
	STATUS	mandatory
	DESCRIPTION
		"The number of ICMP Time Exceeded messages sent."
	::= { wfIpInterfaceEntry 54 }

wfIpInterfaceIcmpOutParmProbs OBJECT-TYPE
	SYNTAX	Counter
	ACCESS	read-only
	STATUS	mandatory
	DESCRIPTION
		"The number of ICMP Parameter Problem messages sent."
	::= { wfIpInterfaceEntry 55 }

wfIpInterfaceIcmpOutSrcQuenchs OBJECT-TYPE
	SYNTAX	Counter
	ACCESS	read-only
	STATUS	mandatory
	DESCRIPTION
		"The number of ICMP Source Quench messages sent."
	::= { wfIpInterfaceEntry 56 }

wfIpInterfaceIcmpOutRedirects OBJECT-TYPE
	SYNTAX	Counter
	ACCESS	read-only
	STATUS	mandatory
	DESCRIPTION
		"The number of ICMP Redirect messages sent. For a
		     host, this object will always be zero, since hosts
		     do not send redirects."
	::= { wfIpInterfaceEntry 57 }

wfIpInterfaceIcmpOutEchos OBJECT-TYPE
	SYNTAX	Counter
	ACCESS	read-only
	STATUS	mandatory
	DESCRIPTION
		"The number of ICMP Echo (request) messages sent."
	::= { wfIpInterfaceEntry 58 }

wfIpInterfaceIcmpOutEchoReps OBJECT-TYPE
	SYNTAX	Counter
	ACCESS	read-only
	STATUS	mandatory
	DESCRIPTION
		"The number of ICMP Echo Reply messages sent."
	::= { wfIpInterfaceEntry 59 }

wfIpInterfaceIcmpOutTimestamps OBJECT-TYPE
	SYNTAX	Counter
	ACCESS	read-only
	STATUS	mandatory
	DESCRIPTION
		"The number of ICMP Timestamp (request) messages sent."
	::= { wfIpInterfaceEntry 60 }

wfIpInterfaceIcmpOutTimestampReps OBJECT-TYPE
	SYNTAX	Counter
	ACCESS	read-only
	STATUS	mandatory
	DESCRIPTION
		"The number of ICMP Timestamp Reply messages sent."
	::= { wfIpInterfaceEntry 61 }

wfIpInterfaceIcmpOutAddrMasks OBJECT-TYPE
	SYNTAX	Counter
	ACCESS	read-only
	STATUS	mandatory
	DESCRIPTION
		"The number of ICMP Address Mask Request messages sent."
	::= { wfIpInterfaceEntry 62 }

wfIpInterfaceIcmpOutAddrMaskReps OBJECT-TYPE
	SYNTAX	Counter
	ACCESS	read-only
	STATUS	mandatory
	DESCRIPTION
		"The number of ICMP Address Mask Reply messages sent."
	::= { wfIpInterfaceEntry 63 }

wfIpInterfaceTrEndStation OBJECT-TYPE
	SYNTAX	INTEGER {
		on(1),
		off(2)
	}
	ACCESS	read-write
	STATUS	mandatory
	DESCRIPTION
		" Use Source Routing over token ring selection. Only applies
		       if pam type is TRING. "
	DEFVAL	{ off }
	::= { wfIpInterfaceEntry 64 }

wfIpInterfaceSMDSGroupAddress OBJECT-TYPE
	SYNTAX	OCTET STRING
	ACCESS	read-write
	STATUS	mandatory
	DESCRIPTION
		" The SMDS group address "
	::= { wfIpInterfaceEntry 65 }

wfIpInterfaceSMDSArpReqAddress OBJECT-TYPE
	SYNTAX	OCTET STRING
	ACCESS	read-write
	STATUS	mandatory
	DESCRIPTION
		" The SMDS arp req address "
	::= { wfIpInterfaceEntry 66 }

wfIpInterfaceFRBcastDlci OBJECT-TYPE
	SYNTAX	INTEGER
	ACCESS	read-write
	STATUS	mandatory
	DESCRIPTION
		" Frame Relay broadcast dlci "
	::= { wfIpInterfaceEntry 67 }

wfIpInterfaceFRMcast1Dlci OBJECT-TYPE
	SYNTAX	INTEGER
	ACCESS	read-write
	STATUS	mandatory
	DESCRIPTION
		" Frame Relay multicast dlci #1 "
	::= { wfIpInterfaceEntry 68 }

wfIpInterfaceFRMcast2Dlci OBJECT-TYPE
	SYNTAX	INTEGER
	ACCESS	read-write
	STATUS	mandatory
	DESCRIPTION
		" Frame Relay multicast dlci #2 "
	::= { wfIpInterfaceEntry 69 }

wfIpInterfaceRedirect OBJECT-TYPE
	SYNTAX	INTEGER {
		on(1),
		off(2)
	}
	ACCESS	read-write
	STATUS	mandatory
	DESCRIPTION
		" Indicates Whether we're sending out redirects on this Interface or not "
	DEFVAL	{ on }
	::= { wfIpInterfaceEntry 70 }

wfIpInterfaceEnetArpEncaps OBJECT-TYPE
	SYNTAX	INTEGER {
		enet(1),
		snap(2),
		both(3)
	}
	ACCESS	read-write
	STATUS	mandatory
	DESCRIPTION
		" The data link encapsulation type to use for ARP packets
		       if the the media is ethernet. "
	DEFVAL	{ enet }
	::= { wfIpInterfaceEntry 71 }

wfIpStaticRouteTable OBJECT-TYPE
	SYNTAX	SEQUENCE OF WfIpStaticRouteEntry
	ACCESS	not-accessible
	STATUS	mandatory
	DESCRIPTION
		" The list of static routes "
	::= { wfIpGroup 5 }

wfIpStaticRouteEntry OBJECT-TYPE
	SYNTAX	WfIpStaticRouteEntry
	ACCESS	not-accessible
	STATUS	mandatory
	DESCRIPTION
		" A static route definition "
	INDEX	{ wfIpSrIpAddress,
		wfIpSrIpNetMask,
		wfIpSrIpAddressRt }
	::= { wfIpStaticRouteTable 1 }

WfIpStaticRouteEntry ::= SEQUENCE {
	wfIpSrCreate
		INTEGER,
	wfIpSrEnable
		INTEGER,
	wfIpSrIpAddress
		IpAddress,
	wfIpSrIpNetMask
		IpAddress,
	wfIpSrCost
		INTEGER,
	wfIpSrNextHopAddr
		IpAddress,
	wfIpSrNextHopMask
		IpAddress,
	wfIpSrPreference
		INTEGER,
	wfIpSrIpAddressRt
		INTEGER,
	wfIpSrValid
		INTEGER
}

wfIpSrCreate OBJECT-TYPE
	SYNTAX	INTEGER {
		create(1),
		delete(2)
	}
	ACCESS	read-write
	STATUS	mandatory
	DESCRIPTION
		"Create/Delete parameter. Default is created.
		         Users perform a set operation on this
		         object in order to create/delete the IP
		         Static Route."
	DEFVAL	{ create }
	::= { wfIpStaticRouteEntry 1 }

wfIpSrEnable OBJECT-TYPE
	SYNTAX	INTEGER {
		enable(1),
		disable(2)
	}
	ACCESS	read-write
	STATUS	mandatory
	DESCRIPTION
		"Enable/Disable parameter. Default is enabled.
		          Users perform a set operation on this
		        object in order to enable/disable this IP
		        Static Route."
	DEFVAL	{ enable }
	::= { wfIpStaticRouteEntry 2 }

wfIpSrIpAddress OBJECT-TYPE
	SYNTAX	IpAddress
	ACCESS	read-only
	STATUS	mandatory
	DESCRIPTION
		" The Address of this static route "
	::= { wfIpStaticRouteEntry 3 }

wfIpSrIpNetMask OBJECT-TYPE
	SYNTAX	IpAddress
	ACCESS	read-only
	STATUS	mandatory
	DESCRIPTION
		" The IP Network Mask for this Static Route "
	::= { wfIpStaticRouteEntry 4 }

wfIpSrCost OBJECT-TYPE
	SYNTAX	INTEGER {
		cost(1)
	}
	ACCESS	read-write
	STATUS	mandatory
	DESCRIPTION
		" The Cost of this Static Route "
	DEFVAL	{ cost }
	::= { wfIpStaticRouteEntry 5 }

wfIpSrNextHopAddr OBJECT-TYPE
	SYNTAX	IpAddress
	ACCESS	read-write
	STATUS	mandatory
	DESCRIPTION
		" The Next Hop IP Address "
	::= { wfIpStaticRouteEntry 6 }

wfIpSrNextHopMask OBJECT-TYPE
	SYNTAX	IpAddress
	ACCESS	read-write
	STATUS	mandatory
	DESCRIPTION
		" The Next Hop IP Netmask "
	::= { wfIpStaticRouteEntry 7 }

wfIpSrPreference OBJECT-TYPE
	SYNTAX	INTEGER {
		pref(16)
	}
	ACCESS	read-write
	STATUS	mandatory
	DESCRIPTION
		" This Routes Preference "
	DEFVAL	{ pref }
	::= { wfIpStaticRouteEntry 8 }

wfIpSrIpAddressRt OBJECT-TYPE
	SYNTAX	INTEGER
	ACCESS	read-only
	STATUS	mandatory
	DESCRIPTION
		" The Route Identifier Which numbered route this is to be"
	::= { wfIpStaticRouteEntry 9 }

wfIpSrValid OBJECT-TYPE
	SYNTAX	INTEGER {
		valid(1),
		invalid(2)
	}
	ACCESS	read-only
	STATUS	mandatory
	DESCRIPTION
		" Whether this Static Route is valid or not "
	DEFVAL	{ valid }
	::= { wfIpStaticRouteEntry 10 }

wfIpAdjacentHostTable OBJECT-TYPE
	SYNTAX	SEQUENCE OF WfIpAdjacentHostEntry
	ACCESS	not-accessible
	STATUS	mandatory
	DESCRIPTION
		" The list of Adjacent Hosts (static IP-Mac resolutions) "
	::= { wfIpGroup 6 }

wfIpAdjacentHostEntry OBJECT-TYPE
	SYNTAX	WfIpAdjacentHostEntry
	ACCESS	not-accessible
	STATUS	mandatory
	DESCRIPTION
		" A description of an adjacent host "
	INDEX	{ wfIpAdjHostIpAddress }
	::= { wfIpAdjacentHostTable 1 }

WfIpAdjacentHostEntry ::= SEQUENCE {
	wfIpAdjHostCreate
		INTEGER,
	wfIpAdjHostEnable
		INTEGER,
	wfIpAdjHostIpAddress
		IpAddress,
	wfIpAdjHostIntf
		IpAddress,
	wfIpAdjHostIntfMask
		IpAddress,
	wfIpAdjHostMacAddr
		OCTET STRING,
	wfIpAdjHostEncaps
		INTEGER,
	wfIpAdjHostValid
		INTEGER
}

wfIpAdjHostCreate OBJECT-TYPE
	SYNTAX	INTEGER {
		create(1),
		delete(2)
	}
	ACCESS	read-write
	STATUS	mandatory
	DESCRIPTION
		" Whether to Delete this Adjacent Host "
	DEFVAL	{ create }
	::= { wfIpAdjacentHostEntry 1 }

wfIpAdjHostEnable OBJECT-TYPE
	SYNTAX	INTEGER {
		enable(1),
		disable(2)
	}
	ACCESS	read-write
	STATUS	mandatory
	DESCRIPTION
		" Whether to Disable this Host "
	DEFVAL	{ enable }
	::= { wfIpAdjacentHostEntry 2 }

wfIpAdjHostIpAddress OBJECT-TYPE
	SYNTAX	IpAddress
	ACCESS	read-only
	STATUS	mandatory
	DESCRIPTION
		" The IP address of this Adjacent Host "
	::= { wfIpAdjacentHostEntry 3 }

wfIpAdjHostIntf OBJECT-TYPE
	SYNTAX	IpAddress
	ACCESS	read-write
	STATUS	mandatory
	DESCRIPTION
		" The Interface for this Adjacent Host "
	::= { wfIpAdjacentHostEntry 4 }

wfIpAdjHostIntfMask OBJECT-TYPE
	SYNTAX	IpAddress
	ACCESS	read-write
	STATUS	mandatory
	DESCRIPTION
		" The Network Mask of this Intf"
	::= { wfIpAdjacentHostEntry 5 }

wfIpAdjHostMacAddr OBJECT-TYPE
	SYNTAX	OCTET STRING
	ACCESS	read-write
	STATUS	mandatory
	DESCRIPTION
		" The LAN Address for this HOST "
	::= { wfIpAdjacentHostEntry 6 }

wfIpAdjHostEncaps OBJECT-TYPE
	SYNTAX	INTEGER {
		enet(1),
		snap(2)
	}
	ACCESS	read-write
	STATUS	mandatory
	DESCRIPTION
		" The encapsulation type of this entry "
	DEFVAL	{ enet }
	::= { wfIpAdjacentHostEntry 7 }

wfIpAdjHostValid OBJECT-TYPE
	SYNTAX	INTEGER {
		valid(1),
		invalid(2)
	}
	ACCESS	read-only
	STATUS	mandatory
	DESCRIPTION
		" Whether the record passed validation or not "
	DEFVAL	{ valid }
	::= { wfIpAdjacentHostEntry 8 }

wfIpTrafficFilterTable OBJECT-TYPE
	SYNTAX	SEQUENCE OF WfIpTrafficFilterEntry
	ACCESS	not-accessible
	STATUS	mandatory
	DESCRIPTION
		" IP Traffic Filters "
	::= { wfIpGroup 7 }

wfIpTrafficFilterEntry OBJECT-TYPE
	SYNTAX	WfIpTrafficFilterEntry
	ACCESS	not-accessible
	STATUS	mandatory
	DESCRIPTION
		" A traffic filter definition "
	INDEX	{ wfIpTrafficFilterInterface,
		wfIpTrafficFilterCircuit,
		wfIpTrafficFilterRuleNumber,
		wfIpTrafficFilterFragment }
	::= { wfIpTrafficFilterTable 1 }

WfIpTrafficFilterEntry ::= SEQUENCE {
	wfIpTrafficFilterCreate
		INTEGER,
	wfIpTrafficFilterEnable
		INTEGER,
	wfIpTrafficFilterStatus
		INTEGER,
	wfIpTrafficFilterCounter
		Counter,
	wfIpTrafficFilterDefinition
		Opaque,
	wfIpTrafficFilterReserved
		INTEGER,
	wfIpTrafficFilterInterface
		IpAddress,
	wfIpTrafficFilterCircuit
		INTEGER,
	wfIpTrafficFilterRuleNumber
		INTEGER,
	wfIpTrafficFilterFragment
		INTEGER
}

wfIpTrafficFilterCreate OBJECT-TYPE
	SYNTAX	INTEGER {
		created(1),
		deleted(2)
	}
	ACCESS	read-write
	STATUS	mandatory
	DESCRIPTION
		" Defines the existence of the traffic filter rule:
		               created - traffic filter exists
		        delete - traffic filter does not exist and can be deleted. "
	DEFVAL	{ created }
	::= { wfIpTrafficFilterEntry 1 }

wfIpTrafficFilterEnable OBJECT-TYPE
	SYNTAX	INTEGER {
		enabled(1),
		disabled(2)
	}
	ACCESS	read-write
	STATUS	mandatory
	DESCRIPTION
		" Defines whether or not the traffic filter rule should be used:
		  enabled - activate the rule.
		  disabled - inactivate the rule. "
	DEFVAL	{ enabled }
	::= { wfIpTrafficFilterEntry 2 }

wfIpTrafficFilterStatus OBJECT-TYPE
	SYNTAX	INTEGER {
		active(1),
		error(2),
		inactive(3)
	}
	ACCESS	read-only
	STATUS	mandatory
	DESCRIPTION
		" Defines the current status of the traffic filter:
		  inactive - the rule is not in use.
		  active - the rule is being used.
		  error - the application detected an error in the rule. "
	DEFVAL	{ inactive }
	::= { wfIpTrafficFilterEntry 3 }

wfIpTrafficFilterCounter OBJECT-TYPE
	SYNTAX	Counter
	ACCESS	read-only
	STATUS	mandatory
	DESCRIPTION
		" The number of received packets that have
		           matched this rule. "
	::= { wfIpTrafficFilterEntry 4 }

wfIpTrafficFilterDefinition OBJECT-TYPE
	SYNTAX	Opaque
	ACCESS	read-write
	STATUS	mandatory
	DESCRIPTION
		" The filter rule definition. "
	::= { wfIpTrafficFilterEntry 5 }

wfIpTrafficFilterReserved OBJECT-TYPE
	SYNTAX	INTEGER
	ACCESS	not-accessible
	STATUS	mandatory
	DESCRIPTION
		" Reserved field. "
	::= { wfIpTrafficFilterEntry 6 }

wfIpTrafficFilterInterface OBJECT-TYPE
	SYNTAX	IpAddress
	ACCESS	read-only
	STATUS	mandatory
	DESCRIPTION
		" The network address of the IP
		    interface to which this filter is applied. "
	::= { wfIpTrafficFilterEntry 7 }

wfIpTrafficFilterCircuit OBJECT-TYPE
	SYNTAX	INTEGER
	ACCESS	read-only
	STATUS	mandatory
	DESCRIPTION
		" The ID of the Circuit to which the
		    filter is applied. "
	::= { wfIpTrafficFilterEntry 8 }

wfIpTrafficFilterRuleNumber OBJECT-TYPE
	SYNTAX	INTEGER
	ACCESS	read-only
	STATUS	mandatory
	DESCRIPTION
		" ID for the rule. "
	::= { wfIpTrafficFilterEntry 9 }

wfIpTrafficFilterFragment OBJECT-TYPE
	SYNTAX	INTEGER
	ACCESS	read-only
	STATUS	mandatory
	DESCRIPTION
		" Fragment number - for large rules. "
	::= { wfIpTrafficFilterEntry 10 }

wfRipIntfTable OBJECT-TYPE
	SYNTAX	SEQUENCE OF WfRipIntfEntry
	ACCESS	not-accessible
	STATUS	mandatory
	DESCRIPTION
		" The list of configured RIP interfaces "
	::= { wfRipGroup 1 }

wfRipIntfEntry OBJECT-TYPE
	SYNTAX	WfRipIntfEntry
	ACCESS	not-accessible
	STATUS	mandatory
	DESCRIPTION
		" A description of a RIP interface "
	INDEX	{ wfRipInterfaceIndex }
	::= { wfRipIntfTable 1 }

WfRipIntfEntry ::= SEQUENCE {
	wfRipInterfaceCreate
		INTEGER,
	wfRipInterfaceEnable
		INTEGER,
	wfRipInterfaceState
		INTEGER,
	wfRipInterfaceIndex
		IpAddress,
	wfRipInterfaceSupply
		INTEGER,
	wfRipInterfaceListen
		INTEGER,
	wfRipInterfaceDefaultRouteSupply
		INTEGER,
	wfRipInterfaceDefaultRouteListen
		INTEGER,
	wfRipInterfacePoisonedReversed
		INTEGER
}

wfRipInterfaceCreate OBJECT-TYPE
	SYNTAX	INTEGER {
		create(1),
		delete(2)
	}
	ACCESS	read-write
	STATUS	mandatory
	DESCRIPTION
		"Create/Delete parameter. Default is created.
		         Users perform a set operation on this
		         object in order to create/delete an RIP Interface instance."
	DEFVAL	{ create }
	::= { wfRipIntfEntry 1 }

wfRipInterfaceEnable OBJECT-TYPE
	SYNTAX	INTEGER {
		enable(1),
		disable(2)
	}
	ACCESS	read-write
	STATUS	mandatory
	DESCRIPTION
		"Enable/Disable parameter. Default is enabled.
		         Users perform a set operation on this
		         object in order to enable/disable a RIP interface."
	DEFVAL	{ enable }
	::= { wfRipIntfEntry 2 }

wfRipInterfaceState OBJECT-TYPE
	SYNTAX	INTEGER {
		up(1),
		down(2),
		init(3),
		notpres(4)
	}
	ACCESS	read-only
	STATUS	mandatory
	DESCRIPTION
		"The current state of RIP on this interface."
	DEFVAL	{ notpres }
	::= { wfRipIntfEntry 3 }

wfRipInterfaceIndex OBJECT-TYPE
	SYNTAX	IpAddress
	ACCESS	read-only
	STATUS	mandatory
	DESCRIPTION
		"The IP interface to run RIP on."
	::= { wfRipIntfEntry 4 }

wfRipInterfaceSupply OBJECT-TYPE
	SYNTAX	INTEGER {
		enable(1),
		disable(2)
	}
	ACCESS	read-write
	STATUS	mandatory
	DESCRIPTION
		"Transmit RIP packets."
	DEFVAL	{ enable }
	::= { wfRipIntfEntry 5 }

wfRipInterfaceListen OBJECT-TYPE
	SYNTAX	INTEGER {
		enable(1),
		disable(2)
	}
	ACCESS	read-write
	STATUS	mandatory
	DESCRIPTION
		" Whether to listen to RIP packets "
	DEFVAL	{ enable }
	::= { wfRipIntfEntry 6 }

wfRipInterfaceDefaultRouteSupply OBJECT-TYPE
	SYNTAX	INTEGER {
		enable(1),
		disable(2)
	}
	ACCESS	read-write
	STATUS	mandatory
	DESCRIPTION
		"Transmit the default route, 0.0.0.0, in RIP packets."
	DEFVAL	{ disable }
	::= { wfRipIntfEntry 7 }

wfRipInterfaceDefaultRouteListen OBJECT-TYPE
	SYNTAX	INTEGER {
		enable(1),
		disable(2)
	}
	ACCESS	read-write
	STATUS	mandatory
	DESCRIPTION
		"Receive the default route, 0.0.0.0, in RIP packets."
	DEFVAL	{ disable }
	::= { wfRipIntfEntry 8 }

wfRipInterfacePoisonedReversed OBJECT-TYPE
	SYNTAX	INTEGER {
		poisoned(1),
		actual(2),
		split(3)
	}
	ACCESS	read-write
	STATUS	mandatory
	DESCRIPTION
		"Specifies how the router advertises routes
		          it has learned from a neighboring router in 
		          periodic updates subsequently sent to the 
		          neighbor. If 'Poisoned', the node implements
		          poisoned reverse. The router now advertises
		          routes learned from a neighbor in RIP updates
		          subsequently sent to that neighbor with a 
		          hop count of wfRipBaseRipNetworkDiameter
		          plus 1, (thus declaring the destination
		          unreachable). If 'Split', the router
		          implements a split-horizon, and omits routes
		          learned from a neighbor in RIP updates
		          subsequently sent to that neighbor.  If
		          'Actual', the learned cost of the route
		          is advertised. "
	DEFVAL	{ poisoned }
	::= { wfRipIntfEntry 9 }

wfArpBase	OBJECT IDENTIFIER ::= { wfArpGroup 1 }

wfArpBaseCreate OBJECT-TYPE
	SYNTAX	INTEGER {
		created(1),
		deleted(2)
	}
	ACCESS	read-write
	STATUS	mandatory
	DESCRIPTION
		"Create/Delete parameter. Default is created.
		     Users perform a set operation on this
		     object in order to create/delete ARP."
	DEFVAL	{ created }
	::= { wfArpBase 1 }

wfArpBaseEnable OBJECT-TYPE
	SYNTAX	INTEGER {
		enabled(1),
		disabled(2)
	}
	ACCESS	read-write
	STATUS	mandatory
	DESCRIPTION
		" Enable/Disable Parameter indicates whether
		       this ARP record is enabled or disabled. "
	DEFVAL	{ enabled }
	::= { wfArpBase 2 }

wfArpBaseForwarding OBJECT-TYPE
	SYNTAX	INTEGER {
		forwarding(1),
		notforwarding(2)
	}
	ACCESS	read-write
	STATUS	mandatory
	DESCRIPTION
		" Equivalent to IP Host Only. This attribute
		       says that ARP should send unknown addresses to the 
		       bridge for further handling "
	DEFVAL	{ forwarding }
	::= { wfArpBase 3 }

wfArpIntfTable OBJECT-TYPE
	SYNTAX	SEQUENCE OF WfArpIntfEntry
	ACCESS	not-accessible
	STATUS	mandatory
	DESCRIPTION
		" List of configured ARP interfaces "
	::= { wfArpGroup 2 }

wfArpIntfEntry OBJECT-TYPE
	SYNTAX	WfArpIntfEntry
	ACCESS	not-accessible
	STATUS	mandatory
	DESCRIPTION
		" A description of an ARP interface "
	INDEX	{ wfArpCctno }
	::= { wfArpIntfTable 1 }

WfArpIntfEntry ::= SEQUENCE {
	wfArpCreate
		INTEGER,
	wfArpEnable
		INTEGER,
	wfArpCctno
		INTEGER
}

wfArpCreate OBJECT-TYPE
	SYNTAX	INTEGER {
		created(1),
		deleted(2)
	}
	ACCESS	read-write
	STATUS	mandatory
	DESCRIPTION
		" Indicates whether this ARP intf record is to be deleted or created "
	DEFVAL	{ created }
	::= { wfArpIntfEntry 1 }

wfArpEnable OBJECT-TYPE
	SYNTAX	INTEGER {
		enabled(1),
		disabled(2)
	}
	ACCESS	read-write
	STATUS	mandatory
	DESCRIPTION
		" Indicates whether this ARP intf record is to be enabled or disabled "
	DEFVAL	{ enabled }
	::= { wfArpIntfEntry 2 }

wfArpCctno OBJECT-TYPE
	SYNTAX	INTEGER
	ACCESS	read-only
	STATUS	mandatory
	DESCRIPTION
		" Which Circuit arp should run on "
	::= { wfArpIntfEntry 3 }

wfIpxBase	OBJECT IDENTIFIER ::= { wfIpxGroup 1 }

wfIpxBaseDelete OBJECT-TYPE
	SYNTAX	INTEGER {
		created(1),
		deleted(2)
	}
	ACCESS	read-write
	STATUS	mandatory
	DESCRIPTION
		"Create/Delete parameter. Default is created.
		     Users perform an SNMP SET operation on this
		     object in order to create/delete IPX."
	DEFVAL	{ created }
	::= { wfIpxBase 1 }

wfIpxBaseDisable OBJECT-TYPE
	SYNTAX	INTEGER {
		enabled(1),
		disabled(2)
	}
	ACCESS	read-write
	STATUS	mandatory
	DESCRIPTION
		"Enable/Disable parameter. Default is enabled.
		     Users perform an SNMP SET operation on this
		     object in order to enable/disable IPX."
	DEFVAL	{ enabled }
	::= { wfIpxBase 2 }

wfIpxBaseState OBJECT-TYPE
	SYNTAX	INTEGER {
		up(1),
		down(2),
		in(3),
		notpresent(4)
	}
	ACCESS	read-only
	STATUS	mandatory
	DESCRIPTION
		"The current state of the entire IPX."
	DEFVAL	{ notpresent }
	::= { wfIpxBase 3 }

wfIpxBaseCfgHostNumber OBJECT-TYPE
	SYNTAX	OCTET STRING
	ACCESS	read-write
	STATUS	mandatory
	DESCRIPTION
		" box generated hostnumber.                              "
	::= { wfIpxBase 4 }

wfIpxBaseActiveHostNumber OBJECT-TYPE
	SYNTAX	OCTET STRING
	ACCESS	read-only
	STATUS	mandatory
	DESCRIPTION
		" generated variable.                                    "
	::= { wfIpxBase 5 }

wfIpxBaseNetCount OBJECT-TYPE
	SYNTAX	Counter
	ACCESS	read-only
	STATUS	mandatory
	DESCRIPTION
		" Count the total number of nets in the box. "
	::= { wfIpxBase 6 }

wfIpxBaseServiceCount OBJECT-TYPE
	SYNTAX	Counter
	ACCESS	read-only
	STATUS	mandatory
	DESCRIPTION
		" Count the total number of saps in the box. "
	::= { wfIpxBase 7 }

wfIpxBaseLogFilter OBJECT-TYPE
	SYNTAX	INTEGER {
		debug(1),
		info(2),
		trace(16),
		debuginfo(3),
		debugtrace(17),
		infotrace(18),
		debuginfotrace(19)
	}
	ACCESS	read-write
	STATUS	mandatory
	DESCRIPTION
		" Filter out some log messages, Default filters out
		 debugs, info, and trace messages."
	DEFVAL	{ trace }
	::= { wfIpxBase 8 }

wfIpxBaseNetTblSize OBJECT-TYPE
	SYNTAX	INTEGER {
		size(250)
	}
	ACCESS	read-write
	STATUS	mandatory
	DESCRIPTION
		" Tell me how much space to set aside when creating the
		 forwarding and network tables. "
	DEFVAL	{ size }
	::= { wfIpxBase 9 }

wfIpxBaseRtEntryTable OBJECT-TYPE
	SYNTAX	SEQUENCE OF WfIpxBaseRtEntry
	ACCESS	not-accessible
	STATUS	mandatory
	DESCRIPTION
		" The table of Elements in IPX's routing table "
	::= { wfIpxGroup 2 }

wfIpxBaseRtEntry OBJECT-TYPE
	SYNTAX	WfIpxBaseRtEntry
	ACCESS	not-accessible
	STATUS	mandatory
	DESCRIPTION
		" An entry in the Routing Table "
	INDEX	{ wfIpxBaseRouteDest }
	::= { wfIpxBaseRtEntryTable 1 }

WfIpxBaseRtEntry ::= SEQUENCE {
	wfIpxBaseRouteDest
		OCTET STRING,
	wfIpxBaseRouteIfIndex
		INTEGER,
	wfIpxBaseRouteMetric
		INTEGER,
	wfIpxBaseRouteNextHopNetwork
		OCTET STRING,
	wfIpxBaseRouteNextHopHost
		OCTET STRING,
	wfIpxBaseRouteType
		INTEGER,
	wfIpxBaseRouteProto
		INTEGER,
	wfIpxBaseRouteAge
		INTEGER,
	wfIpxBaseRouteInfo
		OCTET STRING
}

wfIpxBaseRouteDest OBJECT-TYPE
	SYNTAX	OCTET STRING
	ACCESS	read-only
	STATUS	mandatory
	DESCRIPTION
		" Multiple routes to a single
		     destination can appear in the table, but access to
		     such multiple entries is dependent on the table-
		     access mechanisms defined by the network
		     management protocol in use."
	::= { wfIpxBaseRtEntry 1 }

wfIpxBaseRouteIfIndex OBJECT-TYPE
	SYNTAX	INTEGER
	ACCESS	read-only
	STATUS	mandatory
	DESCRIPTION
		"The index value which uniquely identifies the
		     local interface through which the next hop of this
		     route should be reached.  The interface identified
		     by a particular value of this index is the same
		     interface as identified by the same value of
		     ifIndex."
	::= { wfIpxBaseRtEntry 2 }

wfIpxBaseRouteMetric OBJECT-TYPE
	SYNTAX	INTEGER
	ACCESS	read-only
	STATUS	mandatory
	DESCRIPTION
		"The primary routing metric for this route. The
		     semantics of this metric are determined by the
		     routing-protocol specified in the route's
		     ipRouteProto value.  If this metric is not used,
		     its value should be set to -1."
	::= { wfIpxBaseRtEntry 3 }

wfIpxBaseRouteNextHopNetwork OBJECT-TYPE
	SYNTAX	OCTET STRING
	ACCESS	read-only
	STATUS	mandatory
	DESCRIPTION
		"(In the case of a route bound to an interface
		     which is realized via a broadcast media, the value
		     of this field is the agent's IPX address on that
		     interface.)"
	::= { wfIpxBaseRtEntry 4 }

wfIpxBaseRouteNextHopHost OBJECT-TYPE
	SYNTAX	OCTET STRING
	ACCESS	read-only
	STATUS	mandatory
	DESCRIPTION
		"
		       Full network.host_id address of nexthop host for
		       this network.
		     "
	::= { wfIpxBaseRtEntry 5 }

wfIpxBaseRouteType OBJECT-TYPE
	SYNTAX	INTEGER {
		other(1),
		invalid(2),
		direct(3),
		indirect(4),
		static(5)
	}
	ACCESS	read-only
	STATUS	mandatory
	DESCRIPTION
		"The type of route. Note that the values
		     direct(3) and indirect(4) refer to the notion of
		     direct and indirect routing in the IPX
		     architecture.
		     Setting this object to the value invalid(2) has
		     the effect of invalidating the corresponding entry
		     in the ipRouteTable object.  That is, it
		     effectively dissasociates the destination
		     identified with said entry from the route
		     identified with said entry.  It is an
		     implementation-specific matter as to whether the
		     agent removes an invalidated entry from the table.
		     nagement stations must be prepared
		     to receive tabular information from agents that
		     corresponds to entries not currently in use.
		     Proper interpretation of such entries requires
		     examination of the relevant ipRouteType object."
	::= { wfIpxBaseRtEntry 6 }

wfIpxBaseRouteProto OBJECT-TYPE
	SYNTAX	INTEGER {
		other(1),
		local(2),
		netmgmt(3),
		rip(4)
	}
	ACCESS	read-only
	STATUS	mandatory
	DESCRIPTION
		"The routing mechanism via which this route was
		     learned.  Inclusion of values for gateway routing
		     protocols is not intended to imply that hosts
		     should support those protocols."
	::= { wfIpxBaseRtEntry 7 }

wfIpxBaseRouteAge OBJECT-TYPE
	SYNTAX	INTEGER
	ACCESS	read-only
	STATUS	mandatory
	DESCRIPTION
		"The number of seconds since this route was last
		     updated or otherwise determined to be correct.
		     Note that no semantics of `too old' can be implied
		     except through knowledge of the routing protocol
		     by which the route was learned."
	::= { wfIpxBaseRtEntry 8 }

wfIpxBaseRouteInfo OBJECT-TYPE
	SYNTAX	OCTET STRING
	ACCESS	read-only
	STATUS	mandatory
	DESCRIPTION
		" A user-defined string which describes this Route entry "
	::= { wfIpxBaseRtEntry 9 }

wfIpxBaseSapEntryTable OBJECT-TYPE
	SYNTAX	SEQUENCE OF WfIpxBaseSapEntry
	ACCESS	not-accessible
	STATUS	mandatory
	DESCRIPTION
		" The table of Elements in IPX's SAP table "
	::= { wfIpxGroup 3 }

wfIpxBaseSapEntry OBJECT-TYPE
	SYNTAX	WfIpxBaseSapEntry
	ACCESS	not-accessible
	STATUS	mandatory
	DESCRIPTION
		" An entry in the Routing Table "
	INDEX	{ wfIpxBaseSapIndex }
	::= { wfIpxBaseSapEntryTable 1 }

WfIpxBaseSapEntry ::= SEQUENCE {
	wfIpxBaseSapType
		OCTET STRING,
	wfIpxBaseSapNetwork
		OCTET STRING,
	wfIpxBaseSapHost
		OCTET STRING,
	wfIpxBaseSapSocket
		OCTET STRING,
	wfIpxBaseSapName
		DisplayString,
	wfIpxBaseSapAge
		INTEGER,
	wfIpxBaseSapHops
		INTEGER,
	wfIpxBaseSapIndex
		OCTET STRING,
	wfIpxBaseSapIntf
		OCTET STRING
}

wfIpxBaseSapType OBJECT-TYPE
	SYNTAX	OCTET STRING
	ACCESS	read-only
	STATUS	mandatory
	DESCRIPTION
		"
		     Multiple routes to a single
		     destination can appear in the table, but access to
		     such multiple entries is dependent on the table-
		     access mechanisms defined by the network
		     management protocol in use.
		     "
	::= { wfIpxBaseSapEntry 1 }

wfIpxBaseSapNetwork OBJECT-TYPE
	SYNTAX	OCTET STRING
	ACCESS	read-only
	STATUS	mandatory
	DESCRIPTION
		"
		      The network address of this service.
		    "
	::= { wfIpxBaseSapEntry 2 }

wfIpxBaseSapHost OBJECT-TYPE
	SYNTAX	OCTET STRING
	ACCESS	read-only
	STATUS	mandatory
	DESCRIPTION
		"
		      The host address for this service.
		     "
	::= { wfIpxBaseSapEntry 3 }

wfIpxBaseSapSocket OBJECT-TYPE
	SYNTAX	OCTET STRING
	ACCESS	read-only
	STATUS	mandatory
	DESCRIPTION
		"
		       The socket for this particular service
		      "
	::= { wfIpxBaseSapEntry 4 }

wfIpxBaseSapName OBJECT-TYPE
	SYNTAX	DisplayString
	ACCESS	read-only
	STATUS	mandatory
	DESCRIPTION
		"
		       The server name.
		     "
	::= { wfIpxBaseSapEntry 5 }

wfIpxBaseSapAge OBJECT-TYPE
	SYNTAX	INTEGER
	ACCESS	read-only
	STATUS	mandatory
	DESCRIPTION
		"
		      The number of seconds  since  SAP entry has been updated.
		      "
	::= { wfIpxBaseSapEntry 6 }

wfIpxBaseSapHops OBJECT-TYPE
	SYNTAX	INTEGER
	ACCESS	read-only
	STATUS	mandatory
	DESCRIPTION
		"
		        The number of Hops away service is from router.
		      "
	::= { wfIpxBaseSapEntry 7 }

wfIpxBaseSapIndex OBJECT-TYPE
	SYNTAX	OCTET STRING
	ACCESS	read-only
	STATUS	mandatory
	DESCRIPTION
		"
		        Index string comprised of type.network.hostid.socket.
		        Makes sorting easier and its a ah work around.
		      "
	::= { wfIpxBaseSapEntry 8 }

wfIpxBaseSapIntf OBJECT-TYPE
	SYNTAX	OCTET STRING
	ACCESS	read-only
	STATUS	mandatory
	DESCRIPTION
		"
		        Network Address of Nexthop Interface.
		       "
	::= { wfIpxBaseSapEntry 9 }

wfIpxInterfaceTable OBJECT-TYPE
	SYNTAX	SEQUENCE OF WfIpxInterfaceEntry
	ACCESS	not-accessible
	STATUS	mandatory
	DESCRIPTION
		" The network interface record "
	::= { wfIpxGroup 4 }

wfIpxInterfaceEntry OBJECT-TYPE
	SYNTAX	WfIpxInterfaceEntry
	ACCESS	not-accessible
	STATUS	mandatory
	DESCRIPTION
		" An entry in the Routing Table "
	INDEX	{ wfIpxInterfaceNetworkNumber,
		wfIpxInterfaceCircuit }
	::= { wfIpxInterfaceTable 1 }

WfIpxInterfaceEntry ::= SEQUENCE {
	wfIpxInterfaceIndex
		INTEGER,
	wfIpxInterfaceDelete
		INTEGER,
	wfIpxInterfaceDisable
		INTEGER,
	wfIpxInterfaceState
		INTEGER,
	wfIpxInterfaceCircuit
		INTEGER,
	wfIpxInterfaceNetworkNumber
		OCTET STRING,
	wfIpxInterfaceCost
		INTEGER,
	wfIpxInterfaceXsumOn
		INTEGER,
	wfIpxInterfaceCfgEncaps
		INTEGER,
	wfIpxInterfaceMacAddress
		OCTET STRING,
	wfIpxInterfaceSMDSGroupAddress
		OCTET STRING,
	wfIpxInterfaceMaxInfo
		INTEGER,
	wfIpxInterfaceInReceives
		Counter,
	wfIpxInterfaceInHdrErrors
		Counter,
	wfIpxInterfaceInAddrErrors
		Counter,
	wfIpxInterfaceForwDatagrams
		Counter,
	wfIpxInterfaceInUnknownProtos
		Counter,
	wfIpxInterfaceInDiscards
		Counter,
	wfIpxInterfaceInDelivers
		Counter,
	wfIpxInterfaceOutRequests
		Counter,
	wfIpxInterfaceOutDiscards
		Counter,
	wfIpxInterfaceOutNoRoutes
		Counter,
	wfIpxInterfaceTrEndStation
		INTEGER,
	wfIpxInterfaceNetbiosAccept
		INTEGER,
	wfIpxInterfaceNetbiosDeliver
		INTEGER,
	wfIpxInterfaceWanSapPeriod
		INTEGER,
	wfIpxInterfaceFRBcast
		OCTET STRING,
	wfIpxInterfaceFRMcast
		OCTET STRING,
	wfIpxInterfaceEncaps
		INTEGER,
	wfIpxInterfaceSplit
		INTEGER,
	wfIpxInterfaceCacheHit
		Counter
}

wfIpxInterfaceIndex OBJECT-TYPE
	SYNTAX	INTEGER
	ACCESS	read-only
	STATUS	mandatory
	DESCRIPTION
		"A unique value for each IPX interface. Its value
		    ranges between 1 and the value of MAXCIRCUITS."
	::= { wfIpxInterfaceEntry 1 }

wfIpxInterfaceDelete OBJECT-TYPE
	SYNTAX	INTEGER {
		created(1),
		deleted(2)
	}
	ACCESS	read-write
	STATUS	mandatory
	DESCRIPTION
		"Create/Delete parameter. Default is created.
		     Users perform an SNMP SET operation on this
		     object in order to create/delete an IPX interface."
	DEFVAL	{ created }
	::= { wfIpxInterfaceEntry 2 }

wfIpxInterfaceDisable OBJECT-TYPE
	SYNTAX	INTEGER {
		enabled(1),
		disabled(2)
	}
	ACCESS	read-write
	STATUS	mandatory
	DESCRIPTION
		"Enable/Disable parameter. Default is enabled.
		     Users perform an SNMP SET operation on this
		     object in order to enable/disable an IPX interface."
	DEFVAL	{ enabled }
	::= { wfIpxInterfaceEntry 3 }

wfIpxInterfaceState OBJECT-TYPE
	SYNTAX	INTEGER {
		up(1),
		down(2),
		init(3),
		notpresent(4)
	}
	ACCESS	read-only
	STATUS	mandatory
	DESCRIPTION
		"The current state of the IPX interface"
	DEFVAL	{ notpresent }
	::= { wfIpxInterfaceEntry 4 }

wfIpxInterfaceCircuit OBJECT-TYPE
	SYNTAX	INTEGER
	ACCESS	read-only
	STATUS	mandatory
	DESCRIPTION
		" The Circuit Number that this interface runs over"
	::= { wfIpxInterfaceEntry 5 }

wfIpxInterfaceNetworkNumber OBJECT-TYPE
	SYNTAX	OCTET STRING
	ACCESS	read-only
	STATUS	mandatory
	DESCRIPTION
		" The IPX Address to which this entry's addressing information
		       pertains "
	::= { wfIpxInterfaceEntry 6 }

wfIpxInterfaceCost OBJECT-TYPE
	SYNTAX	INTEGER {
		cost(1)
	}
	ACCESS	read-write
	STATUS	mandatory
	DESCRIPTION
		" The Cost associated with the IPX Address of this entry "
	DEFVAL	{ cost }
	::= { wfIpxInterfaceEntry 7 }

wfIpxInterfaceXsumOn OBJECT-TYPE
	SYNTAX	INTEGER {
		enabled(1),
		disabled(2)
	}
	ACCESS	read-write
	STATUS	mandatory
	DESCRIPTION
		" Flag for checksums "
	DEFVAL	{ enabled }
	::= { wfIpxInterfaceEntry 8 }

wfIpxInterfaceCfgEncaps OBJECT-TYPE
	SYNTAX	INTEGER {
		ethernet(1),
		lsap(2),
		novell(3),
		snap(4)
	}
	ACCESS	read-write
	STATUS	mandatory
	DESCRIPTION
		"
		      The encapsulation method associated with this interface
		      chosen by the user but not necessarily the one used. 
		      (See wfIpxInterfaceEncaps)
		    "
	DEFVAL	{ ethernet }
	::= { wfIpxInterfaceEntry 9 }

wfIpxInterfaceMacAddress OBJECT-TYPE
	SYNTAX	OCTET STRING
	ACCESS	read-only
	STATUS	mandatory
	DESCRIPTION
		"
		       The MacAddress of this interface 
		       this port will receive or transmit.
		     "
	::= { wfIpxInterfaceEntry 10 }

wfIpxInterfaceSMDSGroupAddress OBJECT-TYPE
	SYNTAX	OCTET STRING
	ACCESS	read-only
	STATUS	mandatory
	DESCRIPTION
		" The SMDS group address "
	::= { wfIpxInterfaceEntry 11 }

wfIpxInterfaceMaxInfo OBJECT-TYPE
	SYNTAX	INTEGER
	ACCESS	read-only
	STATUS	mandatory
	DESCRIPTION
		"The maximum size of the INFO (non-MAC) field that this port will receive or transmit."
	::= { wfIpxInterfaceEntry 12 }

wfIpxInterfaceInReceives OBJECT-TYPE
	SYNTAX	Counter
	ACCESS	read-only
	STATUS	mandatory
	DESCRIPTION
		"The total number of input datagrams received from
		                      interfaces, including those received in error."
	::= { wfIpxInterfaceEntry 13 }

wfIpxInterfaceInHdrErrors OBJECT-TYPE
	SYNTAX	Counter
	ACCESS	read-only
	STATUS	mandatory
	DESCRIPTION
		"The number of input datagrams discarded due to
		     errors in their IPX headers, including bad
		     checksums, version number mismatch, other format
		     errors, time-to-live exceeded, errors discovered
		     in processing their IPX options, etc."
	::= { wfIpxInterfaceEntry 14 }

wfIpxInterfaceInAddrErrors OBJECT-TYPE
	SYNTAX	Counter
	ACCESS	read-only
	STATUS	mandatory
	DESCRIPTION
		"The number of input datagrams discarded because
		     the IPX address in their IPX header's destination
		     field was not a valid address to be received at
		     this entity.
		      "
	::= { wfIpxInterfaceEntry 15 }

wfIpxInterfaceForwDatagrams OBJECT-TYPE
	SYNTAX	Counter
	ACCESS	read-only
	STATUS	mandatory
	DESCRIPTION
		"The number of input datagrams for which this
		     entity was not their final IPX destination, as a
		     result of which an attempt was made to find a
		     route to forward them to that final destination.
		     In entities which do not act as IPX Gateways, this
		     counter will include only those packets which were
		     Source-Routed via this entity, and the Source-
		     Route option processing was successful."
	::= { wfIpxInterfaceEntry 16 }

wfIpxInterfaceInUnknownProtos OBJECT-TYPE
	SYNTAX	Counter
	ACCESS	read-only
	STATUS	mandatory
	DESCRIPTION
		"The number of locally-addressed datagrams
		     received successfully but discarded because of an
		     unknown or unsupported protocol."
	::= { wfIpxInterfaceEntry 17 }

wfIpxInterfaceInDiscards OBJECT-TYPE
	SYNTAX	Counter
	ACCESS	read-only
	STATUS	mandatory
	DESCRIPTION
		"The number of input IPX datagrams for which no
		     problems were encountered to prevent their
		     continued processing, but which were discarded
		     (e.g., for lack of buffer space).  Note that this
		     counter does not include any datagrams discarded
		     while awaiting re-assembly."
	::= { wfIpxInterfaceEntry 18 }

wfIpxInterfaceInDelivers OBJECT-TYPE
	SYNTAX	Counter
	ACCESS	read-only
	STATUS	mandatory
	DESCRIPTION
		"
		      The total number of input datagrams successfully
		      delivered to IPX user-protocols .
		    "
	::= { wfIpxInterfaceEntry 19 }

wfIpxInterfaceOutRequests OBJECT-TYPE
	SYNTAX	Counter
	ACCESS	read-only
	STATUS	mandatory
	DESCRIPTION
		"
		     The total number of IPX datagrams which local IPX
		     user-protocols supplied to IPX in
		     requests for transmission.  Note that this counter
		     does not include any datagrams counted in
		     ipxForwDatagrams.
		     "
	::= { wfIpxInterfaceEntry 20 }

wfIpxInterfaceOutDiscards OBJECT-TYPE
	SYNTAX	Counter
	ACCESS	read-only
	STATUS	mandatory
	DESCRIPTION
		"The number of output IPX datagrams for which no
		     problem was encountered to prevent their
		     transmission to their destination, but which were
		     discarded (e.g., for lack of buffer space).  Note
		     that this counter would include datagrams counted
		     in ipForwDatagrams if any such packets met this
		     (discretionary) discard criterion."
	::= { wfIpxInterfaceEntry 21 }

wfIpxInterfaceOutNoRoutes OBJECT-TYPE
	SYNTAX	Counter
	ACCESS	read-only
	STATUS	mandatory
	DESCRIPTION
		"The number of IPX datagrams discarded because no
		     route could be found to transmit them to their
		     destination.  Note that this counter includes any
		     packets counted in ipForwDatagrams which meet this
		     `no-route' criterion.  Note that this includes any
		     datagarms which a host cannot route because all of
		     its default gateways are down."
	::= { wfIpxInterfaceEntry 22 }

wfIpxInterfaceTrEndStation OBJECT-TYPE
	SYNTAX	INTEGER {
		enabled(1),
		disabled(2)
	}
	ACCESS	read-write
	STATUS	mandatory
	DESCRIPTION
		" Source Routing flag "
	DEFVAL	{ disabled }
	::= { wfIpxInterfaceEntry 23 }

wfIpxInterfaceNetbiosAccept OBJECT-TYPE
	SYNTAX	INTEGER {
		enabled(1),
		disabled(2)
	}
	ACCESS	read-write
	STATUS	mandatory
	DESCRIPTION
		" Accept NetBios All Networks Broadcast Packets "
	DEFVAL	{ enabled }
	::= { wfIpxInterfaceEntry 24 }

wfIpxInterfaceNetbiosDeliver OBJECT-TYPE
	SYNTAX	INTEGER {
		enabled(1),
		disabled(2)
	}
	ACCESS	read-write
	STATUS	mandatory
	DESCRIPTION
		" Deliver NetBios All Networks Broadcast Packets "
	DEFVAL	{ enabled }
	::= { wfIpxInterfaceEntry 25 }

wfIpxInterfaceWanSapPeriod OBJECT-TYPE
	SYNTAX	INTEGER {
		default(1)
	}
	ACCESS	read-write
	STATUS	mandatory
	DESCRIPTION
		" Timer for Sap entries over WAN "
	DEFVAL	{ default }
	::= { wfIpxInterfaceEntry 26 }

wfIpxInterfaceFRBcast OBJECT-TYPE
	SYNTAX	OCTET STRING
	ACCESS	read-write
	STATUS	mandatory
	DESCRIPTION
		" Configurable Frame Relay broadcast address "
	::= { wfIpxInterfaceEntry 27 }

wfIpxInterfaceFRMcast OBJECT-TYPE
	SYNTAX	OCTET STRING
	ACCESS	read-write
	STATUS	mandatory
	DESCRIPTION
		" Configurable Frame Relay multicast address "
	::= { wfIpxInterfaceEntry 28 }

wfIpxInterfaceEncaps OBJECT-TYPE
	SYNTAX	INTEGER {
		ethernet(1),
		lsap(2),
		novell(3),
		snap(4)
	}
	ACCESS	read-only
	STATUS	mandatory
	DESCRIPTION
		" The Active or final encapsulation method associated with
		      this interface as determined by the router's implementation
		      of encapsulation algorithms (rules, restrictions) based on media type.
		   "
	DEFVAL	{ ethernet }
	::= { wfIpxInterfaceEntry 29 }

wfIpxInterfaceSplit OBJECT-TYPE
	SYNTAX	INTEGER {
		enabled(1),
		disabled(2)
	}
	ACCESS	read-write
	STATUS	mandatory
	DESCRIPTION
		" Comes into to play for non full-meshed WAN networks (Frame Relay)"
	DEFVAL	{ enabled }
	::= { wfIpxInterfaceEntry 30 }

wfIpxInterfaceCacheHit OBJECT-TYPE
	SYNTAX	Counter
	ACCESS	read-only
	STATUS	mandatory
	DESCRIPTION
		" Will provide information that will determine the usefullness of caching. "
	::= { wfIpxInterfaceEntry 31 }

wfIpxRipIntfTable OBJECT-TYPE
	SYNTAX	SEQUENCE OF WfIpxRipIntfEntry
	ACCESS	not-accessible
	STATUS	mandatory
	DESCRIPTION
		" The list of RIP interfaces "
	::= { wfIpxGroup 5 }

wfIpxRipIntfEntry OBJECT-TYPE
	SYNTAX	WfIpxRipIntfEntry
	ACCESS	not-accessible
	STATUS	mandatory
	DESCRIPTION
		" An entry in the Routing Table "
	INDEX	{ wfIpxRipInterfaceIndex }
	::= { wfIpxRipIntfTable 1 }

WfIpxRipIntfEntry ::= SEQUENCE {
	wfIpxRipInterfaceDelete
		INTEGER,
	wfIpxRipInterfaceDisable
		INTEGER,
	wfIpxRipInterfaceState
		INTEGER,
	wfIpxRipInterfaceIndex
		OCTET STRING,
	wfIpxRipInterfaceSupply
		INTEGER,
	wfIpxRipInterfaceListen
		INTEGER
}

wfIpxRipInterfaceDelete OBJECT-TYPE
	SYNTAX	INTEGER {
		created(1),
		deleted(2)
	}
	ACCESS	read-write
	STATUS	mandatory
	DESCRIPTION
		"Create/Delete parameter. Default is created.
		     Users perform an SNMP SET operation on this
		     object in order to create/delete an RIP Interface instance."
	DEFVAL	{ created }
	::= { wfIpxRipIntfEntry 1 }

wfIpxRipInterfaceDisable OBJECT-TYPE
	SYNTAX	INTEGER {
		enabled(1),
		disabled(2)
	}
	ACCESS	read-write
	STATUS	mandatory
	DESCRIPTION
		"Enable/Disable parameter. Default is enabled.
		     Users perform an SNMP SET operation on this
		     object in order to enable/disable an RIP instance."
	DEFVAL	{ enabled }
	::= { wfIpxRipIntfEntry 2 }

wfIpxRipInterfaceState OBJECT-TYPE
	SYNTAX	INTEGER {
		up(1),
		down(2),
		init(3),
		notpresent(4)
	}
	ACCESS	read-only
	STATUS	mandatory
	DESCRIPTION
		"The current state of RIP on this interface."
	DEFVAL	{ notpresent }
	::= { wfIpxRipIntfEntry 3 }

wfIpxRipInterfaceIndex OBJECT-TYPE
	SYNTAX	OCTET STRING
	ACCESS	read-only
	STATUS	mandatory
	DESCRIPTION
		"The IPX interface to run RIP on (instance id )."
	::= { wfIpxRipIntfEntry 4 }

wfIpxRipInterfaceSupply OBJECT-TYPE
	SYNTAX	INTEGER {
		enabled(1),
		disabled(2)
	}
	ACCESS	read-write
	STATUS	mandatory
	DESCRIPTION
		"Transmit RIP packets."
	DEFVAL	{ enabled }
	::= { wfIpxRipIntfEntry 5 }

wfIpxRipInterfaceListen OBJECT-TYPE
	SYNTAX	INTEGER {
		enabled(1),
		disabled(2)
	}
	ACCESS	read-write
	STATUS	mandatory
	DESCRIPTION
		"Receive RIP packets."
	DEFVAL	{ enabled }
	::= { wfIpxRipIntfEntry 6 }

wfIpxAdjacentHostTable OBJECT-TYPE
	SYNTAX	SEQUENCE OF WfIpxAdjacentHostEntry
	ACCESS	not-accessible
	STATUS	mandatory
	DESCRIPTION
		"  must be configured for a nexthop host.                     "
	::= { wfIpxGroup 6 }

wfIpxAdjacentHostEntry OBJECT-TYPE
	SYNTAX	WfIpxAdjacentHostEntry
	ACCESS	not-accessible
	STATUS	mandatory
	DESCRIPTION
		" An entry in the Adjacent Host Table "
	INDEX	{ wfIpxAhTargHostNetwork,
		wfIpxAhTargHostId }
	::= { wfIpxAdjacentHostTable 1 }

WfIpxAdjacentHostEntry ::= SEQUENCE {
	wfIpxAhDelete
		INTEGER,
	wfIpxAhDisable
		INTEGER,
	wfIpxAhTargHostNetwork
		OCTET STRING,
	wfIpxAhTargHostId
		OCTET STRING,
	wfIpxAhNextHopIntf
		OCTET STRING,
	wfIpxAhDlci
		OCTET STRING
}

wfIpxAhDelete OBJECT-TYPE
	SYNTAX	INTEGER {
		created(1),
		deleted(2)
	}
	ACCESS	read-write
	STATUS	mandatory
	DESCRIPTION
		"Create/Delete parameter. Default is created.
		     Users perform an SNMP SET operation on this
		     object in order to create/delete the IPX
		     Static Host."
	DEFVAL	{ created }
	::= { wfIpxAdjacentHostEntry 1 }

wfIpxAhDisable OBJECT-TYPE
	SYNTAX	INTEGER {
		enabled(1),
		disabled(2)
	}
	ACCESS	read-write
	STATUS	mandatory
	DESCRIPTION
		"Enable/Disable parameter. Default is enabled.
		     Users perform an SNMP SET operation on this
		     object in order to enable/disable this IPX
		     Static Route."
	DEFVAL	{ enabled }
	::= { wfIpxAdjacentHostEntry 2 }

wfIpxAhTargHostNetwork OBJECT-TYPE
	SYNTAX	OCTET STRING
	ACCESS	read-only
	STATUS	mandatory
	DESCRIPTION
		"The network address of the static host. "
	::= { wfIpxAdjacentHostEntry 3 }

wfIpxAhTargHostId OBJECT-TYPE
	SYNTAX	OCTET STRING
	ACCESS	read-only
	STATUS	mandatory
	DESCRIPTION
		" The Address of this static host. "
	::= { wfIpxAdjacentHostEntry 4 }

wfIpxAhNextHopIntf OBJECT-TYPE
	SYNTAX	OCTET STRING
	ACCESS	read-write
	STATUS	mandatory
	DESCRIPTION
		" The Next Hop Interface Network Address "
	::= { wfIpxAdjacentHostEntry 5 }

wfIpxAhDlci OBJECT-TYPE
	SYNTAX	OCTET STRING
	ACCESS	read-write
	STATUS	mandatory
	DESCRIPTION
		" The next Hop Host address "
	::= { wfIpxAdjacentHostEntry 6 }

wfIpxStaticRouteTable OBJECT-TYPE
	SYNTAX	SEQUENCE OF WfIpxStaticRouteEntry
	ACCESS	not-accessible
	STATUS	mandatory
	DESCRIPTION
		" The list of static routes used for Configuring IPX "
	::= { wfIpxGroup 7 }

wfIpxStaticRouteEntry OBJECT-TYPE
	SYNTAX	WfIpxStaticRouteEntry
	ACCESS	not-accessible
	STATUS	mandatory
	DESCRIPTION
		" An entry in the Routing Table "
	INDEX	{ wfIpxSrTargNetwork,
		wfIpxSrNextHopNetwork }
	::= { wfIpxStaticRouteTable 1 }

WfIpxStaticRouteEntry ::= SEQUENCE {
	wfIpxSrDelete
		INTEGER,
	wfIpxSrDisable
		INTEGER,
	wfIpxSrTargNetwork
		OCTET STRING,
	wfIpxSrCost
		INTEGER,
	wfIpxSrNextHopNetwork
		OCTET STRING,
	wfIpxSrNextHopHost
		OCTET STRING,
	wfIpxSrTargNetworkRt
		INTEGER
}

wfIpxSrDelete OBJECT-TYPE
	SYNTAX	INTEGER {
		created(1),
		deleted(2)
	}
	ACCESS	read-write
	STATUS	mandatory
	DESCRIPTION
		"Create/Delete parameter. Default is created.
		     Users perform an SNMP SET operation on this
		     object in order to create/delete the IPX
		     Static Route."
	DEFVAL	{ created }
	::= { wfIpxStaticRouteEntry 1 }

wfIpxSrDisable OBJECT-TYPE
	SYNTAX	INTEGER {
		enabled(1),
		disabled(2)
	}
	ACCESS	read-write
	STATUS	mandatory
	DESCRIPTION
		"Enable/Disable parameter. Default is enabled.
		     Users perform an SNMP SET operation on this
		     object in order to enable/disable this IPX
		     Static Route."
	DEFVAL	{ enabled }
	::= { wfIpxStaticRouteEntry 2 }

wfIpxSrTargNetwork OBJECT-TYPE
	SYNTAX	OCTET STRING
	ACCESS	read-only
	STATUS	mandatory
	DESCRIPTION
		" The Address of this static route "
	::= { wfIpxStaticRouteEntry 3 }

wfIpxSrCost OBJECT-TYPE
	SYNTAX	INTEGER
	ACCESS	read-write
	STATUS	mandatory
	DESCRIPTION
		" The Cost of this Static Route "
	::= { wfIpxStaticRouteEntry 4 }

wfIpxSrNextHopNetwork OBJECT-TYPE
	SYNTAX	OCTET STRING
	ACCESS	read-only
	STATUS	mandatory
	DESCRIPTION
		" The Next Hop IPX Address "
	::= { wfIpxStaticRouteEntry 5 }

wfIpxSrNextHopHost OBJECT-TYPE
	SYNTAX	OCTET STRING
	ACCESS	read-write
	STATUS	mandatory
	DESCRIPTION
		" The next Hop Host address "
	::= { wfIpxStaticRouteEntry 6 }

wfIpxSrTargNetworkRt OBJECT-TYPE
	SYNTAX	INTEGER
	ACCESS	read-only
	STATUS	mandatory
	DESCRIPTION
		" The Route Identifier Which numbered route this is to be "
	::= { wfIpxStaticRouteEntry 7 }

wfIpxNetBiosStaticRouteTable OBJECT-TYPE
	SYNTAX	SEQUENCE OF WfIpxNetBiosStaticRouteEntry
	ACCESS	not-accessible
	STATUS	mandatory
	DESCRIPTION
		" The list of static routes used for Configuring IPX "
	::= { wfIpxGroup 8 }

wfIpxNetBiosStaticRouteEntry OBJECT-TYPE
	SYNTAX	WfIpxNetBiosStaticRouteEntry
	ACCESS	not-accessible
	STATUS	mandatory
	DESCRIPTION
		" An entry in the Routing Table "
	INDEX	{ wfIpxNetBiosSrTargNetwork,
		wfIpxNetBiosSrIntf }
	::= { wfIpxNetBiosStaticRouteTable 1 }

WfIpxNetBiosStaticRouteEntry ::= SEQUENCE {
	wfIpxNetBiosSrDelete
		INTEGER,
	wfIpxNetBiosSrDisable
		INTEGER,
	wfIpxNetBiosSrTargNetwork
		OCTET STRING,
	wfIpxNetBiosSrName
		OCTET STRING,
	wfIpxNetBiosSrIntf
		OCTET STRING,
	wfIpxNetBiosSrIndex
		INTEGER
}

wfIpxNetBiosSrDelete OBJECT-TYPE
	SYNTAX	INTEGER {
		created(1),
		deleted(2)
	}
	ACCESS	read-write
	STATUS	mandatory
	DESCRIPTION
		"Create/Delete parameter. Default is created.
		     Users perform an SNMP SET operation on this
		     object in order to create/delete the IPX NETBIOS
		     Static Route."
	DEFVAL	{ created }
	::= { wfIpxNetBiosStaticRouteEntry 1 }

wfIpxNetBiosSrDisable OBJECT-TYPE
	SYNTAX	INTEGER {
		enabled(1),
		disabled(2)
	}
	ACCESS	read-write
	STATUS	mandatory
	DESCRIPTION
		"Enable/Disable parameter. Default is enabled.
		     Users perform an SNMP SET operation on this
		     object in order to enable/disable this IPX NETBIOS
		     Static Route."
	DEFVAL	{ enabled }
	::= { wfIpxNetBiosStaticRouteEntry 2 }

wfIpxNetBiosSrTargNetwork OBJECT-TYPE
	SYNTAX	OCTET STRING
	ACCESS	read-only
	STATUS	mandatory
	DESCRIPTION
		" The Address of this static route "
	::= { wfIpxNetBiosStaticRouteEntry 3 }

wfIpxNetBiosSrName OBJECT-TYPE
	SYNTAX	OCTET STRING
	ACCESS	read-write
	STATUS	mandatory
	DESCRIPTION
		" The Name of the Target Server "
	::= { wfIpxNetBiosStaticRouteEntry 4 }

wfIpxNetBiosSrIntf OBJECT-TYPE
	SYNTAX	OCTET STRING
	ACCESS	read-only
	STATUS	mandatory
	DESCRIPTION
		" The Interface Identifier for this static entry "
	::= { wfIpxNetBiosStaticRouteEntry 5 }

wfIpxNetBiosSrIndex OBJECT-TYPE
	SYNTAX	INTEGER
	ACCESS	read-only
	STATUS	mandatory
	DESCRIPTION
		" The Entry Index Which identifies this is entry "
	::= { wfIpxNetBiosStaticRouteEntry 6 }

wfIpxSapNetLvlFilterTable OBJECT-TYPE
	SYNTAX	SEQUENCE OF WfIpxSapNetLvlFilter
	ACCESS	not-accessible
	STATUS	mandatory
	DESCRIPTION
		" The list of Network Level SAP Filters "
	::= { wfIpxGroup 9 }

wfIpxSapNetLvlFilter OBJECT-TYPE
	SYNTAX	WfIpxSapNetLvlFilter
	ACCESS	not-accessible
	STATUS	mandatory
	DESCRIPTION
		" An entry in the Filter Table "
	INDEX	{ wfIpxSapNetLvlIntf,
		wfIpxSapNetLvlIndex }
	::= { wfIpxSapNetLvlFilterTable 1 }

WfIpxSapNetLvlFilter ::= SEQUENCE {
	wfIpxSapNetLvlDelete
		INTEGER,
	wfIpxSapNetLvlDisable
		INTEGER,
	wfIpxSapNetLvlTargNetwork
		OCTET STRING,
	wfIpxSapNetLvlType
		OCTET STRING,
	wfIpxSapNetLvlAction
		INTEGER,
	wfIpxSapNetLvlIntf
		OCTET STRING,
	wfIpxSapNetLvlIndex
		INTEGER
}

wfIpxSapNetLvlDelete OBJECT-TYPE
	SYNTAX	INTEGER {
		created(1),
		deleted(2)
	}
	ACCESS	read-write
	STATUS	mandatory
	DESCRIPTION
		"
		     Create/Delete parameter. Default is created.
		     Users perform an SNMP SET operation on this
		     object in order to create/delete the IPX
		     Sap network level filter.
		    "
	DEFVAL	{ created }
	::= { wfIpxSapNetLvlFilter 1 }

wfIpxSapNetLvlDisable OBJECT-TYPE
	SYNTAX	INTEGER {
		enabled(1),
		disabled(2)
	}
	ACCESS	read-write
	STATUS	mandatory
	DESCRIPTION
		"
		     Enable/Disable parameter. Default is enabled.
		     Users perform an SNMP SET operation on this
		     object in order to enable/disable this IPX
		     network level SAP filter.
		     "
	DEFVAL	{ enabled }
	::= { wfIpxSapNetLvlFilter 2 }

wfIpxSapNetLvlTargNetwork OBJECT-TYPE
	SYNTAX	OCTET STRING
	ACCESS	read-write
	STATUS	mandatory
	DESCRIPTION
		" The Target Network address to monitor "
	::= { wfIpxSapNetLvlFilter 3 }

wfIpxSapNetLvlType OBJECT-TYPE
	SYNTAX	OCTET STRING
	ACCESS	read-write
	STATUS	mandatory
	DESCRIPTION
		" The Type of service to monitor "
	::= { wfIpxSapNetLvlFilter 4 }

wfIpxSapNetLvlAction OBJECT-TYPE
	SYNTAX	INTEGER {
		active(1),
		inactive(2)
	}
	ACCESS	read-write
	STATUS	mandatory
	DESCRIPTION
		" The Action to take Advertise or not Advertise "
	DEFVAL	{ active }
	::= { wfIpxSapNetLvlFilter 5 }

wfIpxSapNetLvlIntf OBJECT-TYPE
	SYNTAX	OCTET STRING
	ACCESS	read-only
	STATUS	mandatory
	DESCRIPTION
		" The Interface identifier for this filter "
	::= { wfIpxSapNetLvlFilter 6 }

wfIpxSapNetLvlIndex OBJECT-TYPE
	SYNTAX	INTEGER
	ACCESS	read-only
	STATUS	mandatory
	DESCRIPTION
		" The Filter Index . "
	::= { wfIpxSapNetLvlFilter 7 }

wfIpxSapServtLvlFilterTable OBJECT-TYPE
	SYNTAX	SEQUENCE OF WfIpxSapServLvlFilter
	ACCESS	not-accessible
	STATUS	mandatory
	DESCRIPTION
		" The list of Server Level SAP Filters "
	::= { wfIpxGroup 10 }

wfIpxSapServLvlFilter OBJECT-TYPE
	SYNTAX	WfIpxSapServLvlFilter
	ACCESS	not-accessible
	STATUS	mandatory
	DESCRIPTION
		" An entry in the Filter Table "
	INDEX	{ wfIpxSapServLvlIntf,
		wfIpxSapServLvlIndex }
	::= { wfIpxSapServtLvlFilterTable 1 }

WfIpxSapServLvlFilter ::= SEQUENCE {
	wfIpxSapServLvlDelete
		INTEGER,
	wfIpxSapServLvlDisable
		INTEGER,
	wfIpxSapServLvlTargServer
		DisplayString,
	wfIpxSapServLvlType
		OCTET STRING,
	wfIpxSapServLvlAction
		INTEGER,
	wfIpxSapServLvlIntf
		OCTET STRING,
	wfIpxSapServLvlIndex
		INTEGER
}

wfIpxSapServLvlDelete OBJECT-TYPE
	SYNTAX	INTEGER {
		created(1),
		deleted(2)
	}
	ACCESS	read-write
	STATUS	mandatory
	DESCRIPTION
		"
		     Create/Delete parameter. Default is created.
		     Users perform an SNMP SET operation on this
		     object in order to create/delete the IPX
		     server-level SAP filter.
		     "
	DEFVAL	{ created }
	::= { wfIpxSapServLvlFilter 1 }

wfIpxSapServLvlDisable OBJECT-TYPE
	SYNTAX	INTEGER {
		enabled(1),
		disabled(2)
	}
	ACCESS	read-write
	STATUS	mandatory
	DESCRIPTION
		"
		     Enable/Disable parameter. Default is enabled.
		     Users perform an SNMP SET operation on this
		     object in order to enable/disable this IPX
		     server-level SAP filter.
		     "
	DEFVAL	{ enabled }
	::= { wfIpxSapServLvlFilter 2 }

wfIpxSapServLvlTargServer OBJECT-TYPE
	SYNTAX	DisplayString
	ACCESS	read-write
	STATUS	mandatory
	DESCRIPTION
		" The Server Name to monitor. "
	::= { wfIpxSapServLvlFilter 3 }

wfIpxSapServLvlType OBJECT-TYPE
	SYNTAX	OCTET STRING
	ACCESS	read-write
	STATUS	mandatory
	DESCRIPTION
		" Type of service File server, Printer, etc... "
	::= { wfIpxSapServLvlFilter 4 }

wfIpxSapServLvlAction OBJECT-TYPE
	SYNTAX	INTEGER {
		active(1),
		inactive(2)
	}
	ACCESS	read-write
	STATUS	mandatory
	DESCRIPTION
		" Associated Action (advertise or ignore )  "
	DEFVAL	{ active }
	::= { wfIpxSapServLvlFilter 5 }

wfIpxSapServLvlIntf OBJECT-TYPE
	SYNTAX	OCTET STRING
	ACCESS	read-only
	STATUS	mandatory
	DESCRIPTION
		" The Interface identifier for this filter "
	::= { wfIpxSapServLvlFilter 6 }

wfIpxSapServLvlIndex OBJECT-TYPE
	SYNTAX	INTEGER
	ACCESS	read-only
	STATUS	mandatory
	DESCRIPTION
		" The Filter Index . "
	::= { wfIpxSapServLvlFilter 7 }

wfIpxTrafficFilterTable OBJECT-TYPE
	SYNTAX	SEQUENCE OF WfIpxTrafficFilterEntry
	ACCESS	not-accessible
	STATUS	mandatory
	DESCRIPTION
		" IPX Traffic Filters "
	::= { wfIpxGroup 11 }

wfIpxTrafficFilterEntry OBJECT-TYPE
	SYNTAX	WfIpxTrafficFilterEntry
	ACCESS	not-accessible
	STATUS	mandatory
	DESCRIPTION
		" A traffic filter definition "
	INDEX	{ wfIpxTrafficFilterInterface,
		wfIpxTrafficFilterCircuit,
		wfIpxTrafficFilterRuleNumber,
		wfIpxTrafficFilterFragment }
	::= { wfIpxTrafficFilterTable 1 }

WfIpxTrafficFilterEntry ::= SEQUENCE {
	wfIpxTrafficFilterCreate
		INTEGER,
	wfIpxTrafficFilterEnable
		INTEGER,
	wfIpxTrafficFilterStatus
		INTEGER,
	wfIpxTrafficFilterCounter
		Counter,
	wfIpxTrafficFilterDefinition
		Opaque,
	wfIpxTrafficFilterReserved
		INTEGER,
	wfIpxTrafficFilterInterface
		OCTET STRING,
	wfIpxTrafficFilterCircuit
		INTEGER,
	wfIpxTrafficFilterRuleNumber
		INTEGER,
	wfIpxTrafficFilterFragment
		INTEGER
}

wfIpxTrafficFilterCreate OBJECT-TYPE
	SYNTAX	INTEGER {
		created(1),
		deleted(2)
	}
	ACCESS	read-write
	STATUS	mandatory
	DESCRIPTION
		" Defines the existence of the traffic filter rule:
		               created - traffic filter exists
		               delete - traffic filter does not exist and can be deleted. 
		        "
	DEFVAL	{ created }
	::= { wfIpxTrafficFilterEntry 1 }

wfIpxTrafficFilterEnable OBJECT-TYPE
	SYNTAX	INTEGER {
		enabled(1),
		disabled(2)
	}
	ACCESS	read-write
	STATUS	mandatory
	DESCRIPTION
		"
		                Defines whether or not the traffic filter rule should be used:
		                enabled - activate the rule.
		                disabled - inactivate the rule. 
		        "
	DEFVAL	{ enabled }
	::= { wfIpxTrafficFilterEntry 2 }

wfIpxTrafficFilterStatus OBJECT-TYPE
	SYNTAX	INTEGER {
		active(1),
		error(2),
		inactive(3)
	}
	ACCESS	read-only
	STATUS	mandatory
	DESCRIPTION
		" Defines the current status of the traffic filter:
		                inactive - the rule is not in use.
		                active - the rule is being used.
		                error - the application detected an error in the rule. "
	DEFVAL	{ inactive }
	::= { wfIpxTrafficFilterEntry 3 }

wfIpxTrafficFilterCounter OBJECT-TYPE
	SYNTAX	Counter
	ACCESS	read-only
	STATUS	mandatory
	DESCRIPTION
		" The number of received packets that have
		           matched this rule. "
	::= { wfIpxTrafficFilterEntry 4 }

wfIpxTrafficFilterDefinition OBJECT-TYPE
	SYNTAX	Opaque
	ACCESS	read-write
	STATUS	mandatory
	DESCRIPTION
		" The filter rule definition. "
	::= { wfIpxTrafficFilterEntry 5 }

wfIpxTrafficFilterReserved OBJECT-TYPE
	SYNTAX	INTEGER
	ACCESS	not-accessible
	STATUS	mandatory
	DESCRIPTION
		" Reserved field. "
	::= { wfIpxTrafficFilterEntry 6 }

wfIpxTrafficFilterInterface OBJECT-TYPE
	SYNTAX	OCTET STRING
	ACCESS	read-only
	STATUS	mandatory
	DESCRIPTION
		"
		           The network address of the IPX
		           interface to which this filter is applied. 
		         "
	::= { wfIpxTrafficFilterEntry 7 }

wfIpxTrafficFilterCircuit OBJECT-TYPE
	SYNTAX	INTEGER
	ACCESS	read-only
	STATUS	mandatory
	DESCRIPTION
		"
		           The ID of the Circuit to which the
		           filter is applied. 
		         "
	::= { wfIpxTrafficFilterEntry 8 }

wfIpxTrafficFilterRuleNumber OBJECT-TYPE
	SYNTAX	INTEGER
	ACCESS	read-only
	STATUS	mandatory
	DESCRIPTION
		" ID for the rule. "
	::= { wfIpxTrafficFilterEntry 9 }

wfIpxTrafficFilterFragment OBJECT-TYPE
	SYNTAX	INTEGER
	ACCESS	read-only
	STATUS	mandatory
	DESCRIPTION
		" Fragment number - for large rules. "
	::= { wfIpxTrafficFilterEntry 10 }

wfProtocols	OBJECT IDENTIFIER ::= { wfSoftwareConfig 1 }

wfIPROTOLoad OBJECT-TYPE
	SYNTAX	Counter
	ACCESS	read-write
	STATUS	mandatory
	DESCRIPTION
		" Bit mask for loading the IP routing suite (RIP, EGP, OSPF) on
		   slots 1-14.  The MSBit represents slot 1, the next most
		   significant bit represents slot 2, and so forth. "
	::= { wfProtocols 1 }

wfDECNETLoad OBJECT-TYPE
	SYNTAX	Counter
	ACCESS	read-write
	STATUS	mandatory
	DESCRIPTION
		" Bit mask for loading the DECNet router on slots 1-14. The MSBit
		   represents slot 1, the next most significant bit represents
		   slot 2, and so forth. "
	::= { wfProtocols 2 }

wfATLoad OBJECT-TYPE
	SYNTAX	Counter
	ACCESS	read-write
	STATUS	mandatory
	DESCRIPTION
		" Bit mask for loading the AppleTalk router on slots 1-14. The MSBit
		   represents slot 1, the next most significant bit represents
		   slot 2, and so forth. "
	::= { wfProtocols 3 }

wfXNSLoad OBJECT-TYPE
	SYNTAX	Counter
	ACCESS	read-write
	STATUS	mandatory
	DESCRIPTION
		" Bit mask for loading the XNS router on slots 1-14. The MSBit
		   represents slot 1, the next most significant bit represents
		   slot 2, and so forth. "
	::= { wfProtocols 4 }

wfIPXLoad OBJECT-TYPE
	SYNTAX	Counter
	ACCESS	read-write
	STATUS	mandatory
	DESCRIPTION
		" Bit mask for loading the IPX router on slots 1-14. The MSBit
		   represents slot 1, the next most significant bit represents
		   slot 2, and so forth. "
	::= { wfProtocols 5 }

wfOSILoad OBJECT-TYPE
	SYNTAX	Counter
	ACCESS	read-write
	STATUS	mandatory
	DESCRIPTION
		" Bit mask for loading the ISO router on slots 1-14. The MSBit
		   represents slot 1, the next most significant bit represents
		   slot 2, and so forth. "
	::= { wfProtocols 6 }

wfX25DTELoad OBJECT-TYPE
	SYNTAX	Counter
	ACCESS	read-write
	STATUS	mandatory
	DESCRIPTION
		" Bit mask for loading the X.25 DTE protocol on slots 1-14. The
		   MSBit represents slot 1, the next most significant bit
		   represents slot 2, and so forth. "
	::= { wfProtocols 7 }

wfX25DCELoad OBJECT-TYPE
	SYNTAX	Counter
	ACCESS	read-write
	STATUS	mandatory
	DESCRIPTION
		" Bit mask for loading the X.25 DCE protocol on slots 1-14. The
		   MSBit represents slot 1, the next most significant bit
		   represents slot 2, and so forth. "
	::= { wfProtocols 8 }

wfVINESLoad OBJECT-TYPE
	SYNTAX	Counter
	ACCESS	read-write
	STATUS	mandatory
	DESCRIPTION
		" Bit mask for loading the VINES router on slots 1-14. The MSBit
		   represents slot 1, the next most significant bit represents
		   slot 2, and so forth. "
	::= { wfProtocols 9 }

wfLinkModules	OBJECT IDENTIFIER ::= { wfSoftwareConfig 2 }

wfENETIILoad OBJECT-TYPE
	SYNTAX	Counter
	ACCESS	read-write
	STATUS	mandatory
	DESCRIPTION
		" Bit mask for loading the Ethernet II driver on slots 1-14. The
		   MSBit represents slot 1, the next most significant bit
		   represents slot 2, and so forth. "
	::= { wfLinkModules 1 }

wfQENETLoad OBJECT-TYPE
	SYNTAX	Counter
	ACCESS	read-write
	STATUS	mandatory
	DESCRIPTION
		" Bit mask for loading the Quad Ethernet driver on slots 1-14. The
		   MSBit represents slot 1, the next most significant bit
		   represents slot 2, and so forth. "
	::= { wfLinkModules 2 }

wfFDDILoad OBJECT-TYPE
	SYNTAX	Counter
	ACCESS	read-write
	STATUS	mandatory
	DESCRIPTION
		" Bit mask for loading the FDDI driver on slots 1-14. The MSBit
		   represents slot 1, the next most significant bit represents slot 2
		   and so forth. "
	::= { wfLinkModules 3 }

wfDSDELoad OBJECT-TYPE
	SYNTAX	Counter
	ACCESS	read-write
	STATUS	mandatory
	DESCRIPTION
		" Bit mask for loading the Dual Sync - Dual Enet driver on slots 1-14.
		   The MSBit represents slot 1, the next most significant bit
		   represents slot 2, and so forth. "
	::= { wfLinkModules 4 }

wfDSDEIILoad OBJECT-TYPE
	SYNTAX	Counter
	ACCESS	read-write
	STATUS	mandatory
	DESCRIPTION
		" Bit mask for loading the Dual Sync - Dual Enet II driver on slots
		   1-14.  The MSBit represents slot 1, the next most significant
		   bit represents slot 2, and so forth. "
	::= { wfLinkModules 5 }

wfQSYNCLoad OBJECT-TYPE
	SYNTAX	Counter
	ACCESS	read-write
	STATUS	mandatory
	DESCRIPTION
		" Bit mask for loading the Quad Sync driver on slots 1-14. The MSBit
		   represents slot 1, the next most significant bit represents
		   slot 2, and so forth. "
	::= { wfLinkModules 6 }

wfDTLoad OBJECT-TYPE
	SYNTAX	Counter
	ACCESS	read-write
	STATUS	mandatory
	DESCRIPTION
		" Bit mask for loading the Dual Token driver on slots 1-14. The MSBit
		   represents slot 1, the next most significant bit represents slot 2
		   and so forth. "
	::= { wfLinkModules 7 }

wfDSTLoad OBJECT-TYPE
	SYNTAX	Counter
	ACCESS	read-write
	STATUS	mandatory
	DESCRIPTION
		" Bit mask for loading the DST driver on slots 1-14. The MSBit
		   represents slot 1, the next most significant bit represents slot 2
		   and so forth. "
	::= { wfLinkModules 8 }

wfT1IILoad OBJECT-TYPE
	SYNTAX	Counter
	ACCESS	read-write
	STATUS	mandatory
	DESCRIPTION
		" Bit mask for loading the T1 II driver on slots 1-14. The MSBit
		   represents slot 1, the next most significant bit represents slot 2
		   and so forth. "
	::= { wfLinkModules 9 }

wfE1IILoad OBJECT-TYPE
	SYNTAX	Counter
	ACCESS	read-write
	STATUS	mandatory
	DESCRIPTION
		" Bit mask for loading the E1 II driver on slots 1-14. The MSBit
		   represents slot 1, the next most significant bit represents slot 2
		   and so forth. "
	::= { wfLinkModules 10 }

wfHSSILoad OBJECT-TYPE
	SYNTAX	Counter
	ACCESS	read-write
	STATUS	mandatory
	DESCRIPTION
		" Bit mask for loading the HSSI driver on slots 1-14. The MSBit
		   represents slot 1, the next most significant bit represents slot 2
		   and so forth. "
	::= { wfLinkModules 11 }

wfFNSDSELoad OBJECT-TYPE
	SYNTAX	Counter
	ACCESS	read-write
	STATUS	mandatory
	DESCRIPTION
		" Bit mask for loading the FNSDSE driver on slot 2 (FNES Only). The MSBit
		   represents slot 1, the next most significant bit represents slot 2
		   and so forth. "
	::= { wfLinkModules 12 }

wfFNSDSDTLoad OBJECT-TYPE
	SYNTAX	Counter
	ACCESS	read-write
	STATUS	mandatory
	DESCRIPTION
		" Bit mask for loading the FNSDSDT driver on slot 2 (FNTS Only). The MSBit
		   represents slot 1, the next most significant bit represents slot 2
		   and so forth. "
	::= { wfLinkModules 13 }

wfDrivers	OBJECT IDENTIFIER ::= { wfSoftwareConfig 3 }

wfLANCELoad OBJECT-TYPE
	SYNTAX	Counter
	ACCESS	read-write
	STATUS	mandatory
	DESCRIPTION
		" Bit mask for loading the LANCE chip driver on slots 1-14. The MSBit
		   represents slot 1, the next most significant bit represents slot 2
		   and so forth. "
	::= { wfDrivers 1 }

wfILACCLoad OBJECT-TYPE
	SYNTAX	Counter
	ACCESS	read-write
	STATUS	mandatory
	DESCRIPTION
		" Bit mask for loading the ILACC chip driver on slots 1-14. The MSBit
		   represents slot 1, the next most significant bit represents slot 2
		   and so forth. "
	::= { wfDrivers 2 }

wfFSILoad OBJECT-TYPE
	SYNTAX	Counter
	ACCESS	read-write
	STATUS	mandatory
	DESCRIPTION
		" Bit mask for loading the FDDI System Interface (FSI) chip driver on
		   slots 1-14. The MSBit represents slot 1, the next most significant
		   bit represents slot 2 and so forth. This attribute shall be used to
		   configure the FSI chip driver on the appropriate slots for FDDI only
		   (see wfHSSIFSILoad for other usage). "
	::= { wfDrivers 3 }

wfTMS380Load OBJECT-TYPE
	SYNTAX	Counter
	ACCESS	read-write
	STATUS	mandatory
	DESCRIPTION
		" Bit mask for loading the TMS380 chip driver on slots 1-14. The MSBit
		   represents slot 1, the next most significant bit represents slot 2
		   and so forth. "
	::= { wfDrivers 4 }

wfMK5025Load OBJECT-TYPE
	SYNTAX	Counter
	ACCESS	read-write
	STATUS	mandatory
	DESCRIPTION
		" Bit mask for loading the MK5025 chip driver on slots 1-14. The MSBit
		   represents slot 1, the next most significant bit represents slot 2
		   and so forth. "
	::= { wfDrivers 5 }

wfDS2180Load OBJECT-TYPE
	SYNTAX	Counter
	ACCESS	read-write
	STATUS	mandatory
	DESCRIPTION
		" Bit mask for loading the DS2180 chip driver on slots 1-14. The MSBit
		   represents slot 1, the next most significant bit represents slot 2
		   and so forth. "
	::= { wfDrivers 6 }

wfDS2181Load OBJECT-TYPE
	SYNTAX	Counter
	ACCESS	read-write
	STATUS	mandatory
	DESCRIPTION
		" Bit mask for loading the DS2181 chip driver on slots 1-14. The MSBit
		   represents slot 1, the next most significant bit represents slot 2
		   and so forth. "
	::= { wfDrivers 7 }

wfDEFALoad OBJECT-TYPE
	SYNTAX	Counter
	ACCESS	read-write
	STATUS	mandatory
	DESCRIPTION
		" Bit mask for loading the AM99C10 chip driver on slots 1-14. The MSBit
		   represents slot 1, the next most significant bit represents slot 2
		   and so forth. The AM99C10 chip is Content Addressable Memory (CAM)
		   and the driver to control it is represented by this attribute. The
		   generic name of this attribute shall be the Hardware Filter Driver
		   which will also provide control of the Dual Ethernet Filter
		   Accelerator (DEFA) chip. "
	::= { wfDrivers 8 }

wfAMZ8530Load OBJECT-TYPE
	SYNTAX	Counter
	ACCESS	read-write
	STATUS	mandatory
	DESCRIPTION
		" Bit mask for loading the AMZ8530 chip driver on slots 1-14. The
		   MSBit represents slot 1, the next most significant bit represents
		   slot 2, and so forth. "
	::= { wfDrivers 9 }

wfHSSIFSILoad OBJECT-TYPE
	SYNTAX	Counter
	ACCESS	read-write
	STATUS	mandatory
	DESCRIPTION
		" Bit mask for loading the HSSI FSI chip driver on slots 1-14. The
		   MSBit represents slot 1, the next most significant bit represents
		   slot 2, and so forth. "
	::= { wfDrivers 10 }

wfOspfGeneralGroup	OBJECT IDENTIFIER ::= { wfOspfGroup 1 }

wfOspfGeneralDelete OBJECT-TYPE
	SYNTAX	INTEGER {
		created(1),
		deleted(2)
	}
	ACCESS	read-write
	STATUS	mandatory
	DESCRIPTION
		"
		     'This value determines whether OSPF is configured'
		 "
	DEFVAL	{ created }
	::= { wfOspfGeneralGroup 1 }

wfOspfGeneralDisable OBJECT-TYPE
	SYNTAX	INTEGER {
		enabled(1),
		disabled(2)
	}
	ACCESS	read-write
	STATUS	mandatory
	DESCRIPTION
		"
		            'The administrative status of OSPF in the router.  The
		            value 'enabled' denotes that the OSPF Process is active
		            on at least one interface; 'disabled' disables it on
		            all interfaces.'
		 "
	DEFVAL	{ enabled }
	::= { wfOspfGeneralGroup 2 }

wfOspfGeneralState OBJECT-TYPE
	SYNTAX	INTEGER {
		up(1),
		down(2),
		init(3),
		notpresent(4)
	}
	ACCESS	read-only
	STATUS	mandatory
	DESCRIPTION
		"
		    'The state of OSPF'
		 "
	DEFVAL	{ down }
	::= { wfOspfGeneralGroup 3 }

wfOspfRouterId OBJECT-TYPE
	SYNTAX	IpAddress
	ACCESS	read-write
	STATUS	mandatory
	DESCRIPTION
		"
		            'A 32-bit integer uniquely identifying the router in
		            the Autonomous System.
		            By convention, to ensure uniqueness, this should
		            default to the value of one of the router's IP
		            interface addresses.'
		         REFERENCE
		            'OSPF Version 2, C.1 Global parameters'
		 "
	::= { wfOspfGeneralGroup 4 }

wfOspfVersionNumber OBJECT-TYPE
	SYNTAX	INTEGER
	ACCESS	read-only
	STATUS	mandatory
	DESCRIPTION
		"
		            'The current version number of the OSPF protocol is 2.'
		         REFERENCE
		            'OSPF Version 2, Title'
		 "
	::= { wfOspfGeneralGroup 5 }

wfOspfAreaBdrRtrStatus OBJECT-TYPE
	SYNTAX	INTEGER {
		true(1),
		false(2)
	}
	ACCESS	read-only
	STATUS	mandatory
	DESCRIPTION
		"
		            'A flag to note whether this router is an area border
		            router.'
		         REFERENCE
		            'OSPF Version 2, Section 3 Splitting the AS into Areas'
		 "
	DEFVAL	{ false }
	::= { wfOspfGeneralGroup 6 }

wfOspfASBdrRtrStatus OBJECT-TYPE
	SYNTAX	INTEGER {
		true(1),
		false(2)
	}
	ACCESS	read-write
	STATUS	mandatory
	DESCRIPTION
		"
		            'A flag to note whether this router is an Autonomous
		            System border router.'
		         REFERENCE
		            'OSPF Version 2, Section 3.3 Classification of routers'
		 "
	DEFVAL	{ false }
	::= { wfOspfGeneralGroup 7 }

wfOspfTOSSupport OBJECT-TYPE
	SYNTAX	INTEGER {
		true(1),
		false(2)
	}
	ACCESS	read-only
	STATUS	mandatory
	DESCRIPTION
		"
		            'The router's support for type-of-service routing.'
		         REFERENCE
		            'OSPF Version 2, Appendix F.1.2 Optional TOS support'
		 "
	DEFVAL	{ false }
	::= { wfOspfGeneralGroup 8 }

wfOspfSpfHoldDown OBJECT-TYPE
	SYNTAX	INTEGER {
		defval(1),
		maximum(10)
	}
	ACCESS	read-write
	STATUS	mandatory
	DESCRIPTION
		"
		       Hold Down Timer for the SPF.  The SPF will run at most
		       once per hold down timer value.  A value of 0 means no
		       hold down.
		 "
	DEFVAL	{ defval }
	::= { wfOspfGeneralGroup 9 }

wfOspfSlotMask OBJECT-TYPE
	SYNTAX	INTEGER {
		slotmask(16383)
	}
	ACCESS	read-write
	STATUS	mandatory
	DESCRIPTION
		"
		       Slot mask for which slots OSPF is eligible
		       to run on.  The LSBit represents slot 1, the
		       next least significant bit represents slot 2,
		       and so on...  Slots can be 1-14.
		 "
	DEFVAL	{ slotmask }
	::= { wfOspfGeneralGroup 10 }

wfOspfAreaTable OBJECT-TYPE
	SYNTAX	SEQUENCE OF WfOspfAreaEntry
	ACCESS	not-accessible
	STATUS	mandatory
	DESCRIPTION
		"
		     --      The OSPF Area Data Structure contains information
		     --      regarding the various areas. The interfaces and
		     --      virtual links are configured as part of these areas.
		     --      Area 0.0.0.0, by definition, is the Backbone Area
		            'Information describing the configured parameters and
		            cumulative statistics of the router's attached areas.'
		         REFERENCE
		            'OSPF Version 2, Section 6  The Area Data Structure'
		 "
	::= { wfOspfGroup 2 }

wfOspfAreaEntry OBJECT-TYPE
	SYNTAX	WfOspfAreaEntry
	ACCESS	not-accessible
	STATUS	mandatory
	DESCRIPTION
		"
		            'Information describing the configured parameters and
		            cumulative statistics of one of the router's attached
		            areas.'
		 "
	INDEX	{ wfOspfAreaId }
	::= { wfOspfAreaTable 1 }

WfOspfAreaEntry ::= SEQUENCE {
	wfOspfAreaDelete
		INTEGER,
	wfOspfAreaDisable
		INTEGER,
	wfOspfAreaState
		INTEGER,
	wfOspfAreaId
		IpAddress,
	wfOspfAuthType
		INTEGER,
	wfOspfImportASExtern
		INTEGER,
	wfOspfStubMetric
		INTEGER,
	wfOspfImportSum
		INTEGER
}

wfOspfAreaDelete OBJECT-TYPE
	SYNTAX	INTEGER {
		created(1),
		deleted(2)
	}
	ACCESS	read-write
	STATUS	mandatory
	DESCRIPTION
		"
		            This value determines if the OSPF router is configured with
		     this area.
		 "
	DEFVAL	{ created }
	::= { wfOspfAreaEntry 1 }

wfOspfAreaDisable OBJECT-TYPE
	SYNTAX	INTEGER {
		enabled(1),
		disabled(2)
	}
	ACCESS	read-write
	STATUS	mandatory
	DESCRIPTION
		"
		     This value indicates the state of this area on the OSPF
		     router.
		 "
	DEFVAL	{ enabled }
	::= { wfOspfAreaEntry 2 }

wfOspfAreaState OBJECT-TYPE
	SYNTAX	INTEGER {
		up(1),
		down(2)
	}
	ACCESS	read-only
	STATUS	mandatory
	DESCRIPTION
		"
		            This value indicates the state of the OSPF Area.
		 "
	DEFVAL	{ down }
	::= { wfOspfAreaEntry 3 }

wfOspfAreaId OBJECT-TYPE
	SYNTAX	IpAddress
	ACCESS	read-only
	STATUS	mandatory
	DESCRIPTION
		"
		            'A 32-bit integer uniquely identifying an area.  Area
		            ID 0.0.0.0 is used for the OSPF backbone.'
		         REFERENCE
		            'OSPF Version 2, Appendix C.2 Area parameters'
		 "
	::= { wfOspfAreaEntry 4 }

wfOspfAuthType OBJECT-TYPE
	SYNTAX	INTEGER {
		nopassword(1),
		simplepassword(2)
	}
	ACCESS	read-write
	STATUS	mandatory
	DESCRIPTION
		"
		            'The authentication type specified for an area.
		            Additional authentication types may be assigned locally
		            on a per Area basis.'
		         REFERENCE
		            'OSPF Version 2, Appendix E Authentication'
		                     -- none (0),
		                     -- simplePassword (1)
		                     -- reserved for future specification (2..255)
		                     -- reserved for AS specific values (> 255)
		 "
	DEFVAL	{ nopassword }
	::= { wfOspfAreaEntry 5 }

wfOspfImportASExtern OBJECT-TYPE
	SYNTAX	INTEGER {
		true(1),
		false(2)
	}
	ACCESS	read-write
	STATUS	mandatory
	DESCRIPTION
		"
		            'The area's support for importing AS external link-
		            state advertisements.'
		         REFERENCE
		            'OSPF Version 2, Appendix C.2 Area parameters'
		 "
	DEFVAL	{ true }
	::= { wfOspfAreaEntry 6 }

wfOspfStubMetric OBJECT-TYPE
	SYNTAX	INTEGER {
		minimum(1),
		maximum(16777215)
	}
	ACCESS	read-write
	STATUS	mandatory
	DESCRIPTION
		"
		            'The metric value applied at the indicated type of
		            service.  By default, this equals the least metric at
		            the type of service among the interfaces to other
		            areas.'
		 "
	DEFVAL	{ minimum }
	::= { wfOspfAreaEntry 7 }

wfOspfImportSum OBJECT-TYPE
	SYNTAX	INTEGER {
		true(1),
		false(2)
	}
	ACCESS	read-write
	STATUS	mandatory
	DESCRIPTION
		"
		            'The area's support for importing Summary 
		            advertisements into a stub area.  This variable
		   should not be set unless wfOspfImportASExtern is
		   set to FALSE'
		 "
	DEFVAL	{ true }
	::= { wfOspfAreaEntry 8 }

wfOspfLsdbTable OBJECT-TYPE
	SYNTAX	SEQUENCE OF WfOspfLsdbEntry
	ACCESS	not-accessible
	STATUS	mandatory
	DESCRIPTION
		"
		     --  OSPF Link State Database
		     --      The Link State Database contains the Link State
		     --      Advertisements from throughout the areas that the
		     --      device is attached to.
		            'The OSPF Process's Links State Database.'
		         REFERENCE
		            'OSPF Version 2, Section 12 Link State Advertisements'
		"
	::= { wfOspfGroup 3 }

wfOspfLsdbEntry OBJECT-TYPE
	SYNTAX	WfOspfLsdbEntry
	ACCESS	not-accessible
	STATUS	mandatory
	DESCRIPTION
		"
		            'A single Link State Advertisement.'
		 "
	INDEX	{ wfOspfLsdbAreaId,
		wfOspfLsdbType,
		wfOspfLsdbLSID,
		wfOspfLsdbRouterId }
	::= { wfOspfLsdbTable 1 }

WfOspfLsdbEntry ::= SEQUENCE {
	wfOspfLsdbAreaId
		IpAddress,
	wfOspfLsdbType
		INTEGER,
	wfOspfLsdbLSID
		IpAddress,
	wfOspfLsdbRouterId
		IpAddress,
	wfOspfLsdbSequence
		INTEGER,
	wfOspfLsdbAge
		INTEGER,
	wfOspfLsdbChecksum
		INTEGER,
	wfOspfLsdbAdvLen
		INTEGER
}

wfOspfLsdbAreaId OBJECT-TYPE
	SYNTAX	IpAddress
	ACCESS	read-only
	STATUS	mandatory
	DESCRIPTION
		"
		            'The 32 bit identifier of the Area from which the LSA
		            was received.'
		         REFERENCE
		            'OSPF Version 2, Appendix C.2 Area parameters'
		 "
	::= { wfOspfLsdbEntry 1 }

wfOspfLsdbType OBJECT-TYPE
	SYNTAX	INTEGER {
		routerlink(1),
		networklink(2),
		summarylink(3),
		assummarylink(4),
		asexternallink(5)
	}
	ACCESS	read-only
	STATUS	mandatory
	DESCRIPTION
		"
		            'The type of the link state advertisement.  Each link
		            state type has a separate advertisement format.'
		         REFERENCE
		            'OSPF Version 2, Appendix A.4.1 The Link State
		            Advertisement header'
		       stubLink   (0),
		                     routerLink (1),
		                     networkLink (2),
		                     summaryLink (3),
		                     asSummaryLink (4),
		                     asExternalLink (5)
		 "
	::= { wfOspfLsdbEntry 2 }

wfOspfLsdbLSID OBJECT-TYPE
	SYNTAX	IpAddress
	ACCESS	read-only
	STATUS	mandatory
	DESCRIPTION
		"
		            'The Link State ID is an LS Type Specific field
		            containing either a Router ID or an IP Address; it
		            identifies the piece of the routing domain that is
		            being described by the advertisement.'
		         REFERENCE
		            'OSPF Version 2, Section 12.1.4 Link State ID'
		 "
	::= { wfOspfLsdbEntry 3 }

wfOspfLsdbRouterId OBJECT-TYPE
	SYNTAX	IpAddress
	ACCESS	read-only
	STATUS	mandatory
	DESCRIPTION
		"
		            'The 32 bit number that uniquely identifies the
		            originating router in the Autonomous System.'
		         REFERENCE
		            'OSPF Version 2, Appendix C.1 Global parameters'
		 "
	::= { wfOspfLsdbEntry 4 }

wfOspfLsdbSequence OBJECT-TYPE
	SYNTAX	INTEGER
	ACCESS	read-only
	STATUS	mandatory
	DESCRIPTION
		"
		     --  Note that the OSPF Sequence Number is a 32 bit signed
		     --  integer.  It starts with the value '80000001'h,
		     --  or -'7FFFFFFF'h, and increments until '7FFFFFFF'h
		     --  Thus, a typical sequence number will be very negative.
		            'The sequence number field is a signed 32-bit integer.
		            It is used to detect old and duplicate link state
		            advertisements.  The space of sequence numbers is
		            linearly ordered.  The larger the sequence number the
		            more recent the advertisement.'
		         REFERENCE
		            'OSPF Version 2, Section 12.1.6 LS sequence number'
		 "
	::= { wfOspfLsdbEntry 5 }

wfOspfLsdbAge OBJECT-TYPE
	SYNTAX	INTEGER {
		lsdbmaxage(3600)
	}
	ACCESS	read-only
	STATUS	mandatory
	DESCRIPTION
		"
		            'This field is the age of the link state advertisement
		            in seconds.'
		      (OSPF_LSDBMINAGE = 0)
		         REFERENCE
		            'OSPF Version 2, Section 12.1.1 LS age'
		 "
	::= { wfOspfLsdbEntry 6 }

wfOspfLsdbChecksum OBJECT-TYPE
	SYNTAX	INTEGER
	ACCESS	read-only
	STATUS	mandatory
	DESCRIPTION
		"
		            'This field is the checksum of the complete contents of
		            the advertisement, excepting the age field.  The age
		            field is excepted so that an advertisement's age can be
		            incremented without updating the checksum.  The
		            checksum used is the same that is used for ISO
		            connectionless datagrams; it is commonly referred to as
		            the Fletcher checksum.'
		         REFERENCE
		            'OSPF Version 2, Section 12.1.7 LS checksum'
		 "
	::= { wfOspfLsdbEntry 7 }

wfOspfLsdbAdvLen OBJECT-TYPE
	SYNTAX	INTEGER
	ACCESS	read-only
	STATUS	mandatory
	DESCRIPTION
		"
		            'The length of entire Link State Advertisement, including its
		            header.'
		         REFERENCE
		            'OSPF Version 2, Section 12 Link State Advertisements'
		 "
	::= { wfOspfLsdbEntry 8 }

wfOspfAreaRangeTable OBJECT-TYPE
	SYNTAX	SEQUENCE OF WfOspfAreaRangeEntry
	ACCESS	not-accessible
	STATUS	mandatory
	DESCRIPTION
		"
		            'A range if IP addresses specified by an IP address/IP
		            network mask pair.  For example, class B address range
		            of X.X.X.X with a network mask of 255.255.0.0 includes
		            all IP addresses from X.X.0.0 to X.X.255.255'
		         REFERENCE
		            'OSPF Version 2, Appendix C.2  Area parameters'
		 "
	::= { wfOspfGroup 4 }

wfOspfAreaRangeEntry OBJECT-TYPE
	SYNTAX	WfOspfAreaRangeEntry
	ACCESS	not-accessible
	STATUS	mandatory
	DESCRIPTION
		"
		 "
	INDEX	{ wfOspfAreaRangeAreaID,
		wfOspfAreaRangeNet }
	::= { wfOspfAreaRangeTable 1 }

WfOspfAreaRangeEntry ::= SEQUENCE {
	wfOspfAreaRangeDelete
		INTEGER,
	wfOspfAreaRangeDisable
		INTEGER,
	wfOspfAreaRangeState
		INTEGER,
	wfOspfAreaRangeAreaID
		IpAddress,
	wfOspfAreaRangeNet
		IpAddress,
	wfOspfAreaRangeMask
		IpAddress
}

wfOspfAreaRangeDelete OBJECT-TYPE
	SYNTAX	INTEGER {
		created(1),
		deleted(2)
	}
	ACCESS	read-write
	STATUS	mandatory
	DESCRIPTION
		"
		     This value determines if an Area Range has been 
		     configured for the OSPF router.
		 "
	DEFVAL	{ created }
	::= { wfOspfAreaRangeEntry 1 }

wfOspfAreaRangeDisable OBJECT-TYPE
	SYNTAX	INTEGER {
		enabled(1),
		disabled(2)
	}
	ACCESS	read-write
	STATUS	mandatory
	DESCRIPTION
		"
		            'This variable displays the status of
		            the entry.  Setting it to 'DISBALED' has the effect of
		            rendering it inoperative.  The internal effect (row
		            removal) is implementation dependent.'
		 "
	DEFVAL	{ enabled }
	::= { wfOspfAreaRangeEntry 2 }

wfOspfAreaRangeState OBJECT-TYPE
	SYNTAX	INTEGER {
		up(1),
		down(2)
	}
	ACCESS	read-only
	STATUS	mandatory
	DESCRIPTION
		"
		     The state of the OSPF Area Range.
		 "
	DEFVAL	{ down }
	::= { wfOspfAreaRangeEntry 3 }

wfOspfAreaRangeAreaID OBJECT-TYPE
	SYNTAX	IpAddress
	ACCESS	read-only
	STATUS	mandatory
	DESCRIPTION
		"
		            'The Area the Address Range is to be found within.'
		         REFERENCE
		            'OSPF Version 2, Appendix C.2 Area parameters'
		 "
	::= { wfOspfAreaRangeEntry 4 }

wfOspfAreaRangeNet OBJECT-TYPE
	SYNTAX	IpAddress
	ACCESS	read-only
	STATUS	mandatory
	DESCRIPTION
		"
		            'The IP Address of the Net or Subnet indicated by the
		            range.'
		         REFERENCE
		            'OSPF Version 2, Appendix C.2 Area parameters'
		 "
	::= { wfOspfAreaRangeEntry 5 }

wfOspfAreaRangeMask OBJECT-TYPE
	SYNTAX	IpAddress
	ACCESS	read-write
	STATUS	mandatory
	DESCRIPTION
		"
		            'The Subnet Mask that pertains to the Net or Subnet.'
		         REFERENCE
		            'OSPF Version 2, Appendix C.2 Area parameters'
		 "
	::= { wfOspfAreaRangeEntry 6 }

wfOspfIfTable OBJECT-TYPE
	SYNTAX	SEQUENCE OF WfOspfIfEntry
	ACCESS	not-accessible
	STATUS	mandatory
	DESCRIPTION
		"
		     --  OSPF Interface Table
		     --      The OSPF Interface Table augments the ifTable with OSPF
		     --      specific information.
		            'The OSPF Interface Table describes the interfaces from
		            the viewpoint of OSPF.'
		         REFERENCE
		            'OSPF Version 2, Appendix C.3  Router interface
		            parameters'
		 "
	::= { wfOspfGroup 5 }

wfOspfIfEntry OBJECT-TYPE
	SYNTAX	WfOspfIfEntry
	ACCESS	not-accessible
	STATUS	mandatory
	DESCRIPTION
		"
		            'The OSPF Interface Entry describes one interface from
		            the viewpoint of OSPF.'
		 "
	INDEX	{ wfOspfIfIpAddress,
		wfOspfAddressLessIf }
	::= { wfOspfIfTable 1 }

WfOspfIfEntry ::= SEQUENCE {
	wfOspfIfDelete
		INTEGER,
	wfOspfIfDisable
		INTEGER,
	wfOspfIfState
		INTEGER,
	wfOspfIfIpAddress
		IpAddress,
	wfOspfAddressLessIf
		INTEGER,
	wfOspfIfAreaId
		IpAddress,
	wfOspfIfType
		INTEGER,
	wfOspfIfRtrPriority
		INTEGER,
	wfOspfIfTransitDelay
		INTEGER,
	wfOspfIfRetransInterval
		INTEGER,
	wfOspfIfHelloInterval
		INTEGER,
	wfOspfIfRtrDeadInterval
		INTEGER,
	wfOspfIfPollInterval
		INTEGER,
	wfOspfIfDesignatedRouter
		IpAddress,
	wfOspfIfBackupDesignatedRouter
		IpAddress,
	wfOspfIfMetricCost
		INTEGER,
	wfOspfIfAuthKey
		OCTET STRING,
	wfOspfIfTxHellos
		Counter,
	wfOspfIfTxDBDescripts
		Counter,
	wfOspfIfTxLinkStateReqs
		Counter,
	wfOspfIfTxLinkStateUpds
		Counter,
	wfOspfIfTxLinkStateAcks
		Counter,
	wfOspfIfRxHellos
		Counter,
	wfOspfIfRxDBDescripts
		Counter,
	wfOspfIfRxLinkStateReqs
		Counter,
	wfOspfIfRxLinkStateUpds
		Counter,
	wfOspfIfRxLinkStateAcks
		Counter,
	wfOspfIfDrops
		Counter
}

wfOspfIfDelete OBJECT-TYPE
	SYNTAX	INTEGER {
		created(1),
		deleted(2)
	}
	ACCESS	read-write
	STATUS	mandatory
	DESCRIPTION
		"
		     This variable determines in an OSPF Interface has been
		     configured on the router.
		 "
	DEFVAL	{ created }
	::= { wfOspfIfEntry 1 }

wfOspfIfDisable OBJECT-TYPE
	SYNTAX	INTEGER {
		enabled(1),
		disabled(2)
	}
	ACCESS	read-write
	STATUS	mandatory
	DESCRIPTION
		"
		            'The OSPF interface's administrative status.  The value
		            'enabled' denotes that neighbor relationships may be
		            formed on the interface, and the interface will be
		            advertised as an internal route to some area.  The
		            value 'disabled' denotes that the interface is external
		            to OSPF.'
		 "
	DEFVAL	{ enabled }
	::= { wfOspfIfEntry 2 }

wfOspfIfState OBJECT-TYPE
	SYNTAX	INTEGER {
		down(1),
		loopback(2),
		waiting(3),
		pointtopoint(4),
		designatedrouter(5),
		backupdesignatedrouter(6),
		otherdesignatedrouter(7)
	}
	ACCESS	read-only
	STATUS	mandatory
	DESCRIPTION
		"
		            'The OSPF Interface State.'
		                     down (1),
		                     loopback (2),
		                     waiting (3),
		                     pointToPoint (4),
		                     designatedRouter (5),
		                     backupDesignatedRouter (6),
		                     otherDesignatedRouter (7)
		 "
	DEFVAL	{ down }
	::= { wfOspfIfEntry 3 }

wfOspfIfIpAddress OBJECT-TYPE
	SYNTAX	IpAddress
	ACCESS	read-only
	STATUS	mandatory
	DESCRIPTION
		"
		            'The IP address of this OSPF interface.'
		 "
	::= { wfOspfIfEntry 4 }

wfOspfAddressLessIf OBJECT-TYPE
	SYNTAX	INTEGER
	ACCESS	read-only
	STATUS	mandatory
	DESCRIPTION
		"
		            'For the purpose of easing the instancing of addressed
		            and addressless interfaces; This variable takes the
		            value 0 on interfaces with IP Addresses, and the
		            corresponding value of ifIndex for interfaces having no
		            IP Address.'
		 "
	::= { wfOspfIfEntry 5 }

wfOspfIfAreaId OBJECT-TYPE
	SYNTAX	IpAddress
	ACCESS	read-write
	STATUS	mandatory
	DESCRIPTION
		"
		            'A 32-bit integer uniquely identifying the area to
		            which the interface connects.  Area ID 0.0.0.0 is used
		            for the OSPF backbone.'
		            default { '00000000'H }    -- 0.0.0.0
		 "
	::= { wfOspfIfEntry 6 }

wfOspfIfType OBJECT-TYPE
	SYNTAX	INTEGER {
		broadcast(1),
		nbma(2),
		pointtopoint(3)
	}
	ACCESS	read-write
	STATUS	mandatory
	DESCRIPTION
		"
		            'The OSPF interface type.
		            By way of a default, this field may be intuited from
		            the corresponding value of ifType.  Broadcast LANs,
		            such as Ethernet and IEEE 802.5, take the value
		            'broadcast', X.25, Frame Relay, and similar
		            technologies take the value 'nbma', and links that are
		            definitively point to point take the value
		            'pointToPoint'.'
		                     broadcast (1),
		                     nbma (2),
		                     pointToPoint (3)
		 "
	::= { wfOspfIfEntry 7 }

wfOspfIfRtrPriority OBJECT-TYPE
	SYNTAX	INTEGER {
		defval(1),
		maximum(255)
	}
	ACCESS	read-write
	STATUS	mandatory
	DESCRIPTION
		"
		            'The priority of this interface.  Used in multi-access
		            networks, this field is used in the designated router
		            election algorithm.  The value 0 signifies that the
		            router is not eligible to become the designated router
		            on this particular network.  In the event of a tie in
		            this value, routers will use their router id as a tie
		            breaker.'
		 "
	DEFVAL	{ defval }
	::= { wfOspfIfEntry 8 }

wfOspfIfTransitDelay OBJECT-TYPE
	SYNTAX	INTEGER {
		minimum(1),
		defval(1),
		maximum(3600)
	}
	ACCESS	read-write
	STATUS	mandatory
	DESCRIPTION
		"
		            'The estimated number of seconds it takes to transmit a
		            link- state update packet over this interface.'
		 "
	DEFVAL	{ defval }
	::= { wfOspfIfEntry 9 }

wfOspfIfRetransInterval OBJECT-TYPE
	SYNTAX	INTEGER {
		minimum(1),
		defval(5),
		maximum(3600)
	}
	ACCESS	read-write
	STATUS	mandatory
	DESCRIPTION
		"
		            'The number of seconds between link-state advertisement
		            retransmissions, for adjacencies belonging to this
		            interface.  This value is also used when retransmitting
		            database description and link-state request packets.'
		 "
	DEFVAL	{ defval }
	::= { wfOspfIfEntry 10 }

wfOspfIfHelloInterval OBJECT-TYPE
	SYNTAX	INTEGER {
		minimum(1),
		defval(10),
		maximum(65535)
	}
	ACCESS	read-write
	STATUS	mandatory
	DESCRIPTION
		"
		            'The length of time, in seconds, between the Hello
		            packets that the router sends on the interface.  This
		            value must be the same for all routers attached to a
		            common network.'
		 "
	DEFVAL	{ defval }
	::= { wfOspfIfEntry 11 }

wfOspfIfRtrDeadInterval OBJECT-TYPE
	SYNTAX	INTEGER {
		minimum(1),
		defval(40),
		maximum(2147483647)
	}
	ACCESS	read-write
	STATUS	mandatory
	DESCRIPTION
		"
		            'The number of seconds that a router's Hello packets
		            have not been seen before it's neighbors declare the
		            router down.  This should be some multiple of the Hello
		            interval.  This value must be the same for all routers
		            attached to a common network.'
		 "
	DEFVAL	{ defval }
	::= { wfOspfIfEntry 12 }

wfOspfIfPollInterval OBJECT-TYPE
	SYNTAX	INTEGER {
		minimum(1),
		defval(120),
		maximum(2147483647)
	}
	ACCESS	read-write
	STATUS	mandatory
	DESCRIPTION
		"
		            'The larger time interval, in seconds, between the
		            Hello packets sent to an inactive non-broadcast multi-
		            access neighbor.'
		 "
	DEFVAL	{ defval }
	::= { wfOspfIfEntry 13 }

wfOspfIfDesignatedRouter OBJECT-TYPE
	SYNTAX	IpAddress
	ACCESS	read-only
	STATUS	mandatory
	DESCRIPTION
		"
		            'The IP Address of the Designated Router.'
		            default { '00000000'H }    -- 0.0.0.0
		 "
	::= { wfOspfIfEntry 14 }

wfOspfIfBackupDesignatedRouter OBJECT-TYPE
	SYNTAX	IpAddress
	ACCESS	read-only
	STATUS	mandatory
	DESCRIPTION
		"
		            'The IP Address of the Backup Designated Router.'
		            default { '00000000'H }    -- 0.0.0.0
		 "
	::= { wfOspfIfEntry 15 }

wfOspfIfMetricCost OBJECT-TYPE
	SYNTAX	INTEGER {
		minimum(1),
		maximum(65535)
	}
	ACCESS	read-write
	STATUS	mandatory
	DESCRIPTION
		"
		            'The cost of using this type of service on this
		            interface.  The default value of the TOS 0 Metric is
		            10^8 / ifSpeed.
		            The value FFFF is distinguished to mean 'no route via
		            this TOS'.'
		 "
	DEFVAL	{ minimum }
	::= { wfOspfIfEntry 16 }

wfOspfIfAuthKey OBJECT-TYPE
	SYNTAX	OCTET STRING
	ACCESS	read-write
	STATUS	mandatory
	DESCRIPTION
		"
		            'The Authentication Key.  If the Area's Authorization
		            Type is simplePassword, and the key length is shorter
		            than 8 octets, the agent will left adjust and zero fill
		            to 8 octets.
		            When read, ospfIfAuthKey always returns an Octet String
		            of length zero.'
		            default  { '0000000000000000'H }    -- 0.0.0.0.0.0.0.0
		         REFERENCE
		            'OSPF Version 2, Section 9 The Interface Data
		            Structure'
		 "
	::= { wfOspfIfEntry 17 }

wfOspfIfTxHellos OBJECT-TYPE
	SYNTAX	Counter
	ACCESS	read-only
	STATUS	mandatory
	DESCRIPTION
		"
		     Number of OSPF Hello packets transmitted.
		 "
	::= { wfOspfIfEntry 18 }

wfOspfIfTxDBDescripts OBJECT-TYPE
	SYNTAX	Counter
	ACCESS	read-only
	STATUS	mandatory
	DESCRIPTION
		"
		     Number of OSPF DataBase Description packets transmitted.
		 "
	::= { wfOspfIfEntry 19 }

wfOspfIfTxLinkStateReqs OBJECT-TYPE
	SYNTAX	Counter
	ACCESS	read-only
	STATUS	mandatory
	DESCRIPTION
		"
		     Number of OSPF Link State Request packets transmitted.
		 "
	::= { wfOspfIfEntry 20 }

wfOspfIfTxLinkStateUpds OBJECT-TYPE
	SYNTAX	Counter
	ACCESS	read-only
	STATUS	mandatory
	DESCRIPTION
		"
		     Number of OSPF Link State Update packets transmitted.
		 "
	::= { wfOspfIfEntry 21 }

wfOspfIfTxLinkStateAcks OBJECT-TYPE
	SYNTAX	Counter
	ACCESS	read-only
	STATUS	mandatory
	DESCRIPTION
		"
		     Number of OSPF Link States Acknowledgements transmitted.
		 "
	::= { wfOspfIfEntry 22 }

wfOspfIfRxHellos OBJECT-TYPE
	SYNTAX	Counter
	ACCESS	read-only
	STATUS	mandatory
	DESCRIPTION
		"
		     Number of OSPF Hello packets received.
		 "
	::= { wfOspfIfEntry 23 }

wfOspfIfRxDBDescripts OBJECT-TYPE
	SYNTAX	Counter
	ACCESS	read-only
	STATUS	mandatory
	DESCRIPTION
		"
		     Number of OSPF DataBase Description packets received.
		 "
	::= { wfOspfIfEntry 24 }

wfOspfIfRxLinkStateReqs OBJECT-TYPE
	SYNTAX	Counter
	ACCESS	read-only
	STATUS	mandatory
	DESCRIPTION
		"
		     Number of OSPF Link State Requests received.
		 "
	::= { wfOspfIfEntry 25 }

wfOspfIfRxLinkStateUpds OBJECT-TYPE
	SYNTAX	Counter
	ACCESS	read-only
	STATUS	mandatory
	DESCRIPTION
		"
		     Number of OSPF Link State Updates received.
		 "
	::= { wfOspfIfEntry 26 }

wfOspfIfRxLinkStateAcks OBJECT-TYPE
	SYNTAX	Counter
	ACCESS	read-only
	STATUS	mandatory
	DESCRIPTION
		"
		     Number of OSPF Link State Acknowledgements received.
		 "
	::= { wfOspfIfEntry 27 }

wfOspfIfDrops OBJECT-TYPE
	SYNTAX	Counter
	ACCESS	read-only
	STATUS	mandatory
	DESCRIPTION
		"
		     Number of OSPF packets dropped because of invalid information
		     in the packet.
		 "
	::= { wfOspfIfEntry 28 }

wfOspfVirtIfTable OBJECT-TYPE
	SYNTAX	SEQUENCE OF WfOspfVirtIfEntry
	ACCESS	not-accessible
	STATUS	mandatory
	DESCRIPTION
		"
		     --  OSPF Virtual Interface Table
		     --      The Virtual Interface Table describes the virtual
		     --      links that the OSPF Process is configured to
		     --      carry on.
		            'Information about this router's virtual interfaces.'
		         REFERENCE
		            'OSPF Version 2, Appendix C.4  Virtual link parameters'
		 "
	::= { wfOspfGroup 6 }

wfOspfVirtIfEntry OBJECT-TYPE
	SYNTAX	WfOspfVirtIfEntry
	ACCESS	not-accessible
	STATUS	mandatory
	DESCRIPTION
		"
		            'Information about a single Virtual Interface.'
		 "
	INDEX	{ wfOspfVirtIfAreaID,
		wfOspfVirtIfNeighbor }
	::= { wfOspfVirtIfTable 1 }

WfOspfVirtIfEntry ::= SEQUENCE {
	wfOspfVirtIfDelete
		INTEGER,
	wfOspfVirtIfDisable
		INTEGER,
	wfOspfVirtIfState
		INTEGER,
	wfOspfVirtIfAreaID
		IpAddress,
	wfOspfVirtIfNeighbor
		IpAddress,
	wfOspfVirtIfTransitDelay
		INTEGER,
	wfOspfVirtIfRetransInterval
		INTEGER,
	wfOspfVirtIfHelloInterval
		INTEGER,
	wfOspfVirtIfRtrDeadInterval
		INTEGER,
	wfOspfVirtIfAuthKey
		OCTET STRING,
	wfOspfVirtIfTxHellos
		Counter,
	wfOspfVirtIfTxDBDescripts
		Counter,
	wfOspfVirtIfTxLinkStateReqs
		Counter,
	wfOspfVirtIfTxLinkStateUpds
		Counter,
	wfOspfVirtIfTxLinkStateAcks
		Counter,
	wfOspfVirtIfRxHellos
		Counter,
	wfOspfVirtIfRxDBDescripts
		Counter,
	wfOspfVirtIfRxLinkStateReqs
		Counter,
	wfOspfVirtIfRxLinkStateUpds
		Counter,
	wfOspfVirtIfRxLinkStateAcks
		Counter,
	wfOspfVirtIfDrops
		Counter
}

wfOspfVirtIfDelete OBJECT-TYPE
	SYNTAX	INTEGER {
		created(1),
		deleted(2)
	}
	ACCESS	read-write
	STATUS	mandatory
	DESCRIPTION
		"
		 "
	DEFVAL	{ created }
	::= { wfOspfVirtIfEntry 1 }

wfOspfVirtIfDisable OBJECT-TYPE
	SYNTAX	INTEGER {
		enabled(1),
		disabled(2)
	}
	ACCESS	read-write
	STATUS	mandatory
	DESCRIPTION
		"
		            'This variable displays the validity or invalidity of
		            the entry.  Setting it to 'invalid' has the effect of
		            rendering it inoperative.  The internal effect (row
		            removal) is implementation dependent.'
		 "
	DEFVAL	{ enabled }
	::= { wfOspfVirtIfEntry 2 }

wfOspfVirtIfState OBJECT-TYPE
	SYNTAX	INTEGER {
		down(1),
		pointtopoint(4)
	}
	ACCESS	read-only
	STATUS	mandatory
	DESCRIPTION
		"
		            'OSPF virtual interface states.'
		                     down (1),               -- these use the same encoding
		                     pointToPoint (4)        -- as the ospfIfTable
		 "
	DEFVAL	{ down }
	::= { wfOspfVirtIfEntry 3 }

wfOspfVirtIfAreaID OBJECT-TYPE
	SYNTAX	IpAddress
	ACCESS	read-only
	STATUS	mandatory
	DESCRIPTION
		"
		            'The Transit Area that the Virtual Link traverses.  By
		            definition, this is not 0.0.0.0'
		 "
	::= { wfOspfVirtIfEntry 4 }

wfOspfVirtIfNeighbor OBJECT-TYPE
	SYNTAX	IpAddress
	ACCESS	read-only
	STATUS	mandatory
	DESCRIPTION
		"
		            'The Router ID of the Virtual Neighbor.'
		 "
	::= { wfOspfVirtIfEntry 5 }

wfOspfVirtIfTransitDelay OBJECT-TYPE
	SYNTAX	INTEGER {
		minimum(1),
		defval(1),
		maximum(3600)
	}
	ACCESS	read-write
	STATUS	mandatory
	DESCRIPTION
		"
		            'The estimated number of seconds it takes to transmit a
		            link- state update packet over this interface.'
		 "
	DEFVAL	{ defval }
	::= { wfOspfVirtIfEntry 6 }

wfOspfVirtIfRetransInterval OBJECT-TYPE
	SYNTAX	INTEGER {
		minimum(1),
		defval(5),
		maximum(3600)
	}
	ACCESS	read-write
	STATUS	mandatory
	DESCRIPTION
		"
		            'The number of seconds between link-state advertisement
		            retransmissions, for adjacencies belonging to this
		            interface.  This value is also used when retransmitting
		            database description and link-state request packets.
		            This value should be well over the expected round-trip
		            time.'
		 "
	DEFVAL	{ defval }
	::= { wfOspfVirtIfEntry 7 }

wfOspfVirtIfHelloInterval OBJECT-TYPE
	SYNTAX	INTEGER {
		minimum(1),
		defval(15),
		maximum(65535)
	}
	ACCESS	read-write
	STATUS	mandatory
	DESCRIPTION
		"
		            'The length of time, in seconds, between the Hello
		            packets that the router sends on the interface.  This
		            value must be the same for the virtual neighbor.'
		 "
	DEFVAL	{ defval }
	::= { wfOspfVirtIfEntry 8 }

wfOspfVirtIfRtrDeadInterval OBJECT-TYPE
	SYNTAX	INTEGER {
		minimum(1),
		defval(60),
		maximum(2147483647)
	}
	ACCESS	read-write
	STATUS	mandatory
	DESCRIPTION
		"
		            'The number of seconds that a router's Hello packets
		            have not been seen before it's neighbors declare the
		            router down.  This should be some multiple of the Hello
		            interval.  This value must be the same for the virtual
		            neighbor.'
		 "
	DEFVAL	{ defval }
	::= { wfOspfVirtIfEntry 9 }

wfOspfVirtIfAuthKey OBJECT-TYPE
	SYNTAX	OCTET STRING
	ACCESS	read-write
	STATUS	mandatory
	DESCRIPTION
		"
		            'If Authentication Type is simplePassword, the device
		            will left adjust and zero fill to 8 octets.
		            When read, ospfVifAuthKey always returns a string of
		            length zero.'
		         REFERENCE
		            'OSPF Version 2, Section 9 The Interface Data
		            Structure'
		 "
	::= { wfOspfVirtIfEntry 10 }

wfOspfVirtIfTxHellos OBJECT-TYPE
	SYNTAX	Counter
	ACCESS	read-only
	STATUS	mandatory
	DESCRIPTION
		"
		     Number of OSPF Hello packets transmitted on
		     Virtual Interfaces.
		 "
	::= { wfOspfVirtIfEntry 11 }

wfOspfVirtIfTxDBDescripts OBJECT-TYPE
	SYNTAX	Counter
	ACCESS	read-only
	STATUS	mandatory
	DESCRIPTION
		"
		     Number of OSPF DataBase Description packets transmitted
		     on Virtual Interfaces.
		 "
	::= { wfOspfVirtIfEntry 12 }

wfOspfVirtIfTxLinkStateReqs OBJECT-TYPE
	SYNTAX	Counter
	ACCESS	read-only
	STATUS	mandatory
	DESCRIPTION
		"
		     Number of OSPF Link State Request packets transmitted
		     on Virtual Interfaces.
		 "
	::= { wfOspfVirtIfEntry 13 }

wfOspfVirtIfTxLinkStateUpds OBJECT-TYPE
	SYNTAX	Counter
	ACCESS	read-only
	STATUS	mandatory
	DESCRIPTION
		"
		     Number of OSPF Link State Update packets transmitted
		     on Virtual Interfaces.
		 "
	::= { wfOspfVirtIfEntry 14 }

wfOspfVirtIfTxLinkStateAcks OBJECT-TYPE
	SYNTAX	Counter
	ACCESS	read-only
	STATUS	mandatory
	DESCRIPTION
		"
		     Number of OSPF Link State Acknowledgement packets
		     transmitted on Virtual Interfaces.
		 "
	::= { wfOspfVirtIfEntry 15 }

wfOspfVirtIfRxHellos OBJECT-TYPE
	SYNTAX	Counter
	ACCESS	read-only
	STATUS	mandatory
	DESCRIPTION
		"
		     Number of OSPF Hello packets received on
		     Virtual Interfaces.
		 "
	::= { wfOspfVirtIfEntry 16 }

wfOspfVirtIfRxDBDescripts OBJECT-TYPE
	SYNTAX	Counter
	ACCESS	read-only
	STATUS	mandatory
	DESCRIPTION
		"
		     Number of OSPF DataBase Description packets received
		     on Virtual Interfaces.
		 "
	::= { wfOspfVirtIfEntry 17 }

wfOspfVirtIfRxLinkStateReqs OBJECT-TYPE
	SYNTAX	Counter
	ACCESS	read-only
	STATUS	mandatory
	DESCRIPTION
		"
		     Number of OSPF Link State Request packets recieved
		     on Virtual Interfaces.
		 "
	::= { wfOspfVirtIfEntry 18 }

wfOspfVirtIfRxLinkStateUpds OBJECT-TYPE
	SYNTAX	Counter
	ACCESS	read-only
	STATUS	mandatory
	DESCRIPTION
		"
		     Number of OSPF Link State Update packets received
		     on Virtual Interfaces.
		 "
	::= { wfOspfVirtIfEntry 19 }

wfOspfVirtIfRxLinkStateAcks OBJECT-TYPE
	SYNTAX	Counter
	ACCESS	read-only
	STATUS	mandatory
	DESCRIPTION
		"
		     Number of OSPF Link State Acknowledgement packets
		     received on Virtual Interfaces.
		 "
	::= { wfOspfVirtIfEntry 20 }

wfOspfVirtIfDrops OBJECT-TYPE
	SYNTAX	Counter
	ACCESS	read-only
	STATUS	mandatory
	DESCRIPTION
		"
		     Number of OSPF packets dropped on
		     Virtual Interfaces.
		 "
	::= { wfOspfVirtIfEntry 21 }

wfOspfNbrTable OBJECT-TYPE
	SYNTAX	SEQUENCE OF WfOspfNbrEntry
	ACCESS	not-accessible
	STATUS	mandatory
	DESCRIPTION
		"
		     --  OSPF Neighbor Table
		     --      The OSPF Neighbor Table describes all neighbors in
		     --      the locality of the subject router.
		            'A table of non-virtual neighbor information.'
		         REFERENCE
		            'OSPF Version 2, Section 10 The Neighbor Data
		            Structure'
		 "
	::= { wfOspfGroup 7 }

wfOspfNbrEntry OBJECT-TYPE
	SYNTAX	WfOspfNbrEntry
	ACCESS	not-accessible
	STATUS	mandatory
	DESCRIPTION
		"
		            'The information regarding a single neighbor.'
		         REFERENCE
		            'OSPF Version 2, Section 10 The Neighbor Data
		            Structure'
		 "
	INDEX	{ wfOspfNbrIpAddr,
		wfOspfNbrAddressLessIndex }
	::= { wfOspfNbrTable 1 }

WfOspfNbrEntry ::= SEQUENCE {
	wfOspfNbrDelete
		INTEGER,
	wfOspfNbrDisable
		INTEGER,
	wfOspfNbrState
		INTEGER,
	wfOspfNbrIpAddr
		IpAddress,
	wfOspfNbrIfAddr
		IpAddress,
	wfOspfNbrAddressLessIndex
		INTEGER,
	wfOspfNbrRtrId
		IpAddress,
	wfOspfNbrOptions
		INTEGER,
	wfOspfNbrPriority
		INTEGER,
	wfOspfNbrEvents
		Counter,
	wfOspfNbrLSRetransQLen
		Gauge
}

wfOspfNbrDelete OBJECT-TYPE
	SYNTAX	INTEGER {
		created(1),
		deleted(2)
	}
	ACCESS	read-write
	STATUS	mandatory
	DESCRIPTION
		"
		     This variable indicates the existence of a static
		     OSPF neighbor.
		 "
	DEFVAL	{ created }
	::= { wfOspfNbrEntry 1 }

wfOspfNbrDisable OBJECT-TYPE
	SYNTAX	INTEGER {
		enabled(1),
		disabled(2)
	}
	ACCESS	read-write
	STATUS	mandatory
	DESCRIPTION
		"
		            'This variable displays the status of
		            the entry.  Setting it to 'DISABLED' has the effect of
		            rendering it inoperative.  The internal effect (row
		            removal) is implementation dependent.'
		 "
	DEFVAL	{ enabled }
	::= { wfOspfNbrEntry 2 }

wfOspfNbrState OBJECT-TYPE
	SYNTAX	INTEGER {
		down(1),
		attempt(2),
		init(3),
		twoway(4),
		exchangstart(5),
		exchange(6),
		loading(7),
		full(8)
	}
	ACCESS	read-only
	STATUS	mandatory
	DESCRIPTION
		"
		            'The State of the relationship with this Neighbor.'
		         REFERENCE
		            'OSPF Version 2, Section 10.1 Neighbor States'
		                     down (1),
		                     attempt (2),
		                     init (3),
		                     twoWay (4),
		                     exchangeStart (5),
		                     exchange (6),
		                     loading (7),
		                     full (8)
		 "
	DEFVAL	{ down }
	::= { wfOspfNbrEntry 3 }

wfOspfNbrIpAddr OBJECT-TYPE
	SYNTAX	IpAddress
	ACCESS	read-only
	STATUS	mandatory
	DESCRIPTION
		"
		            'The IP address of this neighbor.'
		 "
	::= { wfOspfNbrEntry 4 }

wfOspfNbrIfAddr OBJECT-TYPE
	SYNTAX	IpAddress
	ACCESS	read-write
	STATUS	mandatory
	DESCRIPTION
		"
		            'The Interface IP address for this neighbor.'
		 "
	::= { wfOspfNbrEntry 5 }

wfOspfNbrAddressLessIndex OBJECT-TYPE
	SYNTAX	INTEGER
	ACCESS	read-only
	STATUS	mandatory
	DESCRIPTION
		"
		            ' On an interface having an IP Address, zero.  On
		            addressless interfaces, the corresponding value of
		            ifIndex in the Internet Standard MIB.  On row creation,
		            this can be derived from the instance.'
		 "
	::= { wfOspfNbrEntry 6 }

wfOspfNbrRtrId OBJECT-TYPE
	SYNTAX	IpAddress
	ACCESS	read-only
	STATUS	mandatory
	DESCRIPTION
		"
		            'A 32-bit integer (represented as a type IpAddress)
		            uniquely identifying the neighboring router in the
		            Autonomous System.'
		            default { '00000000'H }    -- 0.0.0.0
		 "
	::= { wfOspfNbrEntry 7 }

wfOspfNbrOptions OBJECT-TYPE
	SYNTAX	INTEGER
	ACCESS	read-only
	STATUS	mandatory
	DESCRIPTION
		"
		            'A Bit Mask corresponding to the neighbor's options
		            field.
		            Bit 0, if set, indicates that the area accepts and
		            operates on external information; if zero, it is a stub
		            area.
		            Bit 1, if set, indicates that the system will operate
		            on Type of Service metrics other than TOS 0.  If zero,
		            the neighbor will ignore all metrics except the TOS 0
		            metric.'
		         REFERENCE
		            'OSPF Version 2, Section 12.1.2 Options'
		 "
	::= { wfOspfNbrEntry 8 }

wfOspfNbrPriority OBJECT-TYPE
	SYNTAX	INTEGER {
		defval(1),
		maximum(255)
	}
	ACCESS	read-write
	STATUS	mandatory
	DESCRIPTION
		"
		            'The priority of this neighbor in the designated router
		            election algorithm.  The value 0 signifies that the
		            neighbor is not eligible to become the designated
		            router on this particular network.'
		 "
	DEFVAL	{ defval }
	::= { wfOspfNbrEntry 9 }

wfOspfNbrEvents OBJECT-TYPE
	SYNTAX	Counter
	ACCESS	read-only
	STATUS	mandatory
	DESCRIPTION
		"
		            'The number of times this neighbor relationship has
		            changed state, or an error has occurred.'
		 "
	::= { wfOspfNbrEntry 10 }

wfOspfNbrLSRetransQLen OBJECT-TYPE
	SYNTAX	Gauge
	ACCESS	read-only
	STATUS	mandatory
	DESCRIPTION
		"
		            'The current length of the retransmission queue.'
		 "
	::= { wfOspfNbrEntry 11 }

wfOspfVirtNbrTable OBJECT-TYPE
	SYNTAX	SEQUENCE OF WfOspfVirtNbrEntry
	ACCESS	not-accessible
	STATUS	mandatory
	DESCRIPTION
		"
		     --  WFOSPF Virtual Neighbor Table
		     --      This table describes all virtual neighbors.
		     --      Since Virtual Links are configured in the
		     --      virtual interface table, this table is read-only.
		            'A table of virtual neighbor information.'
		         REFERENCE
		            'OSPF Version 2, '
		 "
	::= { wfOspfGroup 8 }

wfOspfVirtNbrEntry OBJECT-TYPE
	SYNTAX	WfOspfVirtNbrEntry
	ACCESS	not-accessible
	STATUS	mandatory
	DESCRIPTION
		"
		            'Virtual neighbor information.'
		         REFERENCE
		            'OSPF Version 2, '
		 "
	INDEX	{ wfOspfVirtNbrArea,
		wfOspfVirtNbrRtrId }
	::= { wfOspfVirtNbrTable 1 }

WfOspfVirtNbrEntry ::= SEQUENCE {
	wfOspfVirtNbrArea
		IpAddress,
	wfOspfVirtNbrRtrId
		IpAddress,
	wfOspfVirtNbrIpAddr
		IpAddress,
	wfOspfVirtNbrOptions
		INTEGER,
	wfOspfVirtNbrState
		INTEGER,
	wfOspfVirtNbrEvents
		Counter,
	wfOspfVirtNbrLSRetransQLen
		Gauge
}

wfOspfVirtNbrArea OBJECT-TYPE
	SYNTAX	IpAddress
	ACCESS	read-only
	STATUS	mandatory
	DESCRIPTION
		"
		            'The Transit Area Identifier.'
		 "
	::= { wfOspfVirtNbrEntry 1 }

wfOspfVirtNbrRtrId OBJECT-TYPE
	SYNTAX	IpAddress
	ACCESS	read-only
	STATUS	mandatory
	DESCRIPTION
		"
		            'A 32-bit integer uniquely identifying the neighboring
		            router in the Autonomous System.'
		 "
	::= { wfOspfVirtNbrEntry 2 }

wfOspfVirtNbrIpAddr OBJECT-TYPE
	SYNTAX	IpAddress
	ACCESS	read-only
	STATUS	mandatory
	DESCRIPTION
		"
		            'The IP address this Virtual Neighbor is using.'
		 "
	::= { wfOspfVirtNbrEntry 3 }

wfOspfVirtNbrOptions OBJECT-TYPE
	SYNTAX	INTEGER
	ACCESS	read-only
	STATUS	mandatory
	DESCRIPTION
		"
		            'A bit map corresponding to the neighbor's options
		            field.  Thus, Bit 1, if set, indicates that the
		            neighbor supports Type of Service Routing; if zero, no
		            metrics other than TOS 0 are in use by the neighbor.'
		 "
	::= { wfOspfVirtNbrEntry 4 }

wfOspfVirtNbrState OBJECT-TYPE
	SYNTAX	INTEGER {
		down(1),
		attempt(2),
		init(3),
		twoway(4),
		exchangstart(5),
		exchange(6),
		loading(7),
		full(8)
	}
	ACCESS	read-only
	STATUS	mandatory
	DESCRIPTION
		"
		            'The state of the Virtual Neighbor Relationship.'
		                     down (1),
		                     attempt (2),
		                     init (3),
		                     twoWay (4),
		                     exchangeStart (5),
		                     exchange (6),
		                     loading (7),
		                     full (8)
		 "
	DEFVAL	{ down }
	::= { wfOspfVirtNbrEntry 5 }

wfOspfVirtNbrEvents OBJECT-TYPE
	SYNTAX	Counter
	ACCESS	read-only
	STATUS	mandatory
	DESCRIPTION
		"
		            'The number of times this virtual link has changed its
		            state, or an error has occurred.'
		 "
	::= { wfOspfVirtNbrEntry 6 }

wfOspfVirtNbrLSRetransQLen OBJECT-TYPE
	SYNTAX	Gauge
	ACCESS	read-only
	STATUS	mandatory
	DESCRIPTION
		"
		            'The current length of the retransmission queue.'
		 "
	::= { wfOspfVirtNbrEntry 7 }

wfOspfDynNbrTable OBJECT-TYPE
	SYNTAX	SEQUENCE OF WfOspfDynNbrEntry
	ACCESS	not-accessible
	STATUS	mandatory
	DESCRIPTION
		"
		     --  OSPF Dynamic Neighbor Table
		     --      The OSPF Dynamic Neighbor Table describes all neighbors in
		     --      the locality of the subject router learned during operation.
		            'A table of non-virtual neighbor information.'
		         REFERENCE
		            'OSPF Version 2, Section 10 The Neighbor Data
		            Structure'
		 "
	::= { wfOspfGroup 9 }

wfOspfDynNbrEntry OBJECT-TYPE
	SYNTAX	WfOspfDynNbrEntry
	ACCESS	not-accessible
	STATUS	mandatory
	DESCRIPTION
		"
		            'The information regarding a single neighbor.'
		         REFERENCE
		            'OSPF Version 2, Section 10 The Neighbor Data
		            Structure'
		 "
	INDEX	{ wfOspfDynNbrIpAddr,
		wfOspfDynNbrAddressLessIndex }
	::= { wfOspfDynNbrTable 1 }

WfOspfDynNbrEntry ::= SEQUENCE {
	wfOspfDynNbrState
		INTEGER,
	wfOspfDynNbrIpAddr
		IpAddress,
	wfOspfDynNbrIfAddr
		IpAddress,
	wfOspfDynNbrAddressLessIndex
		INTEGER,
	wfOspfDynNbrRtrId
		IpAddress,
	wfOspfDynNbrOptions
		INTEGER,
	wfOspfDynNbrPriority
		INTEGER,
	wfOspfDynNbrEvents
		Counter,
	wfOspfDynNbrLSRetransQLen
		Gauge
}

wfOspfDynNbrState OBJECT-TYPE
	SYNTAX	INTEGER {
		down(1),
		attempt(2),
		init(3),
		twoway(4),
		exchangstart(5),
		exchange(6),
		loading(7),
		full(8)
	}
	ACCESS	read-only
	STATUS	mandatory
	DESCRIPTION
		"
		            'The State of the relationship with this Neighbor.'
		         REFERENCE
		            'OSPF Version 2, Section 10.1 Neighbor States'
		                     down (1),
		                     attempt (2),
		                     init (3),
		                     twoWay (4),
		                     exchangeStart (5),
		                     exchange (6),
		                     loading (7),
		                     full (8)
		 "
	DEFVAL	{ down }
	::= { wfOspfDynNbrEntry 1 }

wfOspfDynNbrIpAddr OBJECT-TYPE
	SYNTAX	IpAddress
	ACCESS	read-only
	STATUS	mandatory
	DESCRIPTION
		"
		            'The IP address of this neighbor.'
		 "
	::= { wfOspfDynNbrEntry 2 }

wfOspfDynNbrIfAddr OBJECT-TYPE
	SYNTAX	IpAddress
	ACCESS	read-only
	STATUS	mandatory
	DESCRIPTION
		"
		            'The Interface IP address for this neighbor.'
		 "
	::= { wfOspfDynNbrEntry 3 }

wfOspfDynNbrAddressLessIndex OBJECT-TYPE
	SYNTAX	INTEGER
	ACCESS	read-only
	STATUS	mandatory
	DESCRIPTION
		"
		            ' On an interface having an IP Address, zero.  On
		            addressless interfaces, the corresponding value of
		            ifIndex in the Internet Standard MIB.  On row creation,
		            this can be derived from the instance.'
		 "
	::= { wfOspfDynNbrEntry 4 }

wfOspfDynNbrRtrId OBJECT-TYPE
	SYNTAX	IpAddress
	ACCESS	read-only
	STATUS	mandatory
	DESCRIPTION
		"
		            'A 32-bit integer (represented as a type IpAddress)
		            uniquely identifying the neighboring router in the
		            Autonomous System.'
		            default { '00000000'H }    -- 0.0.0.0
		 "
	::= { wfOspfDynNbrEntry 5 }

wfOspfDynNbrOptions OBJECT-TYPE
	SYNTAX	INTEGER
	ACCESS	read-only
	STATUS	mandatory
	DESCRIPTION
		"
		            'A Bit Mask corresponding to the neighbor's options
		            field.
		            Bit 0, if set, indicates that the area accepts and
		            operates on external information; if zero, it is a stub
		            area.
		            Bit 1, if set, indicates that the system will operate
		            on Type of Service metrics other than TOS 0.  If zero,
		            the neighbor will ignore all metrics except the TOS 0
		            metric.'
		         REFERENCE
		            'OSPF Version 2, Section 12.1.2 Options'
		 "
	::= { wfOspfDynNbrEntry 6 }

wfOspfDynNbrPriority OBJECT-TYPE
	SYNTAX	INTEGER
	ACCESS	read-only
	STATUS	mandatory
	DESCRIPTION
		"
		            'The priority of this neighbor in the designated router
		            election algorithm.  The value 0 signifies that the
		            neighbor is not eligible to become the designated
		            router on this particular network.'
		 "
	::= { wfOspfDynNbrEntry 7 }

wfOspfDynNbrEvents OBJECT-TYPE
	SYNTAX	Counter
	ACCESS	read-only
	STATUS	mandatory
	DESCRIPTION
		"
		            'The number of times this neighbor relationship has
		            changed state, or an error has occurred.'
		 "
	::= { wfOspfDynNbrEntry 8 }

wfOspfDynNbrLSRetransQLen OBJECT-TYPE
	SYNTAX	Gauge
	ACCESS	read-only
	STATUS	mandatory
	DESCRIPTION
		"
		            'The current length of the retransmission queue.'
		 "
	::= { wfOspfDynNbrEntry 9 }

wfIpRfRipImportTable OBJECT-TYPE
	SYNTAX	SEQUENCE OF WfIpRfRipImportEntry
	ACCESS	not-accessible
	STATUS	mandatory
	DESCRIPTION
		" The list of Rip Import Route Filter Rules in IP "
	::= { wfIpGroup 8 }

wfIpRfRipImportEntry OBJECT-TYPE
	SYNTAX	WfIpRfRipImportEntry
	ACCESS	not-accessible
	STATUS	mandatory
	DESCRIPTION
		" An entry in the Rip Import Rule Table "
	INDEX	{ wfIpRfRipImportAddress,
		wfIpRfRipImportMask,
		wfIpRfRipImportRipGateway,
		wfIpRfRipImportRipInterface }
	::= { wfIpRfRipImportTable 1 }

WfIpRfRipImportEntry ::= SEQUENCE {
	wfIpRfRipImportCreate
		INTEGER,
	wfIpRfRipImportEnable
		INTEGER,
	wfIpRfRipImportAddress
		IpAddress,
	wfIpRfRipImportMask
		IpAddress,
	wfIpRfRipImportAction
		INTEGER,
	wfIpRfRipImportPreference
		INTEGER,
	wfIpRfRipImportRipGateway
		IpAddress,
	wfIpRfRipImportRipInterface
		IpAddress
}

wfIpRfRipImportCreate OBJECT-TYPE
	SYNTAX	INTEGER {
		create(1),
		delete(2)
	}
	ACCESS	read-write
	STATUS	mandatory
	DESCRIPTION
		"Create/Delete parameter. Default is created.
		     Users perform an SNMP SET operation on this
		     object in order to create/delete this Rule."
	DEFVAL	{ create }
	::= { wfIpRfRipImportEntry 1 }

wfIpRfRipImportEnable OBJECT-TYPE
	SYNTAX	INTEGER {
		enable(1),
		disable(2)
	}
	ACCESS	read-write
	STATUS	mandatory
	DESCRIPTION
		"Enable/Disable parameter. Default is enabled.
		     Users perform an SNMP SET operation on this
		     object in order to enable/disable this Rule."
	DEFVAL	{ enable }
	::= { wfIpRfRipImportEntry 2 }

wfIpRfRipImportAddress OBJECT-TYPE
	SYNTAX	IpAddress
	ACCESS	read-only
	STATUS	mandatory
	DESCRIPTION
		" The IP address to which this filter applies "
	::= { wfIpRfRipImportEntry 3 }

wfIpRfRipImportMask OBJECT-TYPE
	SYNTAX	IpAddress
	ACCESS	read-only
	STATUS	mandatory
	DESCRIPTION
		" The Mask to which this filter applies. When combined
		       with the Address, a range is specified for application
		       of this rule "
	::= { wfIpRfRipImportEntry 4 }

wfIpRfRipImportAction OBJECT-TYPE
	SYNTAX	INTEGER {
		accept(1),
		ignore(3)
	}
	ACCESS	read-write
	STATUS	mandatory
	DESCRIPTION
		" The Action of this Filter "
	DEFVAL	{ accept }
	::= { wfIpRfRipImportEntry 5 }

wfIpRfRipImportPreference OBJECT-TYPE
	SYNTAX	INTEGER {
		maximum(16)
	}
	ACCESS	read-write
	STATUS	mandatory
	DESCRIPTION
		" The Preference associated with this filter - only valid if accept "
	::= { wfIpRfRipImportEntry 6 }

wfIpRfRipImportRipGateway OBJECT-TYPE
	SYNTAX	IpAddress
	ACCESS	read-only
	STATUS	mandatory
	DESCRIPTION
		" The RIP Gateway to be concerned with "
	::= { wfIpRfRipImportEntry 7 }

wfIpRfRipImportRipInterface OBJECT-TYPE
	SYNTAX	IpAddress
	ACCESS	read-only
	STATUS	mandatory
	DESCRIPTION
		" The IP Network Interface to be concerned with "
	::= { wfIpRfRipImportEntry 8 }

wfIpRfRipExportTable OBJECT-TYPE
	SYNTAX	SEQUENCE OF WfIpRfRipExportEntry
	ACCESS	not-accessible
	STATUS	mandatory
	DESCRIPTION
		" The list of Rip Export Route Filter Rules in IP "
	::= { wfIpGroup 9 }

wfIpRfRipExportEntry OBJECT-TYPE
	SYNTAX	WfIpRfRipExportEntry
	ACCESS	not-accessible
	STATUS	mandatory
	DESCRIPTION
		" An entry in the Rip Export Rule Table "
	INDEX	{ wfIpRfRipExportAddress,
		wfIpRfRipExportMask,
		wfIpRfRipExportFromProtocol,
		wfIpRfRipExportInterface }
	::= { wfIpRfRipExportTable 1 }

WfIpRfRipExportEntry ::= SEQUENCE {
	wfIpRfRipExportCreate
		INTEGER,
	wfIpRfRipExportEnable
		INTEGER,
	wfIpRfRipExportAddress
		IpAddress,
	wfIpRfRipExportMask
		IpAddress,
	wfIpRfRipExportFromProtocol
		INTEGER,
	wfIpRfRipExportAction
		INTEGER,
	wfIpRfRipExportInterface
		IpAddress,
	wfIpRfRipExportRipMetric
		INTEGER
}

wfIpRfRipExportCreate OBJECT-TYPE
	SYNTAX	INTEGER {
		create(1),
		delete(2)
	}
	ACCESS	read-write
	STATUS	mandatory
	DESCRIPTION
		"Create/Delete parameter. Default is created.
		     Users perform an SNMP SET operation on this
		     object in order to create/delete this Rule."
	DEFVAL	{ create }
	::= { wfIpRfRipExportEntry 1 }

wfIpRfRipExportEnable OBJECT-TYPE
	SYNTAX	INTEGER {
		enable(1),
		disable(2)
	}
	ACCESS	read-write
	STATUS	mandatory
	DESCRIPTION
		"Enable/Disable parameter. Default is enabled.
		     Users perform an SNMP SET operation on this
		     object in order to enable/disable this Rule."
	DEFVAL	{ enable }
	::= { wfIpRfRipExportEntry 2 }

wfIpRfRipExportAddress OBJECT-TYPE
	SYNTAX	IpAddress
	ACCESS	read-only
	STATUS	mandatory
	DESCRIPTION
		" The IP address to which this filter applies "
	::= { wfIpRfRipExportEntry 3 }

wfIpRfRipExportMask OBJECT-TYPE
	SYNTAX	IpAddress
	ACCESS	read-only
	STATUS	mandatory
	DESCRIPTION
		" The Mask for the Address Above. When combined
		       with the Address, a range is specified for application
		       of this filter rule "
	::= { wfIpRfRipExportEntry 4 }

wfIpRfRipExportFromProtocol OBJECT-TYPE
	SYNTAX	INTEGER {
		rip(1),
		ospf(3),
		direct(4),
		static(5)
	}
	ACCESS	read-only
	STATUS	mandatory
	DESCRIPTION
		" The protocol from which this Information is derived "
	DEFVAL	{ rip }
	::= { wfIpRfRipExportEntry 5 }

wfIpRfRipExportAction OBJECT-TYPE
	SYNTAX	INTEGER {
		propa(2),
		ignore(3)
	}
	ACCESS	read-write
	STATUS	mandatory
	DESCRIPTION
		" The action of this export filter "
	DEFVAL	{ propa }
	::= { wfIpRfRipExportEntry 6 }

wfIpRfRipExportInterface OBJECT-TYPE
	SYNTAX	IpAddress
	ACCESS	read-only
	STATUS	mandatory
	DESCRIPTION
		" The optional outbound interface on which to apply this filter "
	::= { wfIpRfRipExportEntry 7 }

wfIpRfRipExportRipMetric OBJECT-TYPE
	SYNTAX	INTEGER {
		maximum(15)
	}
	ACCESS	read-write
	STATUS	mandatory
	DESCRIPTION
		" The optional export RIP metric to apply to this filter.
		       Zero means: use the route's actual cost. Only valid for propagate "
	::= { wfIpRfRipExportEntry 8 }

wfIpRfOspfImportTable OBJECT-TYPE
	SYNTAX	SEQUENCE OF WfIpRfOspfImportEntry
	ACCESS	not-accessible
	STATUS	mandatory
	DESCRIPTION
		" The list of OSPF Import Route Filter Rules in IP "
	::= { wfIpGroup 10 }

wfIpRfOspfImportEntry OBJECT-TYPE
	SYNTAX	WfIpRfOspfImportEntry
	ACCESS	not-accessible
	STATUS	mandatory
	DESCRIPTION
		" An entry in the OSPF Import Route Filter Table "
	INDEX	{ wfIpRfOspfImportAddress,
		wfIpRfOspfImportMask,
		wfIpRfOspfImportType,
		wfIpRfOspfImportTag }
	::= { wfIpRfOspfImportTable 1 }

WfIpRfOspfImportEntry ::= SEQUENCE {
	wfIpRfOspfImportCreate
		INTEGER,
	wfIpRfOspfImportEnable
		INTEGER,
	wfIpRfOspfImportAddress
		IpAddress,
	wfIpRfOspfImportMask
		IpAddress,
	wfIpRfOspfImportAction
		INTEGER,
	wfIpRfOspfImportPreference
		INTEGER,
	wfIpRfOspfImportType
		INTEGER,
	wfIpRfOspfImportTag
		INTEGER
}

wfIpRfOspfImportCreate OBJECT-TYPE
	SYNTAX	INTEGER {
		create(1),
		delete(2)
	}
	ACCESS	read-write
	STATUS	mandatory
	DESCRIPTION
		"Create/Delete parameter. Default is created.
		     Users perform an SNMP SET operation on this
		     object in order to create/delete this Rule."
	DEFVAL	{ create }
	::= { wfIpRfOspfImportEntry 1 }

wfIpRfOspfImportEnable OBJECT-TYPE
	SYNTAX	INTEGER {
		enable(1),
		disable(2)
	}
	ACCESS	read-write
	STATUS	mandatory
	DESCRIPTION
		"Enable/Disable parameter. Default is enabled.
		     Users perform an SNMP SET operation on this
		     object in order to enable/disable this Rule."
	DEFVAL	{ enable }
	::= { wfIpRfOspfImportEntry 2 }

wfIpRfOspfImportAddress OBJECT-TYPE
	SYNTAX	IpAddress
	ACCESS	read-only
	STATUS	mandatory
	DESCRIPTION
		" The IP Address to which this filter applies "
	::= { wfIpRfOspfImportEntry 3 }

wfIpRfOspfImportMask OBJECT-TYPE
	SYNTAX	IpAddress
	ACCESS	read-only
	STATUS	mandatory
	DESCRIPTION
		" The Mask to which this filter applies. When combined
		       with the Address, a range is specified for application
		       of this rule "
	::= { wfIpRfOspfImportEntry 4 }

wfIpRfOspfImportAction OBJECT-TYPE
	SYNTAX	INTEGER {
		accept(1),
		ignore(3)
	}
	ACCESS	read-write
	STATUS	mandatory
	DESCRIPTION
		" The Action of this Filter "
	DEFVAL	{ accept }
	::= { wfIpRfOspfImportEntry 5 }

wfIpRfOspfImportPreference OBJECT-TYPE
	SYNTAX	INTEGER {
		maximum(16)
	}
	ACCESS	read-write
	STATUS	mandatory
	DESCRIPTION
		" The Preference associated with this filter - only valid if accept "
	::= { wfIpRfOspfImportEntry 6 }

wfIpRfOspfImportType OBJECT-TYPE
	SYNTAX	INTEGER
	ACCESS	read-only
	STATUS	mandatory
	DESCRIPTION
		" The OSPF route Type to be concerned with. The valid values are null
		       (any route type), 1 (OSPF external type 1), and 2 (OSPF external
		       type 2).  "
	::= { wfIpRfOspfImportEntry 7 }

wfIpRfOspfImportTag OBJECT-TYPE
	SYNTAX	INTEGER
	ACCESS	read-only
	STATUS	mandatory
	DESCRIPTION
		" The OSPF Tag to be concerned with "
	::= { wfIpRfOspfImportEntry 8 }

wfIpRfOspfExportTable OBJECT-TYPE
	SYNTAX	SEQUENCE OF WfIpRfOspfExportEntry
	ACCESS	not-accessible
	STATUS	mandatory
	DESCRIPTION
		" The list of OSPF Export Route Filter Rules in IP "
	::= { wfIpGroup 11 }

wfIpRfOspfExportEntry OBJECT-TYPE
	SYNTAX	WfIpRfOspfExportEntry
	ACCESS	not-accessible
	STATUS	mandatory
	DESCRIPTION
		" An entry in the OSPF Export Route Filter Table "
	INDEX	{ wfIpRfOspfExportAddress,
		wfIpRfOspfExportMask,
		wfIpRfOspfExportFromProtocol }
	::= { wfIpRfOspfExportTable 1 }

WfIpRfOspfExportEntry ::= SEQUENCE {
	wfIpRfOspfExportCreate
		INTEGER,
	wfIpRfOspfExportEnable
		INTEGER,
	wfIpRfOspfExportAddress
		IpAddress,
	wfIpRfOspfExportMask
		IpAddress,
	wfIpRfOspfExportFromProtocol
		INTEGER,
	wfIpRfOspfExportAction
		INTEGER,
	wfIpRfOspfExportType
		INTEGER,
	wfIpRfOspfExportTag
		INTEGER
}

wfIpRfOspfExportCreate OBJECT-TYPE
	SYNTAX	INTEGER {
		create(1),
		delete(2)
	}
	ACCESS	read-write
	STATUS	mandatory
	DESCRIPTION
		"Create/Delete parameter. Default is created.
		     Users perform an SNMP SET operation on this
		     object in order to create/delete this Rule."
	DEFVAL	{ create }
	::= { wfIpRfOspfExportEntry 1 }

wfIpRfOspfExportEnable OBJECT-TYPE
	SYNTAX	INTEGER {
		enable(1),
		disable(2)
	}
	ACCESS	read-write
	STATUS	mandatory
	DESCRIPTION
		"Enable/Disable parameter. Default is enabled.
		     Users perform an SNMP SET operation on this
		     object in order to enable/disable this Rule."
	DEFVAL	{ enable }
	::= { wfIpRfOspfExportEntry 2 }

wfIpRfOspfExportAddress OBJECT-TYPE
	SYNTAX	IpAddress
	ACCESS	read-only
	STATUS	mandatory
	DESCRIPTION
		" The IP address to which this filter applies "
	::= { wfIpRfOspfExportEntry 3 }

wfIpRfOspfExportMask OBJECT-TYPE
	SYNTAX	IpAddress
	ACCESS	read-only
	STATUS	mandatory
	DESCRIPTION
		" The Mask for the Address Above. When combined
		       with the Address, a range is specified for application
		       of this filter rule "
	::= { wfIpRfOspfExportEntry 4 }

wfIpRfOspfExportFromProtocol OBJECT-TYPE
	SYNTAX	INTEGER {
		rip(1),
		ospf(3),
		direct(4),
		static(5)
	}
	ACCESS	read-only
	STATUS	mandatory
	DESCRIPTION
		" The protocol from which this Information is derived "
	DEFVAL	{ rip }
	::= { wfIpRfOspfExportEntry 5 }

wfIpRfOspfExportAction OBJECT-TYPE
	SYNTAX	INTEGER {
		propa(2),
		ignore(3)
	}
	ACCESS	read-write
	STATUS	mandatory
	DESCRIPTION
		" The action of this export filter "
	DEFVAL	{ propa }
	::= { wfIpRfOspfExportEntry 6 }

wfIpRfOspfExportType OBJECT-TYPE
	SYNTAX	INTEGER {
		type1(1),
		type2(2)
	}
	ACCESS	read-write
	STATUS	mandatory
	DESCRIPTION
		" The ospf type to use when this filter matches "
	DEFVAL	{ type1 }
	::= { wfIpRfOspfExportEntry 7 }

wfIpRfOspfExportTag OBJECT-TYPE
	SYNTAX	INTEGER
	ACCESS	read-write
	STATUS	mandatory
	DESCRIPTION
		" The ospf tag to use when this filter matches "
	::= { wfIpRfOspfExportEntry 8 }

wfSipL2 OBJECT-TYPE
	SYNTAX	SEQUENCE OF WfSipL2Entry
	ACCESS	not-accessible
	STATUS	mandatory
	DESCRIPTION
		" The SIP L2 Table "
	::= { wfSipGroup 1 }

wfSipL2Entry OBJECT-TYPE
	SYNTAX	WfSipL2Entry
	ACCESS	not-accessible
	STATUS	mandatory
	DESCRIPTION
		" per circuit SIP Level 2 objects - wfSipL2Index
		    corresponds to Wellfleet circuit number "
	INDEX	{ wfSipL2Index }
	::= { wfSipL2 1 }

WfSipL2Entry ::= SEQUENCE {
	wfSipL2Index
		INTEGER,
	wfSipL2ReceivedCounts
		Counter,
	wfSipL2SentCounts
		Counter,
	wfSipHcsOrCRCErrors
		Counter,
	wfSipL2PayloadLengthErrors
		Counter,
	wfSipL2SequenceNumberErrors
		Counter,
	wfSipL2MidCurrentlyActiveErrors
		Counter,
	wfSipL2BomOrSSMsMIDErrors
		Counter,
	wfSipL2EomsMIDErrors
		Counter
}

wfSipL2Index OBJECT-TYPE
	SYNTAX	INTEGER {
		minimum(1),
		maximum(1024)
	}
	ACCESS	read-only
	STATUS	mandatory
	DESCRIPTION
		" this corresponds to the Wellfleet circuit number "
	::= { wfSipL2Entry 1 }

wfSipL2ReceivedCounts OBJECT-TYPE
	SYNTAX	Counter
	ACCESS	read-only
	STATUS	mandatory
	DESCRIPTION
		" total of unerrored received SIP L2 PDUs "
	::= { wfSipL2Entry 2 }

wfSipL2SentCounts OBJECT-TYPE
	SYNTAX	Counter
	ACCESS	read-only
	STATUS	mandatory
	DESCRIPTION
		" total of unerrored SIP L2 PDU's sent across the SNI "
	::= { wfSipL2Entry 3 }

wfSipHcsOrCRCErrors OBJECT-TYPE
	SYNTAX	Counter
	ACCESS	read-only
	STATUS	mandatory
	DESCRIPTION
		" total SIP L2 PDUs with HCS or CRC errors "
	::= { wfSipL2Entry 4 }

wfSipL2PayloadLengthErrors OBJECT-TYPE
	SYNTAX	Counter
	ACCESS	read-only
	STATUS	mandatory
	DESCRIPTION
		" total SIP L2 PDUs with length errors "
	::= { wfSipL2Entry 5 }

wfSipL2SequenceNumberErrors OBJECT-TYPE
	SYNTAX	Counter
	ACCESS	read-only
	STATUS	mandatory
	DESCRIPTION
		" total SIP L2 PDUs with unexpected sequence numbers "
	::= { wfSipL2Entry 6 }

wfSipL2MidCurrentlyActiveErrors OBJECT-TYPE
	SYNTAX	Counter
	ACCESS	read-only
	STATUS	mandatory
	DESCRIPTION
		" number of SIP L2 PDUs with BOMs previously started "
	::= { wfSipL2Entry 7 }

wfSipL2BomOrSSMsMIDErrors OBJECT-TYPE
	SYNTAX	Counter
	ACCESS	read-only
	STATUS	mandatory
	DESCRIPTION
		" number of SIP L2 PDUs with zero BOMs or SSMs not zero "
	::= { wfSipL2Entry 8 }

wfSipL2EomsMIDErrors OBJECT-TYPE
	SYNTAX	Counter
	ACCESS	read-only
	STATUS	mandatory
	DESCRIPTION
		" number of SIP L2 PDUs with zero EOMs or EOMs without BOMs "
	::= { wfSipL2Entry 9 }

wfSipDs1Plcp OBJECT-TYPE
	SYNTAX	SEQUENCE OF WfSipDs1PlcpEntry
	ACCESS	not-accessible
	STATUS	mandatory
	DESCRIPTION
		" The SIP DS1 PLCP Table "
	::= { wfSipPlcpGroup 1 }

wfSipDs1PlcpEntry OBJECT-TYPE
	SYNTAX	WfSipDs1PlcpEntry
	ACCESS	not-accessible
	STATUS	mandatory
	DESCRIPTION
		" per circuit DS1 PLCP objects - wfSipDs1PlcpIndex
		    corresponds to Wellfleet circuit number "
	INDEX	{ wfSipDs1PlcpIndex }
	::= { wfSipDs1Plcp 1 }

WfSipDs1PlcpEntry ::= SEQUENCE {
	wfSipDs1PlcpIndex
		INTEGER,
	wfSipDs1PlcpSEFs
		Counter,
	wfSipDs1PlcpAlarmState
		INTEGER,
	wfSipDs1PlcpUASs
		Counter
}

wfSipDs1PlcpIndex OBJECT-TYPE
	SYNTAX	INTEGER {
		minimum(1),
		maximum(1024)
	}
	ACCESS	read-only
	STATUS	mandatory
	DESCRIPTION
		" this corresponds to the Wellfleet circuit number "
	::= { wfSipDs1PlcpEntry 1 }

wfSipDs1PlcpSEFs OBJECT-TYPE
	SYNTAX	Counter
	ACCESS	read-only
	STATUS	mandatory
	DESCRIPTION
		" number of second intervals containing one or more
		    severely errored seconds "
	::= { wfSipDs1PlcpEntry 2 }

wfSipDs1PlcpAlarmState OBJECT-TYPE
	SYNTAX	INTEGER {
		noalarm(1),
		receivedfarendalarm(2),
		incominglof(3)
	}
	ACCESS	read-only
	STATUS	mandatory
	DESCRIPTION
		" alarm state "
	::= { wfSipDs1PlcpEntry 3 }

wfSipDs1PlcpUASs OBJECT-TYPE
	SYNTAX	Counter
	ACCESS	read-only
	STATUS	mandatory
	DESCRIPTION
		" number of second intervals containing one or more unavailable
		    seconds "
	::= { wfSipDs1PlcpEntry 4 }

wfSipDs3Plcp OBJECT-TYPE
	SYNTAX	SEQUENCE OF WfSipDs3PlcpEntry
	ACCESS	not-accessible
	STATUS	mandatory
	DESCRIPTION
		" The SIP DS3 PLCP Table "
	::= { wfSipPlcpGroup 2 }

wfSipDs3PlcpEntry OBJECT-TYPE
	SYNTAX	WfSipDs3PlcpEntry
	ACCESS	not-accessible
	STATUS	mandatory
	DESCRIPTION
		" per circuit DS3 PLCP objects - wfSipDs3PlcpIndex
		    corresponds to Wellfleet circuit number "
	INDEX	{ wfSipDs3PlcpIndex }
	::= { wfSipDs3Plcp 1 }

WfSipDs3PlcpEntry ::= SEQUENCE {
	wfSipDs3PlcpIndex
		INTEGER,
	wfSipDs3PlcpSEFs
		Counter,
	wfSipDs3PlcpAlarmState
		INTEGER,
	wfSipDs3PlcpUASs
		Counter
}

wfSipDs3PlcpIndex OBJECT-TYPE
	SYNTAX	INTEGER {
		minimum(1),
		maximum(1024)
	}
	ACCESS	read-only
	STATUS	mandatory
	DESCRIPTION
		" this corresponds to the Wellfleet circuit number "
	::= { wfSipDs3PlcpEntry 1 }

wfSipDs3PlcpSEFs OBJECT-TYPE
	SYNTAX	Counter
	ACCESS	read-only
	STATUS	mandatory
	DESCRIPTION
		" number of second intervals containing one or more
		    severely errored seconds "
	::= { wfSipDs3PlcpEntry 2 }

wfSipDs3PlcpAlarmState OBJECT-TYPE
	SYNTAX	INTEGER {
		noalarm(1),
		receivedfarendalarm(2),
		incominglof(3)
	}
	ACCESS	read-only
	STATUS	mandatory
	DESCRIPTION
		" alarm state "
	::= { wfSipDs3PlcpEntry 3 }

wfSipDs3PlcpUASs OBJECT-TYPE
	SYNTAX	Counter
	ACCESS	read-only
	STATUS	mandatory
	DESCRIPTION
		" number of second intervals containing one or more unavailable
		    seconds "
	::= { wfSipDs3PlcpEntry 4 }

wfSmdsCircuitTable OBJECT-TYPE
	SYNTAX	SEQUENCE OF WfSmdsCircuitEntry
	ACCESS	not-accessible
	STATUS	mandatory
	DESCRIPTION
		" The Wellfleet SMDS Circuit Record "
	::= { wfWanGroup 3 }

wfSmdsCircuitEntry OBJECT-TYPE
	SYNTAX	WfSmdsCircuitEntry
	ACCESS	not-accessible
	STATUS	mandatory
	DESCRIPTION
		" per Wellfleet circuit SMDS configuration parameters and
		    counters "
	INDEX	{ wfSmdsCircuitID }
	::= { wfSmdsCircuitTable 1 }

WfSmdsCircuitEntry ::= SEQUENCE {
	wfSmdsCircuitDelete
		INTEGER,
	wfSmdsCircuitDisable
		INTEGER,
	wfSmdsCircuitState
		INTEGER,
	wfSmdsCircuitID
		INTEGER,
	wfSmdsCircuitIndivAddr
		OCTET STRING,
	wfSmdsCircuitGroupAddr
		OCTET STRING,
	wfSmdsCircuitArpAddr
		OCTET STRING,
	wfSmdsCircuitDisableHrtbtPoll
		INTEGER,
	wfSmdsCircuitHrtbtPollInterval
		INTEGER,
	wfSmdsCircuitHrtbtPollDownCount
		INTEGER,
	wfSmdsCircuitDisableNetMgmt
		INTEGER,
	wfSmdsCircuitSipL3ReceivedIndividualDAs
		Counter,
	wfSmdsCircuitSipL3ReceivedGAs
		Counter,
	wfSmdsCircuitSipL3SentIndividualDAs
		Counter,
	wfSmdsCircuitSipL3SentGAs
		Counter,
	wfSmdsCircuitSipL3VersionSupport
		INTEGER
}

wfSmdsCircuitDelete OBJECT-TYPE
	SYNTAX	INTEGER {
		created(1),
		deleted(2)
	}
	ACCESS	read-write
	STATUS	mandatory
	DESCRIPTION
		" create/delete parameter, dflt = created "
	DEFVAL	{ created }
	::= { wfSmdsCircuitEntry 1 }

wfSmdsCircuitDisable OBJECT-TYPE
	SYNTAX	INTEGER {
		enabled(1),
		disabled(2)
	}
	ACCESS	read-write
	STATUS	mandatory
	DESCRIPTION
		" enable/disable parameter, dflt = enabled"
	DEFVAL	{ enabled }
	::= { wfSmdsCircuitEntry 2 }

wfSmdsCircuitState OBJECT-TYPE
	SYNTAX	INTEGER {
		up(1),
		down(2),
		init(3),
		notpresent(4)
	}
	ACCESS	read-only
	STATUS	mandatory
	DESCRIPTION
		" SMDS state variable, Up, Down Init, Not Present "
	DEFVAL	{ notpresent }
	::= { wfSmdsCircuitEntry 3 }

wfSmdsCircuitID OBJECT-TYPE
	SYNTAX	INTEGER {
		minimum(1),
		maximum(1023)
	}
	ACCESS	read-only
	STATUS	mandatory
	DESCRIPTION
		" cct number for this instance "
	::= { wfSmdsCircuitEntry 4 }

wfSmdsCircuitIndivAddr OBJECT-TYPE
	SYNTAX	OCTET STRING
	ACCESS	read-write
	STATUS	mandatory
	DESCRIPTION
		" SMDS E.164 Individual address for this Wellfleet
		    circuit - must be 8 octets long "
	::= { wfSmdsCircuitEntry 5 }

wfSmdsCircuitGroupAddr OBJECT-TYPE
	SYNTAX	OCTET STRING
	ACCESS	read-write
	STATUS	mandatory
	DESCRIPTION
		" SMDS E.164 Group address for this Wellfleet
		    circuit - must be 8 octets long "
	::= { wfSmdsCircuitEntry 6 }

wfSmdsCircuitArpAddr OBJECT-TYPE
	SYNTAX	OCTET STRING
	ACCESS	read-write
	STATUS	mandatory
	DESCRIPTION
		" SMDS E.164 ARP address for this Wellfleet
		    circuit - must be 8 octets long "
	::= { wfSmdsCircuitEntry 7 }

wfSmdsCircuitDisableHrtbtPoll OBJECT-TYPE
	SYNTAX	INTEGER {
		enabled(1),
		disabled(2)
	}
	ACCESS	read-write
	STATUS	mandatory
	DESCRIPTION
		" determine use of DXI heartbeat poll "
	DEFVAL	{ disabled }
	::= { wfSmdsCircuitEntry 8 }

wfSmdsCircuitHrtbtPollInterval OBJECT-TYPE
	SYNTAX	INTEGER {
		minimum(6),
		default(10)
	}
	ACCESS	read-write
	STATUS	mandatory
	DESCRIPTION
		" heartbeat polling messages get sent every this many
		    seconds - we don't want the polling interval to be
		    less than or equal to the unacknowledgment timer, which
		    is 5 seconds "
	DEFVAL	{ default }
	::= { wfSmdsCircuitEntry 9 }

wfSmdsCircuitHrtbtPollDownCount OBJECT-TYPE
	SYNTAX	INTEGER {
		minimum(1),
		default(3)
	}
	ACCESS	read-write
	STATUS	mandatory
	DESCRIPTION
		" if this many consecutive heartbeat polling messages
		    go unacknowledged, log an event declaring the line
		    down "
	DEFVAL	{ default }
	::= { wfSmdsCircuitEntry 10 }

wfSmdsCircuitDisableNetMgmt OBJECT-TYPE
	SYNTAX	INTEGER {
		enabled(1),
		disabled(2)
	}
	ACCESS	read-write
	STATUS	mandatory
	DESCRIPTION
		" determine use of LMI network management "
	DEFVAL	{ disabled }
	::= { wfSmdsCircuitEntry 11 }

wfSmdsCircuitSipL3ReceivedIndividualDAs OBJECT-TYPE
	SYNTAX	Counter
	ACCESS	read-only
	STATUS	mandatory
	DESCRIPTION
		" The total number of individually addressed SIP Level 3 PDUs
		    received from the remote system across the SNI. The total
		    includes only unerrored L3PDUs. "
	::= { wfSmdsCircuitEntry 12 }

wfSmdsCircuitSipL3ReceivedGAs OBJECT-TYPE
	SYNTAX	Counter
	ACCESS	read-only
	STATUS	mandatory
	DESCRIPTION
		" The total number of group addressed SIP Level 3 PDUs
		    received from the remote system across the SNI.  The 
		    total includes only unerrored L3PDUs. "
	::= { wfSmdsCircuitEntry 13 }

wfSmdsCircuitSipL3SentIndividualDAs OBJECT-TYPE
	SYNTAX	Counter
	ACCESS	read-only
	STATUS	mandatory
	DESCRIPTION
		" The number of individually addressed SIP Level 3 PDUs
		    that have been sent by this system across the SNI. "
	::= { wfSmdsCircuitEntry 14 }

wfSmdsCircuitSipL3SentGAs OBJECT-TYPE
	SYNTAX	Counter
	ACCESS	read-only
	STATUS	mandatory
	DESCRIPTION
		" The number of group addressed SIP L3PDUs that have been
		    sent by this system across the SNI. "
	::= { wfSmdsCircuitEntry 15 }

wfSmdsCircuitSipL3VersionSupport OBJECT-TYPE
	SYNTAX	INTEGER {
		version(1)
	}
	ACCESS	read-only
	STATUS	mandatory
	DESCRIPTION
		" A value which indicates the version(s) of SIP
		    that this interface supports.  The value is a sum.
		    This sum initially takes the value zero.  For each
		    version, V, that this interface supports, 2 raised
		    to (V - 1) is added to the sum. For example, a
		    port supporting versions 1 and 2 would have a
		    value of (2^(1-1)+2^(2-1))=3.  The
		    SipL3VersionSupport is effectively a bit mask with
		    Version 1 equal to the least significant bit (LSB). "
	DEFVAL	{ version }
	::= { wfSmdsCircuitEntry 16 }

wfSnmp		OBJECT IDENTIFIER ::= { wfSnmpGroup 1 }

wfSnmpDisable OBJECT-TYPE
	SYNTAX	INTEGER {
		enabled(1),
		disabled(2)
	}
	ACCESS	read-write
	STATUS	mandatory
	DESCRIPTION
		" Enables or disables the SNMP subsystem "
	DEFVAL	{ enabled }
	::= { wfSnmp 1 }

wfSnmpUseLock OBJECT-TYPE
	SYNTAX	INTEGER {
		enabled(1),
		disabled(2)
	}
	ACCESS	read-write
	STATUS	mandatory
	DESCRIPTION
		" Flag to indicate whether locking mechanism is enabled or disabled "
	DEFVAL	{ enabled }
	::= { wfSnmp 2 }

wfSnmpLockAddress OBJECT-TYPE
	SYNTAX	IpAddress
	ACCESS	read-write
	STATUS	mandatory
	DESCRIPTION
		" Address of remote manager that is enforcing the lock. This value is set
		  by the SNMP agent.  Remote managers are only allowed to clear it.
		 "
	::= { wfSnmp 3 }

wfSnmpLockTimeOut OBJECT-TYPE
	SYNTAX	INTEGER {
		default(2),
		minimum(1),
		maximum(60)
	}
	ACCESS	read-write
	STATUS	mandatory
	DESCRIPTION
		" The maximum time (in minutes) a lock can be idle before it is cleared. "
	DEFVAL	{ default }
	::= { wfSnmp 4 }

wfSnmpAuth OBJECT-TYPE
	SYNTAX	INTEGER {
		trivial(1),
		party(2)
	}
	ACCESS	read-write
	STATUS	mandatory
	DESCRIPTION
		" The type of authentication used by the agent "
	DEFVAL	{ trivial }
	::= { wfSnmp 5 }

wfSnmpInPkts OBJECT-TYPE
	SYNTAX	Counter
	ACCESS	read-only
	STATUS	mandatory
	DESCRIPTION
		" Total number of PDUs received by SNMP from transport entity "
	::= { wfSnmp 6 }

wfSnmpOutPkts OBJECT-TYPE
	SYNTAX	Counter
	ACCESS	read-only
	STATUS	mandatory
	DESCRIPTION
		" Total number of PDUs sent by SNMP to transport entity "
	::= { wfSnmp 7 }

wfSnmpInBadVersions OBJECT-TYPE
	SYNTAX	Counter
	ACCESS	read-only
	STATUS	mandatory
	DESCRIPTION
		" Total number of PDUs requesting unsupported versions "
	::= { wfSnmp 8 }

wfSnmpInBadCommunityNames OBJECT-TYPE
	SYNTAX	Counter
	ACCESS	read-only
	STATUS	mandatory
	DESCRIPTION
		" Total number of PDUs which had an invalid community string "
	::= { wfSnmp 9 }

wfSnmpInBadCommunityUses OBJECT-TYPE
	SYNTAX	Counter
	ACCESS	read-only
	STATUS	mandatory
	DESCRIPTION
		" Total number of PDUs requesting an operation unsupported by the community "
	::= { wfSnmp 10 }

wfSnmpInASNParseErrs OBJECT-TYPE
	SYNTAX	Counter
	ACCESS	read-only
	STATUS	mandatory
	DESCRIPTION
		" Total number of ASN.1 parsing errors during decoding "
	::= { wfSnmp 11 }

wfSnmpInBadTypes OBJECT-TYPE
	SYNTAX	Counter
	ACCESS	read-only
	STATUS	mandatory
	DESCRIPTION
		" Total number of PDUs having an unknown PDU type "
	::= { wfSnmp 12 }

wfSnmpInTooBigs OBJECT-TYPE
	SYNTAX	Counter
	ACCESS	read-only
	STATUS	mandatory
	DESCRIPTION
		" Total number of PDUs delivered with ErrorStatus='tooBig' "
	::= { wfSnmp 13 }

wfSnmpInNoSuchNames OBJECT-TYPE
	SYNTAX	Counter
	ACCESS	read-only
	STATUS	mandatory
	DESCRIPTION
		" Total number of PDUs delivered with ErrorStatus='noSuchName' "
	::= { wfSnmp 14 }

wfSnmpInBadValues OBJECT-TYPE
	SYNTAX	Counter
	ACCESS	read-only
	STATUS	mandatory
	DESCRIPTION
		" Total number of PDUs delivered with ErrorStatus='badValue' "
	::= { wfSnmp 15 }

wfSnmpInReadOnlys OBJECT-TYPE
	SYNTAX	Counter
	ACCESS	read-only
	STATUS	mandatory
	DESCRIPTION
		" Total number of PDUs delivered with ErrorStatus='readOnly' "
	::= { wfSnmp 16 }

wfSnmpInGenErrs OBJECT-TYPE
	SYNTAX	Counter
	ACCESS	read-only
	STATUS	mandatory
	DESCRIPTION
		" Total number of PDUs delivered with ErrorStatus='genErr' "
	::= { wfSnmp 17 }

wfSnmpInTotalReqVars OBJECT-TYPE
	SYNTAX	Counter
	ACCESS	read-only
	STATUS	mandatory
	DESCRIPTION
		" Total number of MIB objects retrieved successfully by the agent "
	::= { wfSnmp 18 }

wfSnmpInTotalSetVars OBJECT-TYPE
	SYNTAX	Counter
	ACCESS	read-only
	STATUS	mandatory
	DESCRIPTION
		" Total number of MIB objects which have been SET successfully "
	::= { wfSnmp 19 }

wfSnmpInGetRequests OBJECT-TYPE
	SYNTAX	Counter
	ACCESS	read-only
	STATUS	mandatory
	DESCRIPTION
		" Total number of Get-Request PDUS accepted and processed"
	::= { wfSnmp 20 }

wfSnmpInGetNexts OBJECT-TYPE
	SYNTAX	Counter
	ACCESS	read-only
	STATUS	mandatory
	DESCRIPTION
		" Total number of GetNext-Request PDUS accepted and processed"
	::= { wfSnmp 21 }

wfSnmpInSetRequests OBJECT-TYPE
	SYNTAX	Counter
	ACCESS	read-only
	STATUS	mandatory
	DESCRIPTION
		" Total number of Set-Request PDUS accepted and processed"
	::= { wfSnmp 22 }

wfSnmpInGetResponses OBJECT-TYPE
	SYNTAX	Counter
	ACCESS	read-only
	STATUS	mandatory
	DESCRIPTION
		" Total number of GetResponse PDUs accepted and processed"
	::= { wfSnmp 23 }

wfSnmpInTraps OBJECT-TYPE
	SYNTAX	Counter
	ACCESS	read-only
	STATUS	mandatory
	DESCRIPTION
		" Total number of Trap PDUs accepted and processed"
	::= { wfSnmp 24 }

wfSnmpOutTooBigs OBJECT-TYPE
	SYNTAX	Counter
	ACCESS	read-only
	STATUS	mandatory
	DESCRIPTION
		" Total number of PDUs generated by the agent with ErrorStatus='tooBig' "
	::= { wfSnmp 25 }

wfSnmpOutNoSuchNames OBJECT-TYPE
	SYNTAX	Counter
	ACCESS	read-only
	STATUS	mandatory
	DESCRIPTION
		" Total number of PDUs generated by the agent with ErrorStatus='noSuchName' "
	::= { wfSnmp 26 }

wfSnmpOutBadValues OBJECT-TYPE
	SYNTAX	Counter
	ACCESS	read-only
	STATUS	mandatory
	DESCRIPTION
		" Total number of PDUs generated by the agent with ErrorStatus='badValue' "
	::= { wfSnmp 27 }

wfSnmpOutReadOnlys OBJECT-TYPE
	SYNTAX	Counter
	ACCESS	read-only
	STATUS	mandatory
	DESCRIPTION
		" Total number of PDUs generated by the agent with ErrorStatus='readOnly' "
	::= { wfSnmp 28 }

wfSnmpOutGenErrs OBJECT-TYPE
	SYNTAX	Counter
	ACCESS	read-only
	STATUS	mandatory
	DESCRIPTION
		" Total number of PDUs generated by the agent with ErrorStatus='genErr' "
	::= { wfSnmp 29 }

wfSnmpOutGetRequests OBJECT-TYPE
	SYNTAX	Counter
	ACCESS	read-only
	STATUS	mandatory
	DESCRIPTION
		" Total number of Get-Request PDUs generated by the agent "
	::= { wfSnmp 30 }

wfSnmpOutGetNexts OBJECT-TYPE
	SYNTAX	Counter
	ACCESS	read-only
	STATUS	mandatory
	DESCRIPTION
		" Total number of Get-Next-Request PDUs generated by the agent "
	::= { wfSnmp 31 }

wfSnmpOutSetRequests OBJECT-TYPE
	SYNTAX	Counter
	ACCESS	read-only
	STATUS	mandatory
	DESCRIPTION
		" Total number of Set-Request PDUs generated by the agent "
	::= { wfSnmp 32 }

wfSnmpOutGetResponses OBJECT-TYPE
	SYNTAX	Counter
	ACCESS	read-only
	STATUS	mandatory
	DESCRIPTION
		" Total number of Get-Response PDUs generated by the agent "
	::= { wfSnmp 33 }

wfSnmpOutTraps OBJECT-TYPE
	SYNTAX	Counter
	ACCESS	read-only
	STATUS	mandatory
	DESCRIPTION
		" Total number of Trap PDUs generated by the agent "
	::= { wfSnmp 34 }

wfSnmpEnableAuthTraps OBJECT-TYPE
	SYNTAX	INTEGER {
		enabled(1),
		disabled(2)
	}
	ACCESS	read-write
	STATUS	mandatory
	DESCRIPTION
		" Idicates whether agent can generate Authentication Failure Traps "
	DEFVAL	{ enabled }
	::= { wfSnmp 35 }

wfSnmpTrapDebug OBJECT-TYPE
	SYNTAX	INTEGER {
		on(1),
		off(2)
	}
	ACCESS	read-write
	STATUS	mandatory
	DESCRIPTION
		" This attribute controls the specific trap filter for debug messages "
	DEFVAL	{ on }
	::= { wfSnmp 36 }

wfSnmpTrapTrace OBJECT-TYPE
	SYNTAX	INTEGER {
		on(1),
		off(2)
	}
	ACCESS	read-write
	STATUS	mandatory
	DESCRIPTION
		" This attribute controls the specific trap filter for trace messages "
	DEFVAL	{ on }
	::= { wfSnmp 37 }

wfSnmpTrapInfo OBJECT-TYPE
	SYNTAX	INTEGER {
		on(1),
		off(2)
	}
	ACCESS	read-write
	STATUS	mandatory
	DESCRIPTION
		" This attribute controls the specific trap filter for informational
		   messages "
	DEFVAL	{ off }
	::= { wfSnmp 38 }

wfSnmpTrapWarn OBJECT-TYPE
	SYNTAX	INTEGER {
		on(1),
		off(2)
	}
	ACCESS	read-write
	STATUS	mandatory
	DESCRIPTION
		" This attribute controls the specific trap filter for warning messages "
	DEFVAL	{ off }
	::= { wfSnmp 39 }

wfSnmpTrapFault OBJECT-TYPE
	SYNTAX	INTEGER {
		on(1),
		off(2)
	}
	ACCESS	read-write
	STATUS	mandatory
	DESCRIPTION
		" This attribute controls the specific trap filter for fault messages "
	DEFVAL	{ off }
	::= { wfSnmp 40 }

wfSnmpCommTable OBJECT-TYPE
	SYNTAX	SEQUENCE OF WfSnmpCommEntry
	ACCESS	not-accessible
	STATUS	mandatory
	DESCRIPTION
		" A table containing valid management communities "
	::= { wfSnmpGroup 2 }

wfSnmpCommEntry OBJECT-TYPE
	SYNTAX	WfSnmpCommEntry
	ACCESS	not-accessible
	STATUS	mandatory
	DESCRIPTION
		" Information about a particular community "
	INDEX	{ wfSnmpCommIndex }
	::= { wfSnmpCommTable 1 }

WfSnmpCommEntry ::= SEQUENCE {
	wfSnmpCommDelete
		INTEGER,
	wfSnmpCommIndex
		INTEGER,
	wfSnmpCommName
		DisplayString,
	wfSnmpCommAccess
		INTEGER
}

wfSnmpCommDelete OBJECT-TYPE
	SYNTAX	INTEGER {
		created(1),
		deleted(2)
	}
	ACCESS	read-write
	STATUS	mandatory
	DESCRIPTION
		" A flag to indicate community instance deletion "
	DEFVAL	{ created }
	::= { wfSnmpCommEntry 1 }

wfSnmpCommIndex OBJECT-TYPE
	SYNTAX	INTEGER
	ACCESS	read-only
	STATUS	mandatory
	DESCRIPTION
		" A unique numeric value that has a one to one correspondence with the
		   community name "
	::= { wfSnmpCommEntry 2 }

wfSnmpCommName OBJECT-TYPE
	SYNTAX	DisplayString
	ACCESS	read-write
	STATUS	mandatory
	DESCRIPTION
		" Community name "
	::= { wfSnmpCommEntry 3 }

wfSnmpCommAccess OBJECT-TYPE
	SYNTAX	INTEGER {
		readonly(1),
		readwrite(2)
	}
	ACCESS	read-write
	STATUS	mandatory
	DESCRIPTION
		" Community access mode "
	DEFVAL	{ readonly }
	::= { wfSnmpCommEntry 4 }

wfSnmpMgrTable OBJECT-TYPE
	SYNTAX	SEQUENCE OF WfSnmpMgrEntry
	ACCESS	not-accessible
	STATUS	mandatory
	DESCRIPTION
		" A table containing managers and their respective communities "
	::= { wfSnmpGroup 3 }

wfSnmpMgrEntry OBJECT-TYPE
	SYNTAX	WfSnmpMgrEntry
	ACCESS	not-accessible
	STATUS	mandatory
	DESCRIPTION
		" Information about a manager of a community "
	INDEX	{ wfSnmpMgrCommIndex,
		wfSnmpMgrAddress }
	::= { wfSnmpMgrTable 1 }

WfSnmpMgrEntry ::= SEQUENCE {
	wfSnmpMgrDelete
		INTEGER,
	wfSnmpMgrCommIndex
		INTEGER,
	wfSnmpMgrAddress
		IpAddress,
	wfSnmpMgrName
		DisplayString,
	wfSnmpMgrTrapPort
		INTEGER,
	wfSnmpMgrTraps
		INTEGER
}

wfSnmpMgrDelete OBJECT-TYPE
	SYNTAX	INTEGER {
		created(1),
		deleted(2)
	}
	ACCESS	read-write
	STATUS	mandatory
	DESCRIPTION
		" A flag to indicate manager instance deletion */ "
	DEFVAL	{ created }
	::= { wfSnmpMgrEntry 1 }

wfSnmpMgrCommIndex OBJECT-TYPE
	SYNTAX	INTEGER
	ACCESS	read-only
	STATUS	mandatory
	DESCRIPTION
		" Associates this manager with a community in the community table "
	::= { wfSnmpMgrEntry 2 }

wfSnmpMgrAddress OBJECT-TYPE
	SYNTAX	IpAddress
	ACCESS	read-only
	STATUS	mandatory
	DESCRIPTION
		" IP Address of this manager "
	::= { wfSnmpMgrEntry 3 }

wfSnmpMgrName OBJECT-TYPE
	SYNTAX	DisplayString
	ACCESS	read-write
	STATUS	mandatory
	DESCRIPTION
		" A name for this manager "
	::= { wfSnmpMgrEntry 4 }

wfSnmpMgrTrapPort OBJECT-TYPE
	SYNTAX	INTEGER
	ACCESS	read-write
	STATUS	mandatory
	DESCRIPTION
		" The UDP Port on which this manager is listening for traps "
	DEFVAL	{ 162 }
	::= { wfSnmpMgrEntry 5 }

wfSnmpMgrTraps OBJECT-TYPE
	SYNTAX	INTEGER {
		none(1),
		generic(2),
		specific(4),
		all(7)
	}
	ACCESS	read-write
	STATUS	mandatory
	DESCRIPTION
		" Allowable Traps to be sent to Manager, defaults to only generic trap types "
	DEFVAL	{ generic }
	::= { wfSnmpMgrEntry 6 }

wfBrStp		OBJECT IDENTIFIER ::= { wfSpanningTree 1 }

wfBrStpBaseDelete OBJECT-TYPE
	SYNTAX	INTEGER {
		created(1),
		deleted(2)
	}
	ACCESS	read-write
	STATUS	mandatory
	DESCRIPTION
		" Create/Delete parameter. Default is created.
		  Users perform an SNMP SET operation on this
		  object in order to create/delete the Spanning
		  tree. "
	DEFVAL	{ created }
	::= { wfBrStp 1 }

wfBrStpBaseEnable OBJECT-TYPE
	SYNTAX	INTEGER {
		enabled(1),
		disabled(2)
	}
	ACCESS	read-write
	STATUS	mandatory
	DESCRIPTION
		" Enable/Disable parameter. Default is enabled.
		  Users perform an SNMP SET operation on this
		  object in order to enable/disable the spanning
		  tree. "
	DEFVAL	{ enabled }
	::= { wfBrStp 2 }

wfBrStpBaseState OBJECT-TYPE
	SYNTAX	INTEGER {
		up(1),
		down(2),
		init(3),
		pres(4)
	}
	ACCESS	read-only
	STATUS	mandatory
	DESCRIPTION
		" The current state of the spanning tree. "
	DEFVAL	{ down }
	::= { wfBrStp 3 }

wfBrStpProtocolSpecification OBJECT-TYPE
	SYNTAX	INTEGER {
		unknown(1),
		declb100(2),
		ieee8021d(3)
	}
	ACCESS	read-only
	STATUS	mandatory
	DESCRIPTION
		" The version of the Spanning Tree protocol being
		  run. "
	DEFVAL	{ ieee8021d }
	::= { wfBrStp 4 }

wfBrStpBridgeID OBJECT-TYPE
	SYNTAX	OCTET STRING
	ACCESS	read-write
	STATUS	mandatory
	DESCRIPTION
		" The Spanning Tree Bridge ID assigned to this
		  bridge.  It is a 8-octet string.  The first two
		  octets make up the bridge priority, and the last
		  six are the MAC address of this bridge, which
		  is commonly the MAC address of the first port
		  on the bridge. "
	::= { wfBrStp 5 }

wfBrStpTimeSinceTopologyChange OBJECT-TYPE
	SYNTAX	Counter
	ACCESS	read-only
	STATUS	mandatory
	DESCRIPTION
		" The time (in hundredths of a second) since the last
		  topology change was detected by the bridge. "
	::= { wfBrStp 6 }

wfBrStpTopChanges OBJECT-TYPE
	SYNTAX	Counter
	ACCESS	read-only
	STATUS	mandatory
	DESCRIPTION
		" The total number of topology changes detected by
		  this bridge since it was last reset or initialized "
	::= { wfBrStp 7 }

wfBrStpDesignatedRoot OBJECT-TYPE
	SYNTAX	OCTET STRING
	ACCESS	read-only
	STATUS	mandatory
	DESCRIPTION
		" The bridge ID of the root of the spanning tree as
		  determined by the Spanning Tree Protocol as 
		  executed by the bridge. This value is used as
		  the Root Identifier parameter in all Configuration
		  Bridge PDUs originated by this node. It is a 8-octet 
		  string.  The first two octets make up the priority, 
		  and the last six are the MAC address of the designated
		  root bridge. "
	::= { wfBrStp 8 }

wfBrStpRootCost OBJECT-TYPE
	SYNTAX	INTEGER
	ACCESS	read-only
	STATUS	mandatory
	DESCRIPTION
		" The cost of the path to the root as seen from this
		  bridge. "
	::= { wfBrStp 9 }

wfBrStpRootPort OBJECT-TYPE
	SYNTAX	INTEGER
	ACCESS	read-only
	STATUS	mandatory
	DESCRIPTION
		" The port identifier of the port which offers the
		    lowest cost path from this bridge to the root bridge. "
	::= { wfBrStp 10 }

wfBrStpMaxAge OBJECT-TYPE
	SYNTAX	INTEGER
	ACCESS	read-only
	STATUS	mandatory
	DESCRIPTION
		" The maximum age of the Spanning Tree Protocol
		  information learned from the network on any port
		  before it is discarded, in hundredths of a second.
		  This represents the value actually in use by the 
		  bridge. "
	::= { wfBrStp 11 }

wfBrStpHelloTime OBJECT-TYPE
	SYNTAX	INTEGER
	ACCESS	read-only
	STATUS	mandatory
	DESCRIPTION
		" The amount of time between transmission of
		  configuration BPDUs by this bridge on any port,
		  when it is the root of the spanning tree or
		  trying to become so, in hundreths of a second.  
		  This represents the value actually in use by the bridge. "
	::= { wfBrStp 12 }

wfBrStpHoldTime OBJECT-TYPE
	SYNTAX	INTEGER {
		time(100)
	}
	ACCESS	read-only
	STATUS	mandatory
	DESCRIPTION
		" The value that determines the interval length during
		  which no more than two configuration BPDUs shall be
		  transmitted by this bridge, in hundredths of a second. "
	DEFVAL	{ time }
	::= { wfBrStp 13 }

wfBrStpForwardDelay OBJECT-TYPE
	SYNTAX	INTEGER
	ACCESS	read-only
	STATUS	mandatory
	DESCRIPTION
		" The time, in hundredths of a second, that a port
		  on this bridge will stay in a transitional state
		  (e.g. LISTENING) before moving to the next state
		  (e.g. LEARNING).  This value is also used to age
		  all dynamic entries in the Forwarding Database
		  when a topology changed has been detected and is
		  underway. This represents the value actually in 
		  use by the bridge. "
	::= { wfBrStp 14 }

wfBrStpBridgeMaxAge OBJECT-TYPE
	SYNTAX	INTEGER {
		minimum(600),
		default(2000),
		maximum(4000)
	}
	ACCESS	read-write
	STATUS	mandatory
	DESCRIPTION
		" The value that all bridges use for MaxAge when
		  this bridge acting as the root. "
	DEFVAL	{ default }
	::= { wfBrStp 15 }

wfBrStpBridgeHelloTime OBJECT-TYPE
	SYNTAX	INTEGER {
		minimum(100),
		default(200),
		maximum(1000)
	}
	ACCESS	read-write
	STATUS	mandatory
	DESCRIPTION
		" The value that all bridges use for HelloTime when
		  this bridge acting as the root. "
	DEFVAL	{ default }
	::= { wfBrStp 16 }

wfBrStpBridgeForwardDelay OBJECT-TYPE
	SYNTAX	INTEGER {
		minimum(400),
		default(1500),
		maximum(3000)
	}
	ACCESS	read-write
	STATUS	mandatory
	DESCRIPTION
		" The value that all bridges use for ForwardDelay when
		  this bridge acting as the root. "
	DEFVAL	{ default }
	::= { wfBrStp 17 }

wfBrStpInterface OBJECT-TYPE
	SYNTAX	SEQUENCE OF WfBrStpInterfaceEntry
	ACCESS	not-accessible
	STATUS	mandatory
	DESCRIPTION
		" inst_id[1] = wfBrStpInterfaceCircuit "
	::= { wfSpanningTree 2 }

wfBrStpInterfaceEntry OBJECT-TYPE
	SYNTAX	WfBrStpInterfaceEntry
	ACCESS	not-accessible
	STATUS	mandatory
	DESCRIPTION
		" An entry in wfBrStpInterface. "
	INDEX	{ wfBrStpInterfaceCircuit }
	::= { wfBrStpInterface 1 }

WfBrStpInterfaceEntry ::= SEQUENCE {
	wfBrStpInterfaceDelete
		INTEGER,
	wfBrStpInterfaceEnable
		INTEGER,
	wfBrStpInterfaceCircuit
		INTEGER,
	wfBrStpInterfacePriority
		INTEGER,
	wfBrStpInterfaceState
		INTEGER,
	wfBrStpInterfaceMultiCastAddr
		OCTET STRING,
	wfBrStpInterfacePathCost
		INTEGER,
	wfBrStpInterfaceDesignatedRoot
		OCTET STRING,
	wfBrStpInterfaceDesignatedCost
		INTEGER,
	wfBrStpInterfaceDesignatedBridge
		OCTET STRING,
	wfBrStpInterfaceDesignatedPort
		INTEGER,
	wfBrStpInterfaceForwardTransitions
		Counter,
	wfBrStpInterfacePktsXmitd
		Counter,
	wfBrStpInterfacePktsRcvd
		Counter
}

wfBrStpInterfaceDelete OBJECT-TYPE
	SYNTAX	INTEGER {
		created(1),
		deleted(2)
	}
	ACCESS	read-write
	STATUS	mandatory
	DESCRIPTION
		" Create/Delete parameter. Default is created.
		  Users perform an SNMP SET operation on this
		  object in order to create/delete an interface
		  for the Spanning Tree. "
	DEFVAL	{ created }
	::= { wfBrStpInterfaceEntry 1 }

wfBrStpInterfaceEnable OBJECT-TYPE
	SYNTAX	INTEGER {
		enabled(1),
		disabled(2)
	}
	ACCESS	read-write
	STATUS	mandatory
	DESCRIPTION
		" Enable/Disable parameter. Default is enabled.
		  Users perform an SNMP SET operation on this
		  object in order to enable/disable an interface
		  for the Spanning Tree. "
	DEFVAL	{ enabled }
	::= { wfBrStpInterfaceEntry 2 }

wfBrStpInterfaceCircuit OBJECT-TYPE
	SYNTAX	INTEGER
	ACCESS	read-only
	STATUS	mandatory
	DESCRIPTION
		" The circuit number on which this interface is defined. "
	::= { wfBrStpInterfaceEntry 3 }

wfBrStpInterfacePriority OBJECT-TYPE
	SYNTAX	INTEGER {
		default(128),
		maximum(255)
	}
	ACCESS	read-write
	STATUS	mandatory
	DESCRIPTION
		" The value of the priority field which is contained in
		  the first octet of the (2 octet long) port ID for this
		  circuit. The other octet of the port ID is given by
		  wfBrStpInterfaceCircuit. "
	DEFVAL	{ default }
	::= { wfBrStpInterfaceEntry 4 }

wfBrStpInterfaceState OBJECT-TYPE
	SYNTAX	INTEGER {
		disabled(1),
		blocking(2),
		listening(3),
		learning(4),
		forwarding(5),
		broken(6)
	}
	ACCESS	read-only
	STATUS	mandatory
	DESCRIPTION
		" The current state of the port as defined by the
		  application of the Spanning Tree Protocol. "
	DEFVAL	{ disabled }
	::= { wfBrStpInterfaceEntry 5 }

wfBrStpInterfaceMultiCastAddr OBJECT-TYPE
	SYNTAX	OCTET STRING
	ACCESS	read-only
	STATUS	mandatory
	DESCRIPTION
		" The MAC address used as the destination for all
		  BPDU packets generated out this port. "
	::= { wfBrStpInterfaceEntry 6 }

wfBrStpInterfacePathCost OBJECT-TYPE
	SYNTAX	INTEGER {
		minimum(1),
		maximum(65535)
	}
	ACCESS	read-write
	STATUS	mandatory
	DESCRIPTION
		" The contribution of this port the the root
		  path cost of paths toward the spanning tree
		  root which include this port. "
	DEFVAL	{ minimum }
	::= { wfBrStpInterfaceEntry 7 }

wfBrStpInterfaceDesignatedRoot OBJECT-TYPE
	SYNTAX	OCTET STRING
	ACCESS	read-only
	STATUS	mandatory
	DESCRIPTION
		" The unique Bridge Identifier of the Bridge recorded
		  as the Root in the Configuration BPDUs transmitted
		  by the Designated Bridge for the segment to which this
		  port is attached.  Bridge IDs are made up of a
		  2-byte priority field, and a 6-byte MAC address. "
	::= { wfBrStpInterfaceEntry 8 }

wfBrStpInterfaceDesignatedCost OBJECT-TYPE
	SYNTAX	INTEGER
	ACCESS	read-only
	STATUS	mandatory
	DESCRIPTION
		" The path cost of the Designated Port of the
		  segment connected to this port. This value
		  is compared to the Root Path Cost field in
		  received bridge PDUs. "
	::= { wfBrStpInterfaceEntry 9 }

wfBrStpInterfaceDesignatedBridge OBJECT-TYPE
	SYNTAX	OCTET STRING
	ACCESS	read-only
	STATUS	mandatory
	DESCRIPTION
		" The Bridge Identifier of the bridge which this
		  port considers to be the Designated Bridge for
		  this port's segment. "
	::= { wfBrStpInterfaceEntry 10 }

wfBrStpInterfaceDesignatedPort OBJECT-TYPE
	SYNTAX	INTEGER
	ACCESS	read-only
	STATUS	mandatory
	DESCRIPTION
		" The Port Identifier of the port on the Designated
		  Bridge for this port's segment. "
	::= { wfBrStpInterfaceEntry 11 }

wfBrStpInterfaceForwardTransitions OBJECT-TYPE
	SYNTAX	Counter
	ACCESS	read-only
	STATUS	mandatory
	DESCRIPTION
		" The number of times this port has transitioned
		  from the Learning State to the Forwarding state. "
	::= { wfBrStpInterfaceEntry 12 }

wfBrStpInterfacePktsXmitd OBJECT-TYPE
	SYNTAX	Counter
	ACCESS	read-only
	STATUS	mandatory
	DESCRIPTION
		" The number of BPDU packets transmitted out this port "
	::= { wfBrStpInterfaceEntry 13 }

wfBrStpInterfacePktsRcvd OBJECT-TYPE
	SYNTAX	Counter
	ACCESS	read-only
	STATUS	mandatory
	DESCRIPTION
		" The number of BPDU packets received on this port "
	::= { wfBrStpInterfaceEntry 14 }

wfBrSr		OBJECT IDENTIFIER ::= { wfBrSourceRouting 1 }

wfBrSrBaseDelete OBJECT-TYPE
	SYNTAX	INTEGER {
		created(1),
		deleted(2)
	}
	ACCESS	read-write
	STATUS	mandatory
	DESCRIPTION
		" Create/Delete parameter. Default is created.
		  Users perform an SNMP SET operation on this
		  object in order to create/delete the bridge. "
	DEFVAL	{ created }
	::= { wfBrSr 1 }

wfBrSrBaseDisable OBJECT-TYPE
	SYNTAX	INTEGER {
		enabled(1),
		disabled(2)
	}
	ACCESS	read-write
	STATUS	mandatory
	DESCRIPTION
		" Enable/Disable parameter. Default is enabled.
		  Users perform an SNMP SET operation on this
		  object in order to enable/disable the bridge. "
	DEFVAL	{ enabled }
	::= { wfBrSr 2 }

wfBrSrBaseState OBJECT-TYPE
	SYNTAX	INTEGER {
		up(1),
		down(2),
		init(3),
		notpresent(4)
	}
	ACCESS	read-only
	STATUS	mandatory
	DESCRIPTION
		" The current state of the SR bridge. "
	DEFVAL	{ down }
	::= { wfBrSr 3 }

wfBrSrBaseInternalLanId OBJECT-TYPE
	SYNTAX	INTEGER
	ACCESS	read-write
	STATUS	mandatory
	DESCRIPTION
		" The SR bridge internal LAN ID "
	::= { wfBrSr 4 }

wfBrSrBaseBridgeId OBJECT-TYPE
	SYNTAX	INTEGER
	ACCESS	read-write
	STATUS	mandatory
	DESCRIPTION
		" The SR bridge Id "
	::= { wfBrSr 5 }

wfBrSrBaseGroupLanId OBJECT-TYPE
	SYNTAX	INTEGER
	ACCESS	read-write
	STATUS	mandatory
	DESCRIPTION
		" The SR bridge Group LAN ID "
	DEFVAL	{ 4095 }
	::= { wfBrSr 6 }

wfBrSrBaseIpEncapsDisable OBJECT-TYPE
	SYNTAX	INTEGER {
		enabled(1),
		disabled(2)
	}
	ACCESS	read-write
	STATUS	mandatory
	DESCRIPTION
		" IP Encapsulation Enable/Disable "
	DEFVAL	{ disabled }
	::= { wfBrSr 7 }

wfBrSrBaseIpNetworkRingId OBJECT-TYPE
	SYNTAX	INTEGER
	ACCESS	read-write
	STATUS	mandatory
	DESCRIPTION
		" The ring number of a connected IP network "
	::= { wfBrSr 8 }

wfBrSrBaseIpInReceives OBJECT-TYPE
	SYNTAX	Counter
	ACCESS	read-only
	STATUS	mandatory
	DESCRIPTION
		" The number IP frames received by the network "
	::= { wfBrSr 9 }

wfBrSrBaseIpSeqErrors OBJECT-TYPE
	SYNTAX	Counter
	ACCESS	read-only
	STATUS	mandatory
	DESCRIPTION
		" The number IP frames received by the network "
	::= { wfBrSr 10 }

wfBrSrBaseIpMtuSize OBJECT-TYPE
	SYNTAX	INTEGER
	ACCESS	read-write
	STATUS	mandatory
	DESCRIPTION
		" to the LF code in the Route Control field "
	DEFVAL	{ 4562 }
	::= { wfBrSr 11 }

wfBrSrInterfaceTable OBJECT-TYPE
	SYNTAX	SEQUENCE OF WfBrSrInterfaceEntry
	ACCESS	not-accessible
	STATUS	mandatory
	DESCRIPTION
		" A table that contains information about every
		  interface that is associated with this
		  source routing bridge.
		  inst_id[1] = wfBrSrInterfaceCircuit "
	::= { wfBrSourceRouting 2 }

wfBrSrInterfaceEntry OBJECT-TYPE
	SYNTAX	WfBrSrInterfaceEntry
	ACCESS	not-accessible
	STATUS	mandatory
	DESCRIPTION
		" An entry in wfBrSrInterface. "
	INDEX	{ wfBrSrInterfaceCircuit }
	::= { wfBrSrInterfaceTable 1 }

WfBrSrInterfaceEntry ::= SEQUENCE {
	wfBrSrInterfaceDelete
		INTEGER,
	wfBrSrInterfaceDisable
		INTEGER,
	wfBrSrInterfaceState
		INTEGER,
	wfBrSrInterfaceCircuit
		INTEGER,
	wfBrSrInterfaceMaxRds
		INTEGER,
	wfBrSrInterfaceRing
		INTEGER,
	wfBrSrInterfaceBlockOutSte
		INTEGER,
	wfBrSrInterfaceBlockInSte
		INTEGER,
	wfBrSrInterfaceBlockIp
		INTEGER,
	wfBrSrInterfaceIpAddress
		IpAddress,
	wfBrSrInterfaceInFrames
		Counter,
	wfBrSrInterfaceOutFrames
		Counter,
	wfBrSrInterfaceOutIpFrames
		Counter,
	wfBrSrInterfaceDropInvalidRcs
		Counter,
	wfBrSrInterfaceDropInvalidRings
		Counter,
	wfBrSrInterfaceDropSrfs
		Counter
}

wfBrSrInterfaceDelete OBJECT-TYPE
	SYNTAX	INTEGER {
		created(1),
		deleted(2)
	}
	ACCESS	read-write
	STATUS	mandatory
	DESCRIPTION
		" Create/Delete parameter. Default is created.
		  Users perform an SNMP SET operation on this
		  object in order to create/delete an interface. "
	DEFVAL	{ created }
	::= { wfBrSrInterfaceEntry 1 }

wfBrSrInterfaceDisable OBJECT-TYPE
	SYNTAX	INTEGER {
		enabled(1),
		disabled(2)
	}
	ACCESS	read-write
	STATUS	mandatory
	DESCRIPTION
		" Enable/Disable parameter. Default is enabled.
		  Users perform an SNMP SET operation on this
		  object in order to enable/disable an interface. "
	DEFVAL	{ enabled }
	::= { wfBrSrInterfaceEntry 2 }

wfBrSrInterfaceState OBJECT-TYPE
	SYNTAX	INTEGER {
		up(1),
		down(2),
		init(3),
		notpresent(4)
	}
	ACCESS	read-only
	STATUS	mandatory
	DESCRIPTION
		" The current state of the interface. "
	DEFVAL	{ down }
	::= { wfBrSrInterfaceEntry 3 }

wfBrSrInterfaceCircuit OBJECT-TYPE
	SYNTAX	INTEGER
	ACCESS	read-only
	STATUS	mandatory
	DESCRIPTION
		" The circuit that this interface runs over. "
	::= { wfBrSrInterfaceEntry 4 }

wfBrSrInterfaceMaxRds OBJECT-TYPE
	SYNTAX	INTEGER
	ACCESS	read-write
	STATUS	mandatory
	DESCRIPTION
		" The maximum number of RDs permitted in incoming
		  explorer frames "
	DEFVAL	{ 7 }
	::= { wfBrSrInterfaceEntry 5 }

wfBrSrInterfaceRing OBJECT-TYPE
	SYNTAX	INTEGER
	ACCESS	read-write
	STATUS	mandatory
	DESCRIPTION
		" The ring number of the source routing circuit.
		  Even non-ring circuit need a ring number if
		  it is to do source routing "
	::= { wfBrSrInterfaceEntry 6 }

wfBrSrInterfaceBlockOutSte OBJECT-TYPE
	SYNTAX	INTEGER {
		block(1),
		accept(2)
	}
	ACCESS	read-write
	STATUS	mandatory
	DESCRIPTION
		" Enables blocking of outbound STEs "
	DEFVAL	{ accept }
	::= { wfBrSrInterfaceEntry 7 }

wfBrSrInterfaceBlockInSte OBJECT-TYPE
	SYNTAX	INTEGER {
		block(1),
		accept(2)
	}
	ACCESS	read-write
	STATUS	mandatory
	DESCRIPTION
		" Enables blocking of inbound STEs "
	DEFVAL	{ accept }
	::= { wfBrSrInterfaceEntry 8 }

wfBrSrInterfaceBlockIp OBJECT-TYPE
	SYNTAX	INTEGER {
		block(1),
		accept(2)
	}
	ACCESS	read-write
	STATUS	mandatory
	DESCRIPTION
		" Enables blocking of inbound explorers that have
		  have already been through the IP network "
	DEFVAL	{ accept }
	::= { wfBrSrInterfaceEntry 9 }

wfBrSrInterfaceIpAddress OBJECT-TYPE
	SYNTAX	IpAddress
	ACCESS	read-write
	STATUS	mandatory
	DESCRIPTION
		" Ip address for this ring. This should match the
		  the IP address in the IP MIB "
	::= { wfBrSrInterfaceEntry 10 }

wfBrSrInterfaceInFrames OBJECT-TYPE
	SYNTAX	Counter
	ACCESS	read-only
	STATUS	mandatory
	DESCRIPTION
		" The number of frames that have been received by
		  this interface from its circuit. "
	::= { wfBrSrInterfaceEntry 11 }

wfBrSrInterfaceOutFrames OBJECT-TYPE
	SYNTAX	Counter
	ACCESS	read-only
	STATUS	mandatory
	DESCRIPTION
		" The number of frames that have been transmitted
		  by this interface "
	::= { wfBrSrInterfaceEntry 12 }

wfBrSrInterfaceOutIpFrames OBJECT-TYPE
	SYNTAX	Counter
	ACCESS	read-only
	STATUS	mandatory
	DESCRIPTION
		" The number of frames that have been transmitted
		  by this interface to the IP network "
	::= { wfBrSrInterfaceEntry 13 }

wfBrSrInterfaceDropInvalidRcs OBJECT-TYPE
	SYNTAX	Counter
	ACCESS	read-only
	STATUS	mandatory
	DESCRIPTION
		" Count of frames received which were
		  discarded because of a bad Route Control field "
	::= { wfBrSrInterfaceEntry 14 }

wfBrSrInterfaceDropInvalidRings OBJECT-TYPE
	SYNTAX	Counter
	ACCESS	read-only
	STATUS	mandatory
	DESCRIPTION
		" Count of frames received which were
		  discarded because of a invalid incoming ring "
	::= { wfBrSrInterfaceEntry 15 }

wfBrSrInterfaceDropSrfs OBJECT-TYPE
	SYNTAX	Counter
	ACCESS	read-only
	STATUS	mandatory
	DESCRIPTION
		" Count of specifically routed frames received which were
		  discarded due to filtering or no next circuit "
	::= { wfBrSrInterfaceEntry 16 }

wfBrSrBridgeTable OBJECT-TYPE
	SYNTAX	SEQUENCE OF WfBrSrBridgeEntry
	ACCESS	not-accessible
	STATUS	mandatory
	DESCRIPTION
		" A table that contains the bridge numbers used
		  by Wellfleet bridges in a source routing network
		  inst_id[2] = wfBrSrBridgeId "
	::= { wfBrSourceRouting 3 }

wfBrSrBridgeEntry OBJECT-TYPE
	SYNTAX	WfBrSrBridgeEntry
	ACCESS	not-accessible
	STATUS	mandatory
	DESCRIPTION
		" An entry in wfBrSrBridge. "
	INDEX	{ wfBrSrBridgeId }
	::= { wfBrSrBridgeTable 1 }

WfBrSrBridgeEntry ::= SEQUENCE {
	wfBrSrBridgeDelete
		INTEGER,
	wfBrSrBridgeId
		INTEGER
}

wfBrSrBridgeDelete OBJECT-TYPE
	SYNTAX	INTEGER {
		created(1),
		deleted(2)
	}
	ACCESS	read-write
	STATUS	mandatory
	DESCRIPTION
		" Create/Delete parameter. Default is created.
		  Users perform an SNMP SET operation on this object in
		  order to create/delete an IP encapsulation peer record. "
	DEFVAL	{ created }
	::= { wfBrSrBridgeEntry 1 }

wfBrSrBridgeId OBJECT-TYPE
	SYNTAX	INTEGER
	ACCESS	read-only
	STATUS	mandatory
	DESCRIPTION
		" The Bridge Id reserved for Wellfleet bridges "
	::= { wfBrSrBridgeEntry 2 }

wfBrSrIpExplorerTable OBJECT-TYPE
	SYNTAX	SEQUENCE OF WfBrSrIpExplorerEntry
	ACCESS	not-accessible
	STATUS	mandatory
	DESCRIPTION
		" A table that contains the table of IP addresses
		  to which source routing explorers should be sent
		  inst_id[2] = wfBrSrIpExplorerAddress "
	::= { wfBrSourceRouting 4 }

wfBrSrIpExplorerEntry OBJECT-TYPE
	SYNTAX	WfBrSrIpExplorerEntry
	ACCESS	not-accessible
	STATUS	mandatory
	DESCRIPTION
		" An entry in wfBrSrIpExplorer. "
	INDEX	{ wfBrSrIpExplorerAddr }
	::= { wfBrSrIpExplorerTable 1 }

WfBrSrIpExplorerEntry ::= SEQUENCE {
	wfBrSrIpExplorerDelete
		INTEGER,
	wfBrSrIpExplorerAddr
		IpAddress
}

wfBrSrIpExplorerDelete OBJECT-TYPE
	SYNTAX	INTEGER {
		created(1),
		deleted(2)
	}
	ACCESS	read-write
	STATUS	mandatory
	DESCRIPTION
		" Create/Delete parameter. Default is created.
		  Users perform an SNMP SET operation on this object in
		  order to create/delete an IP encapsulation peer record. "
	DEFVAL	{ created }
	::= { wfBrSrIpExplorerEntry 1 }

wfBrSrIpExplorerAddr OBJECT-TYPE
	SYNTAX	IpAddress
	ACCESS	read-only
	STATUS	mandatory
	DESCRIPTION
		" The IP address of this encapsulation peer. "
	::= { wfBrSrIpExplorerEntry 2 }

wfBrSrIpEncapsTable OBJECT-TYPE
	SYNTAX	SEQUENCE OF WfBrSrIpEncapsEntry
	ACCESS	not-accessible
	STATUS	mandatory
	DESCRIPTION
		" A table that contains information about IP
		  Encapsulation ring-to-IP Address mappings.
		  This information is used to make the 'next
		  ring' IP Address decision.
		  inst = wfBrSrIpEncapsRing "
	::= { wfBrSourceRouting 5 }

wfBrSrIpEncapsEntry OBJECT-TYPE
	SYNTAX	WfBrSrIpEncapsEntry
	ACCESS	not-accessible
	STATUS	mandatory
	DESCRIPTION
		" An entry in the wfBrSrIpEncapsTable. "
	INDEX	{ wfBrSrIpEncapsRing }
	::= { wfBrSrIpEncapsTable 1 }

WfBrSrIpEncapsEntry ::= SEQUENCE {
	wfBrSrIpEncapsRing
		INTEGER,
	wfBrSrIpEncapsIpAddress
		IpAddress,
	wfBrSrIpEncapsStatus
		INTEGER
}

wfBrSrIpEncapsRing OBJECT-TYPE
	SYNTAX	INTEGER
	ACCESS	read-only
	STATUS	mandatory
	DESCRIPTION
		" The remote ring number for which we have a ring to
		  IP Address mapping. "
	::= { wfBrSrIpEncapsEntry 1 }

wfBrSrIpEncapsIpAddress OBJECT-TYPE
	SYNTAX	IpAddress
	ACCESS	read-only
	STATUS	mandatory
	DESCRIPTION
		" The IP Address of the Wellfleet IP Encapsulation
		  peer to which this ring is connected. "
	::= { wfBrSrIpEncapsEntry 2 }

wfBrSrIpEncapsStatus OBJECT-TYPE
	SYNTAX	INTEGER {
		learned(3)
	}
	ACCESS	read-only
	STATUS	mandatory
	DESCRIPTION
		" The status of this entry. The meanings of the
		  values are:
		    learned(3) : the value of the corresponding
		                instance of wfBrSrIpEncapsRing was
		                learned, and is being used. "
	DEFVAL	{ learned }
	::= { wfBrSrIpEncapsEntry 3 }

wfBrSrTrafficFilterTable OBJECT-TYPE
	SYNTAX	SEQUENCE OF WfBrSrTrafficFilterEntry
	ACCESS	not-accessible
	STATUS	mandatory
	DESCRIPTION
		" SR Bridge Traffic Filters "
	::= { wfBrSourceRouting 6 }

wfBrSrTrafficFilterEntry OBJECT-TYPE
	SYNTAX	WfBrSrTrafficFilterEntry
	ACCESS	not-accessible
	STATUS	mandatory
	DESCRIPTION
		" An entry in WfBrSrTrafficFilterTable. "
	INDEX	{ wfBrSrTrafficFilterCircuit,
		wfBrSrTrafficFilterRuleNumber,
		wfBrSrTrafficFilterFragment }
	::= { wfBrSrTrafficFilterTable 1 }

WfBrSrTrafficFilterEntry ::= SEQUENCE {
	wfBrSrTrafficFilterCreate
		INTEGER,
	wfBrSrTrafficFilterEnable
		INTEGER,
	wfBrSrTrafficFilterStatus
		INTEGER,
	wfBrSrTrafficFilterCounter
		Counter,
	wfBrSrTrafficFilterDefinition
		OCTET STRING,
	wfBrSrTrafficFilterReserved
		INTEGER,
	wfBrSrTrafficFilterCircuit
		INTEGER,
	wfBrSrTrafficFilterRuleNumber
		INTEGER,
	wfBrSrTrafficFilterFragment
		INTEGER
}

wfBrSrTrafficFilterCreate OBJECT-TYPE
	SYNTAX	INTEGER {
		created(1),
		deleted(2)
	}
	ACCESS	read-write
	STATUS	mandatory
	DESCRIPTION
		" Defines the existence of the traffic filter rule:
		                created - traffic filter exists
		                delete - traffic filter does not exist and can be deleted. "
	DEFVAL	{ created }
	::= { wfBrSrTrafficFilterEntry 1 }

wfBrSrTrafficFilterEnable OBJECT-TYPE
	SYNTAX	INTEGER {
		enabled(1),
		disabled(2)
	}
	ACCESS	read-write
	STATUS	mandatory
	DESCRIPTION
		" Defines whether or not the traffic filter rule should be used:
		                enabled - activate the rule.
		                disabled - inactivate the rule. "
	DEFVAL	{ enabled }
	::= { wfBrSrTrafficFilterEntry 2 }

wfBrSrTrafficFilterStatus OBJECT-TYPE
	SYNTAX	INTEGER {
		active(1),
		error(2),
		inactive(3)
	}
	ACCESS	read-only
	STATUS	mandatory
	DESCRIPTION
		" Defines the current status of the traffic filter:
		                inactive - the rule is not in use.
		                active - the rule is being used.
		                error - the application detected an error in the rule. "
	DEFVAL	{ inactive }
	::= { wfBrSrTrafficFilterEntry 3 }

wfBrSrTrafficFilterCounter OBJECT-TYPE
	SYNTAX	Counter
	ACCESS	read-only
	STATUS	mandatory
	DESCRIPTION
		" The number of received packets that have
		           matched this rule. "
	::= { wfBrSrTrafficFilterEntry 4 }

wfBrSrTrafficFilterDefinition OBJECT-TYPE
	SYNTAX	OCTET STRING
	ACCESS	read-write
	STATUS	mandatory
	DESCRIPTION
		" The filter rule definition. "
	::= { wfBrSrTrafficFilterEntry 5 }

wfBrSrTrafficFilterReserved OBJECT-TYPE
	SYNTAX	INTEGER
	ACCESS	not-accessible
	STATUS	mandatory
	DESCRIPTION
		" Reserved field. "
	::= { wfBrSrTrafficFilterEntry 6 }

wfBrSrTrafficFilterCircuit OBJECT-TYPE
	SYNTAX	INTEGER
	ACCESS	read-only
	STATUS	mandatory
	DESCRIPTION
		" The ID of the Bridge Circuit to which the
		           filter is applied. "
	::= { wfBrSrTrafficFilterEntry 7 }

wfBrSrTrafficFilterRuleNumber OBJECT-TYPE
	SYNTAX	INTEGER
	ACCESS	read-only
	STATUS	mandatory
	DESCRIPTION
		" ID for the rule. "
	::= { wfBrSrTrafficFilterEntry 8 }

wfBrSrTrafficFilterFragment OBJECT-TYPE
	SYNTAX	INTEGER
	ACCESS	read-only
	STATUS	mandatory
	DESCRIPTION
		" Fragment number - for large rules. "
	::= { wfBrSrTrafficFilterEntry 9 }

wfBrSrEsRifTable OBJECT-TYPE
	SYNTAX	SEQUENCE OF WfBrSrEsRifEntry
	ACCESS	not-accessible
	STATUS	mandatory
	DESCRIPTION
		" A table that contains the currently active
		  RIFs in use by Router End Station Support
		  inst_id[9] = wfBrSrIpExplorerAddress "
	::= { wfBrSourceRouting 7 }

wfBrSrEsRifEntry OBJECT-TYPE
	SYNTAX	WfBrSrEsRifEntry
	ACCESS	not-accessible
	STATUS	mandatory
	DESCRIPTION
		" An entry in wfBrSrEsRif. "
	INDEX	{ wfBrSrEsRifCircuit,
		wfBrSrEsRifProtocol,
		wfBrSrEsRifMacAddr }
	::= { wfBrSrEsRifTable 1 }

WfBrSrEsRifEntry ::= SEQUENCE {
	wfBrSrEsRifCircuit
		INTEGER,
	wfBrSrEsRifProtocol
		OCTET STRING,
	wfBrSrEsRifMacAddr
		OCTET STRING,
	wfBrSrEsRifRoute
		OCTET STRING
}

wfBrSrEsRifCircuit OBJECT-TYPE
	SYNTAX	INTEGER
	ACCESS	read-only
	STATUS	mandatory
	DESCRIPTION
		" The circuit on which this entry was learned "
	::= { wfBrSrEsRifEntry 1 }

wfBrSrEsRifProtocol OBJECT-TYPE
	SYNTAX	OCTET STRING
	ACCESS	read-only
	STATUS	mandatory
	DESCRIPTION
		" protocol type. "
	::= { wfBrSrEsRifEntry 2 }

wfBrSrEsRifMacAddr OBJECT-TYPE
	SYNTAX	OCTET STRING
	ACCESS	read-only
	STATUS	mandatory
	DESCRIPTION
		" to this RIF. "
	::= { wfBrSrEsRifEntry 3 }

wfBrSrEsRifRoute OBJECT-TYPE
	SYNTAX	OCTET STRING
	ACCESS	read-only
	STATUS	mandatory
	DESCRIPTION
		" The route contained in the RIF field "
	::= { wfBrSrEsRifEntry 4 }

wfSyncTable OBJECT-TYPE
	SYNTAX	SEQUENCE OF WfSyncEntry
	ACCESS	not-accessible
	STATUS	mandatory
	DESCRIPTION
		"
		    SYNC  line record
		 "
	::= { wfLine 5 }

wfSyncEntry OBJECT-TYPE
	SYNTAX	WfSyncEntry
	ACCESS	not-accessible
	STATUS	mandatory
	DESCRIPTION
		" An entry in the SYNC table "
	INDEX	{ wfSyncSlot,
		wfSyncConnector }
	::= { wfSyncTable 1 }

WfSyncEntry ::= SEQUENCE {
	wfSyncDelete
		INTEGER,
	wfSyncDisable
		INTEGER,
	wfSyncState
		INTEGER,
	wfSyncSlot
		INTEGER,
	wfSyncConnector
		INTEGER,
	wfSyncCct
		INTEGER,
	wfSyncBofl
		INTEGER,
	wfSyncBoflTmo
		INTEGER,
	wfSyncMtu
		INTEGER,
	wfSyncMadr
		OCTET STRING,
	wfSyncPromiscuous
		INTEGER,
	wfSyncXid
		INTEGER,
	wfSyncClkSource
		INTEGER,
	wfSyncClkSpeed
		INTEGER,
	wfSyncSignalMode
		INTEGER,
	wfSyncRtsEnable
		INTEGER,
	wfSyncBurstCount
		INTEGER,
	wfSyncService
		INTEGER,
	wfSyncRetryCount
		INTEGER,
	wfSyncLinkIdleTimer
		INTEGER,
	wfSyncRetryTimer
		INTEGER,
	wfSyncExtendedAddress
		INTEGER,
	wfSyncExtendedAddressForce
		INTEGER,
	wfSyncExtendedControl
		INTEGER,
	wfSyncExtendedControlForce
		INTEGER,
	wfSyncConnectAttempts
		INTEGER,
	wfSyncWindowSizeTx
		INTEGER,
	wfSyncWindowSizeTxExtc
		INTEGER,
	wfSyncMinFrameSpace
		INTEGER,
	wfSyncLocalAddress
		INTEGER,
	wfSyncRemoteAddress
		INTEGER,
	wfSyncPassThruLocalMadr
		OCTET STRING,
	wfSyncPassThruRemoteMadr
		OCTET STRING,
	wfSyncWanProtocol
		INTEGER,
	wfSyncCrcSize
		INTEGER,
	wfSyncRxOctets
		Counter,
	wfSyncRxFrames
		Counter,
	wfSyncTxOctets
		Counter,
	wfSyncTxFrames
		Counter,
	wfSyncRxErrors
		Counter,
	wfSyncTxErrors
		Counter,
	wfSyncLackRescRx
		Counter,
	wfSyncLackRescTx
		Counter,
	wfSyncUnderFlowTx
		Counter,
	wfSyncRejectsTx
		Counter,
	wfSyncRejectsRx
		Counter,
	wfSyncOverFlowRx
		Counter,
	wfSyncFramesIncompRx
		Counter,
	wfSyncBadFramesRx
		Counter,
	wfSyncFrameRejectsRx
		Counter,
	wfSyncRuntsRx
		Counter,
	wfSyncT1Timeouts
		Counter,
	wfSyncMemoryErrors
		Counter,
	wfSyncMediaType
		INTEGER
}

wfSyncDelete OBJECT-TYPE
	SYNTAX	INTEGER {
		created(1),
		deleted(2)
	}
	ACCESS	read-write
	STATUS	mandatory
	DESCRIPTION
		" Create/Delete parameter "
	DEFVAL	{ created }
	::= { wfSyncEntry 1 }

wfSyncDisable OBJECT-TYPE
	SYNTAX	INTEGER {
		enabled(1),
		disabled(2)
	}
	ACCESS	read-write
	STATUS	mandatory
	DESCRIPTION
		" Enable/Disable parameter "
	DEFVAL	{ enabled }
	::= { wfSyncEntry 2 }

wfSyncState OBJECT-TYPE
	SYNTAX	INTEGER {
		up(1),
		down(2),
		init(3),
		wait(4),
		notpresent(5)
	}
	ACCESS	read-only
	STATUS	mandatory
	DESCRIPTION
		" Line Driver state variable, Not Present, Init, Down, Up "
	DEFVAL	{ notpresent }
	::= { wfSyncEntry 3 }

wfSyncSlot OBJECT-TYPE
	SYNTAX	INTEGER {
		minimum(1),
		maximum(14)
	}
	ACCESS	read-only
	STATUS	mandatory
	DESCRIPTION
		" Instance ID Slot, filled in by driver "
	::= { wfSyncEntry 4 }

wfSyncConnector OBJECT-TYPE
	SYNTAX	INTEGER {
		one(1),
		two(2),
		three(3),
		four(4)
	}
	ACCESS	read-only
	STATUS	mandatory
	DESCRIPTION
		" Instance ID Connector, filled in by driver "
	::= { wfSyncEntry 5 }

wfSyncCct OBJECT-TYPE
	SYNTAX	INTEGER {
		minimum(1),
		maximum(1023)
	}
	ACCESS	read-write
	STATUS	mandatory
	DESCRIPTION
		" CCT number for this line instance "
	::= { wfSyncEntry 6 }

wfSyncBofl OBJECT-TYPE
	SYNTAX	INTEGER {
		enabled(1),
		disabled(2)
	}
	ACCESS	read-write
	STATUS	mandatory
	DESCRIPTION
		" breath of life parameter "
	DEFVAL	{ enabled }
	::= { wfSyncEntry 7 }

wfSyncBoflTmo OBJECT-TYPE
	SYNTAX	INTEGER {
		minimum(1),
		maximum(60),
		default(5)
	}
	ACCESS	read-write
	STATUS	mandatory
	DESCRIPTION
		" breath of life timeout in seconds "
	DEFVAL	{ default }
	::= { wfSyncEntry 8 }

wfSyncMtu OBJECT-TYPE
	SYNTAX	INTEGER {
		minimum(3),
		maximum(4500),
		default(1600)
	}
	ACCESS	read-write
	STATUS	mandatory
	DESCRIPTION
		" MTU parameter, this is buffer size for SYNC media, fixed "
	DEFVAL	{ default }
	::= { wfSyncEntry 9 }

wfSyncMadr OBJECT-TYPE
	SYNTAX	OCTET STRING
	ACCESS	read-only
	STATUS	mandatory
	DESCRIPTION
		" Line MAC address, fixed - line driver fills in from the 48 bit
		   address stored in the serial number prom for this connector.   "
	::= { wfSyncEntry 10 }

wfSyncPromiscuous OBJECT-TYPE
	SYNTAX	INTEGER {
		enabled(1),
		disabled(2)
	}
	ACCESS	read-write
	STATUS	mandatory
	DESCRIPTION
		" The promiscuous parameter allows address filtering based on the local
		   and remote addresses.  When enabled, all frames are received, disabled
		   indicates only frames destined for this local address are received "
	DEFVAL	{ disabled }
	::= { wfSyncEntry 11 }

wfSyncXid OBJECT-TYPE
	SYNTAX	INTEGER {
		enabled(1),
		disabled(2)
	}
	ACCESS	read-write
	STATUS	mandatory
	DESCRIPTION
		" XID enable/disable parameter. This parameter is used to enable
		   or disable transmission/reception of Test XID frames. "
	DEFVAL	{ disabled }
	::= { wfSyncEntry 12 }

wfSyncClkSource OBJECT-TYPE
	SYNTAX	INTEGER {
		internal(1),
		external(2)
	}
	ACCESS	read-write
	STATUS	mandatory
	DESCRIPTION
		" Tx/Rx clock source is either internally or external generated. "
	DEFVAL	{ external }
	::= { wfSyncEntry 13 }

wfSyncClkSpeed OBJECT-TYPE
	SYNTAX	INTEGER {
		clk1200b(1200),
		clk2400b(2401),
		clk4800b(4807),
		clk7200b(7204),
		clk9600b(9615),
		clk19200b(19230),
		clk32000b(32051),
		clk38400b(38461),
		clk56k(56818),
		clk64k(64102),
		clk125k(125000),
		clk230k(227272),
		clk420k(416666),
		clk625k(625000),
		clk833k(833333),
		clk1mb(1250000),
		clk2mb(2500000),
		clk5mb(5000000)
	}
	ACCESS	read-write
	STATUS	mandatory
	DESCRIPTION
		" Tx/Rx clock speed. This speed selection is valid only when the
		   internal clock speed parameter has been selected. "
	DEFVAL	{ clk64k }
	::= { wfSyncEntry 14 }

wfSyncSignalMode OBJECT-TYPE
	SYNTAX	INTEGER {
		balanced(1),
		unbalanced(2)
	}
	ACCESS	read-write
	STATUS	mandatory
	DESCRIPTION
		" The signal mode parameter indicates the line paramter balanced or
		   unbalanced. "
	DEFVAL	{ balanced }
	::= { wfSyncEntry 15 }

wfSyncRtsEnable OBJECT-TYPE
	SYNTAX	INTEGER {
		enabled(1),
		disabled(2)
	}
	ACCESS	read-write
	STATUS	mandatory
	DESCRIPTION
		" The RTS parameter enables/disables detection of RTS signals on the
		   interface.  Normal default mode is running without RTS enabled. "
	DEFVAL	{ disabled }
	::= { wfSyncEntry 16 }

wfSyncBurstCount OBJECT-TYPE
	SYNTAX	INTEGER {
		enabled(1),
		disabled(2)
	}
	ACCESS	read-write
	STATUS	mandatory
	DESCRIPTION
		" Allows single or multiple DMA burst cycles. When enabled the chip
		   performs 8 word burst's. Single word cycles are performed when disabled"
	DEFVAL	{ disabled }
	::= { wfSyncEntry 17 }

wfSyncService OBJECT-TYPE
	SYNTAX	INTEGER {
		transparent(1),
		llc1(2),
		llc2(3)
	}
	ACCESS	read-write
	STATUS	mandatory
	DESCRIPTION
		" Service type for this circuit. Transparent is raw HDLC mode, LLC1 will
		   prefix the HDLC address and control fields to the frame.  The LLC2 service
		   provides the LAPB protocol service. "
	DEFVAL	{ llc1 }
	::= { wfSyncEntry 18 }

wfSyncRetryCount OBJECT-TYPE
	SYNTAX	INTEGER {
		minimum(1),
		maximum(64),
		default(16)
	}
	ACCESS	read-write
	STATUS	mandatory
	DESCRIPTION
		" The Retry count parameter indicates the number of retransmission
		   attempts which will be tried per frame before a line is determined
		   to be down.  The retry count is max attempts following expiration of
		   the T1 timer.  This parameter is equal to the N2 counter in ICB. "
	DEFVAL	{ default }
	::= { wfSyncEntry 19 }

wfSyncLinkIdleTimer OBJECT-TYPE
	SYNTAX	INTEGER {
		minimum(1),
		maximum(9999),
		default(3)
	}
	ACCESS	read-write
	STATUS	mandatory
	DESCRIPTION
		" The link idle parameter is the number of seconds before a line has
		   been determined to be idle.  An idle line is considered disconnectd
		   This value is expressed in seconds. "
	DEFVAL	{ default }
	::= { wfSyncEntry 20 }

wfSyncRetryTimer OBJECT-TYPE
	SYNTAX	INTEGER {
		minimum(1),
		maximum(9999),
		default(3)
	}
	ACCESS	read-write
	STATUS	mandatory
	DESCRIPTION
		" The Retry Timer parameter indicates the timeout in seconds for a
		   response to be heard form the link.  Link control frames are sent at
		   the expiration of this timer value.  The frames will be resent up to
		   retry count (N2) at which time the link will be disconnected. "
	DEFVAL	{ default }
	::= { wfSyncEntry 21 }

wfSyncExtendedAddress OBJECT-TYPE
	SYNTAX	INTEGER {
		enabled(1),
		disabled(2)
	}
	ACCESS	read-write
	STATUS	mandatory
	DESCRIPTION
		" This parameter controls length determination of the address field.
		   When this parameter is enabled, the first bit of the address field
		   be tested to determine the length of address field in octets. "
	DEFVAL	{ disabled }
	::= { wfSyncEntry 22 }

wfSyncExtendedAddressForce OBJECT-TYPE
	SYNTAX	INTEGER {
		enabled(1),
		disabled(2)
	}
	ACCESS	read-write
	STATUS	mandatory
	DESCRIPTION
		" When this parameter is enabled, the receiver will assume that all
		   address fields are 2 octets in length regardless of the first two
		   bits of the control field.  Usefull only in Transparent Mode. "
	DEFVAL	{ disabled }
	::= { wfSyncEntry 23 }

wfSyncExtendedControl OBJECT-TYPE
	SYNTAX	INTEGER {
		enabled(1),
		disabled(2)
	}
	ACCESS	read-write
	STATUS	mandatory
	DESCRIPTION
		" This parameter allows the control fields of all S and I frames to
		   become 2 octets in length instead of one.  Numbering of all I frame
		   become modulo 128 instead of modulo 8.  The control field of U 
		   frames remains one octet in length. "
	DEFVAL	{ disabled }
	::= { wfSyncEntry 24 }

wfSyncExtendedControlForce OBJECT-TYPE
	SYNTAX	INTEGER {
		enabled(1),
		disabled(2)
	}
	ACCESS	read-write
	STATUS	mandatory
	DESCRIPTION
		" This parameter when enabled will force all control fields to become
		   two octets in length regardless the first two bits in the control 
		   field.  Usefull only in Transparent Mode. (LLC1) "
	DEFVAL	{ disabled }
	::= { wfSyncEntry 25 }

wfSyncConnectAttempts OBJECT-TYPE
	SYNTAX	INTEGER {
		minimum(1),
		maximum(9999),
		default(10)
	}
	ACCESS	read-write
	STATUS	mandatory
	DESCRIPTION
		" This parameter controls the number of connection attempts which
		   will be made during a LAPB connection request.  This parameter 
		   is applicable only during LLC2 service.  "
	DEFVAL	{ default }
	::= { wfSyncEntry 26 }

wfSyncWindowSizeTx OBJECT-TYPE
	SYNTAX	INTEGER {
		minimum(1),
		maximum(7),
		default(1)
	}
	ACCESS	read-write
	STATUS	mandatory
	DESCRIPTION
		" The window size parameter controls the number of I frames which
		   may be transmitted without acknowledgement. Non EXTC mode. "
	DEFVAL	{ default }
	::= { wfSyncEntry 27 }

wfSyncWindowSizeTxExtc OBJECT-TYPE
	SYNTAX	INTEGER {
		minimum(1),
		maximum(7),
		default(1)
	}
	ACCESS	read-write
	STATUS	mandatory
	DESCRIPTION
		" The window size parameter controls the number of I frames which
		   may be transmitted without acknowledgement in EXTC mode. "
	DEFVAL	{ default }
	::= { wfSyncEntry 28 }

wfSyncMinFrameSpace OBJECT-TYPE
	SYNTAX	INTEGER {
		minimum(1),
		maximum(32),
		default(1)
	}
	ACCESS	read-write
	STATUS	mandatory
	DESCRIPTION
		" The minimum frame spacing parameter defines the number of flags
		   that are transmitted between adjacent frames. "
	DEFVAL	{ default }
	::= { wfSyncEntry 29 }

wfSyncLocalAddress OBJECT-TYPE
	SYNTAX	INTEGER {
		addressdte(1),
		addressdce(3),
		addressexplicit(7)
	}
	ACCESS	read-write
	STATUS	mandatory
	DESCRIPTION
		" The local address parameter contains the DTE,DCE or EXPLICIT
		   value expressed as a single octet.  It may be extended to 2
		   octets if EXTA has been set. "
	DEFVAL	{ addressexplicit }
	::= { wfSyncEntry 30 }

wfSyncRemoteAddress OBJECT-TYPE
	SYNTAX	INTEGER {
		addressdte(1),
		addressdce(3),
		addressexplicit(7)
	}
	ACCESS	read-write
	STATUS	mandatory
	DESCRIPTION
		" The remote address parameter contains the DTE,DCE or EXPLICIT
		   value expressed as a single octet.  It may be extended to 2 
		   octets if EXTA has been set. "
	DEFVAL	{ addressexplicit }
	::= { wfSyncEntry 31 }

wfSyncPassThruLocalMadr OBJECT-TYPE
	SYNTAX	OCTET STRING
	ACCESS	read-write
	STATUS	mandatory
	DESCRIPTION
		" 48 bit MAC address of Local end of Sync Passthru circuit "
	::= { wfSyncEntry 32 }

wfSyncPassThruRemoteMadr OBJECT-TYPE
	SYNTAX	OCTET STRING
	ACCESS	read-write
	STATUS	mandatory
	DESCRIPTION
		" 48 bit MAC address of Remote end of Sync Passthru circuit "
	::= { wfSyncEntry 33 }

wfSyncWanProtocol OBJECT-TYPE
	SYNTAX	INTEGER {
		standard(1),
		passthru(2),
		ppp(3),
		smds(4),
		framerelay(5)
	}
	ACCESS	read-write
	STATUS	mandatory
	DESCRIPTION
		" WAN protocol selection is provided via this parameter. The
		   supported protocols can be selected per interface. "
	DEFVAL	{ standard }
	::= { wfSyncEntry 34 }

wfSyncCrcSize OBJECT-TYPE
	SYNTAX	INTEGER {
		crc16bit(1),
		crc32bit(2)
	}
	ACCESS	read-write
	STATUS	mandatory
	DESCRIPTION
		" CRC size parameter, 16 bit standard CCITT or extended 32 bit CRC "
	DEFVAL	{ crc16bit }
	::= { wfSyncEntry 35 }

wfSyncRxOctets OBJECT-TYPE
	SYNTAX	Counter
	ACCESS	read-only
	STATUS	mandatory
	DESCRIPTION
		" Number of octets received without error "
	::= { wfSyncEntry 36 }

wfSyncRxFrames OBJECT-TYPE
	SYNTAX	Counter
	ACCESS	read-only
	STATUS	mandatory
	DESCRIPTION
		" Number of frames received without error "
	::= { wfSyncEntry 37 }

wfSyncTxOctets OBJECT-TYPE
	SYNTAX	Counter
	ACCESS	read-only
	STATUS	mandatory
	DESCRIPTION
		" Number of octets transmitted without error "
	::= { wfSyncEntry 38 }

wfSyncTxFrames OBJECT-TYPE
	SYNTAX	Counter
	ACCESS	read-only
	STATUS	mandatory
	DESCRIPTION
		" Number of frames transmitted without error "
	::= { wfSyncEntry 39 }

wfSyncRxErrors OBJECT-TYPE
	SYNTAX	Counter
	ACCESS	read-only
	STATUS	mandatory
	DESCRIPTION
		" Number of receive errors "
	::= { wfSyncEntry 40 }

wfSyncTxErrors OBJECT-TYPE
	SYNTAX	Counter
	ACCESS	read-only
	STATUS	mandatory
	DESCRIPTION
		" Number of transmission errors "
	::= { wfSyncEntry 41 }

wfSyncLackRescRx OBJECT-TYPE
	SYNTAX	Counter
	ACCESS	read-only
	STATUS	mandatory
	DESCRIPTION
		" Number of Rx frames dropped due to lack of buffer resources "
	::= { wfSyncEntry 42 }

wfSyncLackRescTx OBJECT-TYPE
	SYNTAX	Counter
	ACCESS	read-only
	STATUS	mandatory
	DESCRIPTION
		" Number of Tx frames dropped due to lack of buffer resources "
	::= { wfSyncEntry 43 }

wfSyncUnderFlowTx OBJECT-TYPE
	SYNTAX	Counter
	ACCESS	read-only
	STATUS	mandatory
	DESCRIPTION
		" Number of transmission underflows, device FIFO went empty before
		   next DMA request was granted.  "
	::= { wfSyncEntry 44 }

wfSyncRejectsTx OBJECT-TYPE
	SYNTAX	Counter
	ACCESS	read-only
	STATUS	mandatory
	DESCRIPTION
		" Number of reject frames which were transmitted "
	::= { wfSyncEntry 45 }

wfSyncRejectsRx OBJECT-TYPE
	SYNTAX	Counter
	ACCESS	read-only
	STATUS	mandatory
	DESCRIPTION
		" Number of reject frames which were received "
	::= { wfSyncEntry 46 }

wfSyncOverFlowRx OBJECT-TYPE
	SYNTAX	Counter
	ACCESS	read-only
	STATUS	mandatory
	DESCRIPTION
		" Number of receive overflows, device FIFO overflowed before next
		   DMA cycle granted.  No buffer resources available. "
	::= { wfSyncEntry 47 }

wfSyncFramesIncompRx OBJECT-TYPE
	SYNTAX	Counter
	ACCESS	read-only
	STATUS	mandatory
	DESCRIPTION
		" Number of frames which were incompletely received. These are frames
		   which may have resulted from FRMRR errors. "
	::= { wfSyncEntry 48 }

wfSyncBadFramesRx OBJECT-TYPE
	SYNTAX	Counter
	ACCESS	read-only
	STATUS	mandatory
	DESCRIPTION
		" Number of bad receive frames, caused by FCS errors or non octet aligned. "
	::= { wfSyncEntry 49 }

wfSyncFrameRejectsRx OBJECT-TYPE
	SYNTAX	Counter
	ACCESS	read-only
	STATUS	mandatory
	DESCRIPTION
		" Number of Frame Rejects received "
	::= { wfSyncEntry 50 }

wfSyncRuntsRx OBJECT-TYPE
	SYNTAX	Counter
	ACCESS	read-only
	STATUS	mandatory
	DESCRIPTION
		" Number of runt frames received "
	::= { wfSyncEntry 51 }

wfSyncT1Timeouts OBJECT-TYPE
	SYNTAX	Counter
	ACCESS	read-only
	STATUS	mandatory
	DESCRIPTION
		" Number of T1 timeout's detected. The T1 timer is the link
		   retransmission timer.  Link control frames will be retransmitted
		   when T1 expires.  This is a count of the number of timeouts. "
	::= { wfSyncEntry 52 }

wfSyncMemoryErrors OBJECT-TYPE
	SYNTAX	Counter
	ACCESS	read-only
	STATUS	mandatory
	DESCRIPTION
		" Number of memory access errors detected. A MERR is the expiration of
		   a DMA cycle without the bus being granted within 26us. "
	::= { wfSyncEntry 53 }

wfSyncMediaType OBJECT-TYPE
	SYNTAX	INTEGER {
		default(1),
		t1(2),
		e1(3)
	}
	ACCESS	read-write
	STATUS	mandatory
	DESCRIPTION
		" Media type selection is provided via this parameter "
	DEFVAL	{ default }
	::= { wfSyncEntry 54 }

wfSys		OBJECT IDENTIFIER ::= { wfSystem 1 }

wfSysDescr OBJECT-TYPE
	SYNTAX	DisplayString
	ACCESS	read-only
	STATUS	mandatory
	DESCRIPTION
		" A textual description of the entity including full name and version of
		   the system's hardware type, OS, and networking SW 
		"
	::= { wfSys 1 }

wfSysObjectID OBJECT-TYPE
	SYNTAX	OBJECT IDENTIFIER
	ACCESS	read-only
	STATUS	mandatory
	DESCRIPTION
		" Provides an unambiguous means for determining the MIB type (old product vs.
		   harpoon MIB).
		"
	::= { wfSys 2 }

wfSysUpTime OBJECT-TYPE
	SYNTAX	TimeTicks
	ACCESS	read-only
	STATUS	mandatory
	DESCRIPTION
		" Time in seconds/100 since the last cold start "
	::= { wfSys 3 }

wfSysContact OBJECT-TYPE
	SYNTAX	DisplayString
	ACCESS	read-write
	STATUS	mandatory
	DESCRIPTION
		" Contact person for this node and where/how to contact them "
	::= { wfSys 4 }

wfSysName OBJECT-TYPE
	SYNTAX	DisplayString
	ACCESS	read-write
	STATUS	mandatory
	DESCRIPTION
		" Node's fully qualified domain name or administratively assigned name "
	::= { wfSys 5 }

wfSysLocation OBJECT-TYPE
	SYNTAX	DisplayString
	ACCESS	read-write
	STATUS	mandatory
	DESCRIPTION
		" Physical Location of this Node "
	::= { wfSys 6 }

wfSysServices OBJECT-TYPE
	SYNTAX	INTEGER
	ACCESS	read-only
	STATUS	mandatory
	DESCRIPTION
		" A sum of numbers indicating the set of services the entity offers. For each
		  layer L, add 2**(L - 1). Example: 78 = Layers 2,3,4, and 7.
		 "
	DEFVAL	{ 78 }
	::= { wfSys 7 }

wfSysGmtOffset OBJECT-TYPE
	SYNTAX	INTEGER
	ACCESS	read-only
	STATUS	mandatory
	DESCRIPTION
		" The positive or negative offset from Greenwich Mean Time (GMT). This
		   effectively describes the time zone. "
	::= { wfSys 8 }

wfSysMibVersion OBJECT-TYPE
	SYNTAX	DisplayString
	ACCESS	read-only
	STATUS	mandatory
	DESCRIPTION
		" The version of the private management information base currently being
		  used by the system software. Format is: xV.RR "
	::= { wfSys 9 }

wfT1Table OBJECT-TYPE
	SYNTAX	SEQUENCE OF WfT1Entry
	ACCESS	not-accessible
	STATUS	mandatory
	DESCRIPTION
		"
		   T1 line record
		 "
	::= { wfLine 10 }

wfT1Entry OBJECT-TYPE
	SYNTAX	WfT1Entry
	ACCESS	not-accessible
	STATUS	mandatory
	DESCRIPTION
		" An entry in the T1 table "
	INDEX	{ wfT1Slot,
		wfT1Connector }
	::= { wfT1Table 1 }

WfT1Entry ::= SEQUENCE {
	wfT1Delete
		INTEGER,
	wfT1Disable
		INTEGER,
	wfT1State
		INTEGER,
	wfT1Slot
		INTEGER,
	wfT1Connector
		INTEGER,
	wfT1Madr
		OCTET STRING,
	wfT1FrameType
		INTEGER,
	wfT1LineBuildout
		INTEGER,
	wfT1B8ZSSupport
		INTEGER,
	wfT1ClockMode
		INTEGER,
	wfT1MiniDacs
		DisplayString,
	wfT1BipolarVios
		Counter,
	wfT1FrameBitErrs
		Counter,
	wfT1OutOfFrameErrs
		Counter,
	wfT1SuperFrameErrs
		Counter,
	wfT1RcvYelAlarms
		Counter,
	wfT1RcvCarrierLoss
		Counter,
	wfT1RcvRedAlarms
		Counter
}

wfT1Delete OBJECT-TYPE
	SYNTAX	INTEGER {
		created(1),
		deleted(2)
	}
	ACCESS	read-write
	STATUS	mandatory
	DESCRIPTION
		" create/delete parameter, dflt = created "
	DEFVAL	{ created }
	::= { wfT1Entry 1 }

wfT1Disable OBJECT-TYPE
	SYNTAX	INTEGER {
		enabled(1),
		disabled(2)
	}
	ACCESS	read-write
	STATUS	mandatory
	DESCRIPTION
		" enable/disable parameter, dflt = enabled "
	DEFVAL	{ enabled }
	::= { wfT1Entry 2 }

wfT1State OBJECT-TYPE
	SYNTAX	INTEGER {
		up(1),
		init(3),
		notpresent(4)
	}
	ACCESS	read-only
	STATUS	mandatory
	DESCRIPTION
		" line driver state variable, Not Present, Init, Up "
	DEFVAL	{ notpresent }
	::= { wfT1Entry 3 }

wfT1Slot OBJECT-TYPE
	SYNTAX	INTEGER {
		minimum(1),
		maximum(14)
	}
	ACCESS	read-only
	STATUS	mandatory
	DESCRIPTION
		" instance ID Slot, filled in by driver "
	::= { wfT1Entry 4 }

wfT1Connector OBJECT-TYPE
	SYNTAX	INTEGER {
		one(1),
		two(2)
	}
	ACCESS	read-only
	STATUS	mandatory
	DESCRIPTION
		" instance ID Connector, filled in by driver "
	::= { wfT1Entry 5 }

wfT1Madr OBJECT-TYPE
	SYNTAX	OCTET STRING
	ACCESS	read-only
	STATUS	mandatory
	DESCRIPTION
		" Line mac address, filled in by driver "
	::= { wfT1Entry 6 }

wfT1FrameType OBJECT-TYPE
	SYNTAX	INTEGER {
		d4(1),
		esf(2)
	}
	ACCESS	read-write
	STATUS	mandatory
	DESCRIPTION
		" Frame Type - differentiates between two tarrifed framing formats
		   D4 and ESF.                                                    "
	DEFVAL	{ esf }
	::= { wfT1Entry 7 }

wfT1LineBuildout OBJECT-TYPE
	SYNTAX	INTEGER {
		minimum(1),
		maximum(655),
		default(1)
	}
	ACCESS	read-write
	STATUS	mandatory
	DESCRIPTION
		" Line Buildout - Approximate length of cable "
	DEFVAL	{ default }
	::= { wfT1Entry 8 }

wfT1B8ZSSupport OBJECT-TYPE
	SYNTAX	INTEGER {
		enabled(1),
		disabled(2)
	}
	ACCESS	read-write
	STATUS	mandatory
	DESCRIPTION
		" B8ZS Support - Enables or disables Binary 8 zeros suppression "
	DEFVAL	{ disabled }
	::= { wfT1Entry 9 }

wfT1ClockMode OBJECT-TYPE
	SYNTAX	INTEGER {
		internal(1),
		slave(2),
		manual(4),
		default(1)
	}
	ACCESS	read-write
	STATUS	mandatory
	DESCRIPTION
		" Clock Mode - Specifies the source of the T1 transmit clock "
	DEFVAL	{ default }
	::= { wfT1Entry 10 }

wfT1MiniDacs OBJECT-TYPE
	SYNTAX	DisplayString
	ACCESS	read-write
	STATUS	mandatory
	DESCRIPTION
		" MiniDacs Configuration - assigns each T1 channel to a specific
		   function                                                       "
	::= { wfT1Entry 11 }

wfT1BipolarVios OBJECT-TYPE
	SYNTAX	Counter
	ACCESS	read-only
	STATUS	mandatory
	DESCRIPTION
		" Number of Bipolar Violations "
	::= { wfT1Entry 12 }

wfT1FrameBitErrs OBJECT-TYPE
	SYNTAX	Counter
	ACCESS	read-only
	STATUS	mandatory
	DESCRIPTION
		" Number of frame bit errors "
	::= { wfT1Entry 13 }

wfT1OutOfFrameErrs OBJECT-TYPE
	SYNTAX	Counter
	ACCESS	read-only
	STATUS	mandatory
	DESCRIPTION
		" Number of Out of Frame errors "
	::= { wfT1Entry 14 }

wfT1SuperFrameErrs OBJECT-TYPE
	SYNTAX	Counter
	ACCESS	read-only
	STATUS	mandatory
	DESCRIPTION
		" Number of  Superframe errors "
	::= { wfT1Entry 15 }

wfT1RcvYelAlarms OBJECT-TYPE
	SYNTAX	Counter
	ACCESS	read-only
	STATUS	mandatory
	DESCRIPTION
		" Number of Yellow Alarms Received "
	::= { wfT1Entry 16 }

wfT1RcvCarrierLoss OBJECT-TYPE
	SYNTAX	Counter
	ACCESS	read-only
	STATUS	mandatory
	DESCRIPTION
		" Number of instances of carrier loss "
	::= { wfT1Entry 17 }

wfT1RcvRedAlarms OBJECT-TYPE
	SYNTAX	Counter
	ACCESS	read-only
	STATUS	mandatory
	DESCRIPTION
		" Number of Red Alarm Received "
	::= { wfT1Entry 18 }

wfTftp		OBJECT IDENTIFIER ::= { wfInternet 6 }

wfTftpDisable OBJECT-TYPE
	SYNTAX	INTEGER {
		enabled(1),
		disabled(2)
	}
	ACCESS	read-write
	STATUS	mandatory
	DESCRIPTION
		" Enables or Disables TFTP Subsystem "
	DEFVAL	{ enabled }
	::= { wfTftp 1 }

wfTftpDefaultVolume OBJECT-TYPE
	SYNTAX	INTEGER {
		minimum(2),
		default(2),
		maximum(14)
	}
	ACCESS	read-write
	STATUS	mandatory
	DESCRIPTION
		" The file system volume number to which transferred files will be written
		   and from which they will be retrieved. The volume number corresponds to
		   the slot number on which the volume resides. Slot 1 is reserved for SRM. "
	DEFVAL	{ default }
	::= { wfTftp 2 }

wfTftpXfers OBJECT-TYPE
	SYNTAX	Counter
	ACCESS	read-only
	STATUS	mandatory
	DESCRIPTION
		" Number of Transfers in Progress "
	::= { wfTftp 3 }

wfTftpTimeOut OBJECT-TYPE
	SYNTAX	INTEGER
	ACCESS	read-write
	STATUS	mandatory
	DESCRIPTION
		" General Retransmission time-out value (seconds) "
	DEFVAL	{ 5 }
	::= { wfTftp 4 }

wfTftpCloseTimeOut OBJECT-TYPE
	SYNTAX	INTEGER
	ACCESS	read-write
	STATUS	mandatory
	DESCRIPTION
		" Retransmission time-out value for sender of final ACK (seconds)"
	DEFVAL	{ 25 }
	::= { wfTftp 5 }

wfTftpRexmit OBJECT-TYPE
	SYNTAX	INTEGER
	ACCESS	read-write
	STATUS	mandatory
	DESCRIPTION
		" Maximum Number of Retransmissions "
	DEFVAL	{ 5 }
	::= { wfTftp 6 }

wfTftpInFiles OBJECT-TYPE
	SYNTAX	Counter
	ACCESS	read-only
	STATUS	mandatory
	DESCRIPTION
		" Number of files Successfully received "
	::= { wfTftp 7 }

wfTftpOutFiles OBJECT-TYPE
	SYNTAX	Counter
	ACCESS	read-only
	STATUS	mandatory
	DESCRIPTION
		" Number of files Successfully sent "
	::= { wfTftp 8 }

wfTftpInWRQ OBJECT-TYPE
	SYNTAX	Counter
	ACCESS	read-only
	STATUS	mandatory
	DESCRIPTION
		" Number of write requests received "
	::= { wfTftp 9 }

wfTftpOutWRQ OBJECT-TYPE
	SYNTAX	Counter
	ACCESS	read-only
	STATUS	mandatory
	DESCRIPTION
		" Number of write requests sent "
	::= { wfTftp 10 }

wfTftpInRRQ OBJECT-TYPE
	SYNTAX	Counter
	ACCESS	read-only
	STATUS	mandatory
	DESCRIPTION
		" Number of read requests received "
	::= { wfTftp 11 }

wfTftpOutRRQ OBJECT-TYPE
	SYNTAX	Counter
	ACCESS	read-only
	STATUS	mandatory
	DESCRIPTION
		" Number of read requests sent "
	::= { wfTftp 12 }

wfTftpRexmitPkts OBJECT-TYPE
	SYNTAX	Counter
	ACCESS	read-only
	STATUS	mandatory
	DESCRIPTION
		" Number of Re-transmitted packets "
	::= { wfTftp 13 }

wfTftpInErr OBJECT-TYPE
	SYNTAX	Counter
	ACCESS	read-only
	STATUS	mandatory
	DESCRIPTION
		" Number of Error PDUs Received "
	::= { wfTftp 14 }

wfTftpOutErr OBJECT-TYPE
	SYNTAX	Counter
	ACCESS	read-only
	STATUS	mandatory
	DESCRIPTION
		" Number of Error PDUs Sent "
	::= { wfTftp 15 }

wfTftpAborts OBJECT-TYPE
	SYNTAX	Counter
	ACCESS	read-only
	STATUS	mandatory
	DESCRIPTION
		" Number of Aborted Pseudo Connections "
	::= { wfTftp 16 }

wfTiRui		OBJECT IDENTIFIER ::= { wfServices 2 }

wfTiRuiState OBJECT-TYPE
	SYNTAX	INTEGER {
		idle(1),
		busy(2)
	}
	ACCESS	read-only
	STATUS	optional
	DESCRIPTION
		" The state of the ti rui command processor. Idle is normal state. Busy
		   indicates a command is being processed. 
		"
	DEFVAL	{ idle }
	::= { wfTiRui 1 }

wfTiRuiAction OBJECT-TYPE
	SYNTAX	DisplayString
	ACCESS	read-write
	STATUS	optional
	DESCRIPTION
		" Ti command request string "
	::= { wfTiRui 2 }

wfTiRuiResult OBJECT-TYPE
	SYNTAX	DisplayString
	ACCESS	read-only
	STATUS	optional
	DESCRIPTION
		" The result of the Ti command requst "
	::= { wfTiRui 3 }

wfTiRuiInReqs OBJECT-TYPE
	SYNTAX	Counter
	ACCESS	read-only
	STATUS	optional
	DESCRIPTION
		" Total number of command requests "
	::= { wfTiRui 4 }

wfTiRuiOutResults OBJECT-TYPE
	SYNTAX	Counter
	ACCESS	read-only
	STATUS	optional
	DESCRIPTION
		" Total number of command requests that processed without error "
	::= { wfTiRui 5 }

wfTiRuiOutResultsErr OBJECT-TYPE
	SYNTAX	Counter
	ACCESS	read-only
	STATUS	optional
	DESCRIPTION
		" Total number of command requests that could not be processed because of
		   errors 
		"
	::= { wfTiRui 6 }

wfTokenRingTable OBJECT-TYPE
	SYNTAX	SEQUENCE OF WfTokenRingEntry
	ACCESS	not-accessible
	STATUS	mandatory
	DESCRIPTION
		"
		   TOKEN RING line record
		 "
	::= { wfLine 2 }

wfTokenRingEntry OBJECT-TYPE
	SYNTAX	WfTokenRingEntry
	ACCESS	not-accessible
	STATUS	mandatory
	DESCRIPTION
		" An entry in the token table "
	INDEX	{ wfTokenRingSlot,
		wfTokenRingConnector }
	::= { wfTokenRingTable 1 }

WfTokenRingEntry ::= SEQUENCE {
	wfTokenRingDelete
		INTEGER,
	wfTokenRingDisable
		INTEGER,
	wfTokenRingState
		INTEGER,
	wfTokenRingSlot
		INTEGER,
	wfTokenRingConnector
		INTEGER,
	wfTokenRingCct
		INTEGER,
	wfTokenRingMtu
		INTEGER,
	wfTokenRingMadr
		OCTET STRING,
	wfTokenRingCfgMadr
		OCTET STRING,
	wfTokenRingMadrSelect
		INTEGER,
	wfTokenRingSpeed
		INTEGER,
	wfTokenRingEarlyTokenRelease
		INTEGER,
	wfTokenRingStatus
		INTEGER,
	wfTokenRingOpenState
		INTEGER,
	wfTokenRingOpenStatus
		INTEGER,
	wfTokenRingUpStream
		OCTET STRING,
	wfTokenRingRxOctets
		Counter,
	wfTokenRingRxFrames
		Counter,
	wfTokenRingTxOctets
		Counter,
	wfTokenRingTxFrames
		Counter,
	wfTokenRingInDiscards
		Counter,
	wfTokenRingInErrors
		Counter,
	wfTokenRingOutDiscards
		Counter,
	wfTokenRingOutErrors
		Counter,
	wfTokenRingTxClipFrames
		Counter,
	wfTokenRingRxReplenMisses
		Counter,
	wfTokenRingSignalLosses
		Counter,
	wfTokenRingHardErrors
		Counter,
	wfTokenRingSoftErrors
		Counter,
	wfTokenRingTransmitBeacons
		Counter,
	wfTokenRingLobeWireFaults
		Counter,
	wfTokenRingAutoRemovalErrors
		Counter,
	wfTokenRingRequestRemoves
		Counter,
	wfTokenRingCounterOverflows
		Counter,
	wfTokenRingSingleStations
		Counter,
	wfTokenRingRingRecoveries
		Counter,
	wfTokenRingAdapterChecks
		Counter,
	wfTokenRingFirstAdapterCheckCode
		INTEGER,
	wfTokenRingLastAdapterCheckCode
		INTEGER,
	wfTokenRingLineErrors
		Counter,
	wfTokenRingBurstErrors
		Counter,
	wfTokenRingAriFciErrors
		Counter,
	wfTokenRingLostFrameErrors
		Counter,
	wfTokenRingRxCongestionErrors
		Counter,
	wfTokenRingFrameCopiedErrors
		Counter,
	wfTokenRingTokenErrors
		Counter,
	wfTokenRingDmaBusErrors
		Counter,
	wfTokenRingDmaParityErrors
		Counter,
	wfTokenRingSrbNotFreeCmdAborts
		Counter,
	wfTokenRingRxProcessings
		Counter,
	wfTokenRingTxProcessings
		Counter,
	wfTokenRingTxCmplProcessings
		Counter,
	wfTokenRingRxTimeouts
		Counter,
	wfTokenRingCmdTimeouts
		Counter,
	wfTokenRingRxHostIntErrors
		Counter,
	wfTokenRingRxTxBufferSize
		INTEGER
}

wfTokenRingDelete OBJECT-TYPE
	SYNTAX	INTEGER {
		created(1),
		deleted(2)
	}
	ACCESS	read-write
	STATUS	mandatory
	DESCRIPTION
		" create/delete parameter. "
	DEFVAL	{ created }
	::= { wfTokenRingEntry 1 }

wfTokenRingDisable OBJECT-TYPE
	SYNTAX	INTEGER {
		enabled(1),
		disabled(2)
	}
	ACCESS	read-write
	STATUS	mandatory
	DESCRIPTION
		" enable/disable parameter. "
	DEFVAL	{ enabled }
	::= { wfTokenRingEntry 2 }

wfTokenRingState OBJECT-TYPE
	SYNTAX	INTEGER {
		up(1),
		down(2),
		init(3),
		notpresent(4)
	}
	ACCESS	read-only
	STATUS	mandatory
	DESCRIPTION
		" line driver state variable, Not Present, Init, Down, Up "
	DEFVAL	{ notpresent }
	::= { wfTokenRingEntry 3 }

wfTokenRingSlot OBJECT-TYPE
	SYNTAX	INTEGER {
		minimum(1),
		maximum(14)
	}
	ACCESS	read-only
	STATUS	mandatory
	DESCRIPTION
		" instance ID Slot, filled in by driver "
	::= { wfTokenRingEntry 4 }

wfTokenRingConnector OBJECT-TYPE
	SYNTAX	INTEGER {
		one(1),
		two(2)
	}
	ACCESS	read-only
	STATUS	mandatory
	DESCRIPTION
		" instance ID Connector, filled in by driver "
	::= { wfTokenRingEntry 5 }

wfTokenRingCct OBJECT-TYPE
	SYNTAX	INTEGER {
		minimum(1),
		maximum(1023)
	}
	ACCESS	read-write
	STATUS	mandatory
	DESCRIPTION
		" cct number for this line instance, configuration required "
	::= { wfTokenRingEntry 6 }

wfTokenRingMtu OBJECT-TYPE
	SYNTAX	INTEGER {
		default(4568)
	}
	ACCESS	read-only
	STATUS	mandatory
	DESCRIPTION
		" mtu parameter, fixed. This mtu of 4568 allows a type 3 Source Route
		   Frame (info=4472) to be IP encapsulated over Token Ring.
		   The components are:
		        AC_FC      (2) +
		        SNAP       (12+8) +
		        SNAP_IP    (12+8+20) +
		        SR         (12+18) +
		        TYPE3_INFO (4472) +
		        FCS        (4)
		        ---------------------
		        total      4568 bytes
		"
	DEFVAL	{ default }
	::= { wfTokenRingEntry 7 }

wfTokenRingMadr OBJECT-TYPE
	SYNTAX	OCTET STRING
	ACCESS	read-only
	STATUS	mandatory
	DESCRIPTION
		" line MAC address, line driver fills in the currently used 48 bit
		    MAC address.
		"
	::= { wfTokenRingEntry 8 }

wfTokenRingCfgMadr OBJECT-TYPE
	SYNTAX	OCTET STRING
	ACCESS	read-write
	STATUS	mandatory
	DESCRIPTION
		" Configured line MAC address. Only used if wfTokenRingMadrSelect
		   is set appropriately.
		"
	::= { wfTokenRingEntry 9 }

wfTokenRingMadrSelect OBJECT-TYPE
	SYNTAX	INTEGER {
		boxwide(1),
		prom(2),
		cnfg(3)
	}
	ACCESS	read-write
	STATUS	mandatory
	DESCRIPTION
		" Selector determines which MAC address the interface will use. "
	DEFVAL	{ boxwide }
	::= { wfTokenRingEntry 10 }

wfTokenRingSpeed OBJECT-TYPE
	SYNTAX	INTEGER {
		mbps4(4194304),
		mbps16(16777216)
	}
	ACCESS	read-write
	STATUS	mandatory
	DESCRIPTION
		" Token Ring speed parameter - 4 and 16 Mbps are only valid values "
	DEFVAL	{ mbps16 }
	::= { wfTokenRingEntry 11 }

wfTokenRingEarlyTokenRelease OBJECT-TYPE
	SYNTAX	INTEGER {
		enabled(1),
		disabled(2)
	}
	ACCESS	read-write
	STATUS	mandatory
	DESCRIPTION
		" Early Token Release parameter, only valid with 16Mbps "
	DEFVAL	{ enabled }
	::= { wfTokenRingEntry 12 }

wfTokenRingStatus OBJECT-TYPE
	SYNTAX	INTEGER
	ACCESS	read-only
	STATUS	mandatory
	DESCRIPTION
		" The current interface status. This attribute is only valid when the
		   wfTokenRingOpenState attribute is set to OPENED.  The attribute's
		   value is a sum of values,  one for each currently applicable condition
		   (ie, bit positions indicate active conditions).  Occurrences of each
		   condition are separately counted and the counts are included in this
		   MIB as attributes wfTokenRingSignalLosses through
		   wfTokenRingRingRecoveries.  The following values are defined:
		        32768 = Signal Losses
		        16384 = Hard Errors
		        8192  = Soft Errors
		        4096  = Transmit Beacons
		        2048  = Lobe Wire Faults
		        1024  = Auto-Removal Errors
		        256   = Remove Received
		        128   = Counter Overflows
		        64    = Single Stations
		        32    = Ring Recoveries
		   This attribute is the most recent sum of these conditions.  More
		   information on each condition is include in the descriptions of the
		   individual counter attributes.
		"
	::= { wfTokenRingEntry 13 }

wfTokenRingOpenState OBJECT-TYPE
	SYNTAX	INTEGER {
		opened(1),
		opening(2),
		closing(3),
		openfailure(4),
		ringfailure(5),
		closed(6)
	}
	ACCESS	read-only
	STATUS	mandatory
	DESCRIPTION
		" The current interface state with respect to entering or leaving
		   the ring.
		"
	DEFVAL	{ closed }
	::= { wfTokenRingEntry 14 }

wfTokenRingOpenStatus OBJECT-TYPE
	SYNTAX	INTEGER {
		open(1),
		badparam(2),
		lobefailed(3),
		signalloss(4),
		insertiontimeout(5),
		ringfailed(6),
		beaconing(7),
		duplicatemac(8),
		requestfailed(9),
		removereceived(10),
		unkerror(11),
		noopen(12)
	}
	ACCESS	read-only
	STATUS	mandatory
	DESCRIPTION
		" Indicates the success, or the reason for failure, of the station's
		   most recent attempt to enter the ring.
		"
	DEFVAL	{ noopen }
	::= { wfTokenRingEntry 15 }

wfTokenRingUpStream OBJECT-TYPE
	SYNTAX	OCTET STRING
	ACCESS	read-only
	STATUS	mandatory
	DESCRIPTION
		" MAC address of Up Stream neighbor. Only valid when 'opened'. "
	::= { wfTokenRingEntry 16 }

wfTokenRingRxOctets OBJECT-TYPE
	SYNTAX	Counter
	ACCESS	read-only
	STATUS	mandatory
	DESCRIPTION
		" Number of octets received without error. "
	::= { wfTokenRingEntry 17 }

wfTokenRingRxFrames OBJECT-TYPE
	SYNTAX	Counter
	ACCESS	read-only
	STATUS	mandatory
	DESCRIPTION
		" Number of frames received without error. "
	::= { wfTokenRingEntry 18 }

wfTokenRingTxOctets OBJECT-TYPE
	SYNTAX	Counter
	ACCESS	read-only
	STATUS	mandatory
	DESCRIPTION
		" Number of octets transmitted without error. "
	::= { wfTokenRingEntry 19 }

wfTokenRingTxFrames OBJECT-TYPE
	SYNTAX	Counter
	ACCESS	read-only
	STATUS	mandatory
	DESCRIPTION
		" Number of frames transmitted without error. "
	::= { wfTokenRingEntry 20 }

wfTokenRingInDiscards OBJECT-TYPE
	SYNTAX	Counter
	ACCESS	read-only
	STATUS	mandatory
	DESCRIPTION
		" Number of error-free inbound packets discarded. Usually due to lack of
		   memory resources. This is equivalent to wfTokenRingRxCongestionErrors.
		"
	::= { wfTokenRingEntry 21 }

wfTokenRingInErrors OBJECT-TYPE
	SYNTAX	Counter
	ACCESS	read-only
	STATUS	mandatory
	DESCRIPTION
		" Number of inbound packets not delivered to higher-layer protocol due to
		   errors.  The sum of wfTokenRingLineErrors and wfTokenRingBurstErrors.
		"
	::= { wfTokenRingEntry 22 }

wfTokenRingOutDiscards OBJECT-TYPE
	SYNTAX	Counter
	ACCESS	read-only
	STATUS	mandatory
	DESCRIPTION
		" Number of error-free outbound packets discarded. Usually due to lack of
		   transmission bandwidth. This is equivalent to wfTokenRingTxClipFrames.
		"
	::= { wfTokenRingEntry 23 }

wfTokenRingOutErrors OBJECT-TYPE
	SYNTAX	Counter
	ACCESS	read-only
	STATUS	mandatory
	DESCRIPTION
		" Number of outbound packets that could not be transmitted because of
		   errors. This is equivalent to wfTokenRingLostFrameErrors.
		"
	::= { wfTokenRingEntry 24 }

wfTokenRingTxClipFrames OBJECT-TYPE
	SYNTAX	Counter
	ACCESS	read-only
	STATUS	mandatory
	DESCRIPTION
		" Number of frames clipped in driver's transmit routine due to transmit
		   congestion.
		"
	::= { wfTokenRingEntry 25 }

wfTokenRingRxReplenMisses OBJECT-TYPE
	SYNTAX	Counter
	ACCESS	read-only
	STATUS	mandatory
	DESCRIPTION
		" Number of packet buffer misses while attempting to replenish driver
		   receive ring.
		"
	::= { wfTokenRingEntry 26 }

wfTokenRingSignalLosses OBJECT-TYPE
	SYNTAX	Counter
	ACCESS	read-only
	STATUS	mandatory
	DESCRIPTION
		" Number of ring signal losses detected. "
	::= { wfTokenRingEntry 27 }

wfTokenRingHardErrors OBJECT-TYPE
	SYNTAX	Counter
	ACCESS	read-only
	STATUS	mandatory
	DESCRIPTION
		" Number of events causing the adapter to transmit or receive beacon
		   MAC frames.
		"
	::= { wfTokenRingEntry 28 }

wfTokenRingSoftErrors OBJECT-TYPE
	SYNTAX	Counter
	ACCESS	read-only
	STATUS	mandatory
	DESCRIPTION
		" Number of soft errors. Corresponds to the number of Report Error MAC
		   frames transmitted by this station.
		"
	::= { wfTokenRingEntry 29 }

wfTokenRingTransmitBeacons OBJECT-TYPE
	SYNTAX	Counter
	ACCESS	read-only
	STATUS	mandatory
	DESCRIPTION
		" Number of events causing the adapter to transmit beacon frames. "
	::= { wfTokenRingEntry 30 }

wfTokenRingLobeWireFaults OBJECT-TYPE
	SYNTAX	Counter
	ACCESS	read-only
	STATUS	mandatory
	DESCRIPTION
		" Number of opens or shorts (cable faults) between the adapter and
		   the MAU.
		"
	::= { wfTokenRingEntry 31 }

wfTokenRingAutoRemovalErrors OBJECT-TYPE
	SYNTAX	Counter
	ACCESS	read-only
	STATUS	mandatory
	DESCRIPTION
		" Number of lobe wrap test failures during beacon auto_removal process. "
	::= { wfTokenRingEntry 32 }

wfTokenRingRequestRemoves OBJECT-TYPE
	SYNTAX	Counter
	ACCESS	read-only
	STATUS	mandatory
	DESCRIPTION
		" Number of Remove Ring Station MAC frames received. Each frame causes
		   this station to leave the ring.
		"
	::= { wfTokenRingEntry 33 }

wfTokenRingCounterOverflows OBJECT-TYPE
	SYNTAX	Counter
	ACCESS	read-only
	STATUS	mandatory
	DESCRIPTION
		" Number of adapter error counter overflows. "
	::= { wfTokenRingEntry 34 }

wfTokenRingSingleStations OBJECT-TYPE
	SYNTAX	Counter
	ACCESS	read-only
	STATUS	mandatory
	DESCRIPTION
		" Number of ring status change interrupts while adapter is only station
		   on the ring.
		"
	::= { wfTokenRingEntry 35 }

wfTokenRingRingRecoveries OBJECT-TYPE
	SYNTAX	Counter
	ACCESS	read-only
	STATUS	mandatory
	DESCRIPTION
		" Number of claim token MAC frames (ring recoveries) observed on
		   the ring.
		"
	::= { wfTokenRingEntry 36 }

wfTokenRingAdapterChecks OBJECT-TYPE
	SYNTAX	Counter
	ACCESS	read-only
	STATUS	mandatory
	DESCRIPTION
		" Number of internal adapter errors that result in adapter crashes. "
	::= { wfTokenRingEntry 37 }

wfTokenRingFirstAdapterCheckCode OBJECT-TYPE
	SYNTAX	INTEGER
	ACCESS	read-only
	STATUS	mandatory
	DESCRIPTION
		" Adapter Check Code of first occurrence. "
	::= { wfTokenRingEntry 38 }

wfTokenRingLastAdapterCheckCode OBJECT-TYPE
	SYNTAX	INTEGER
	ACCESS	read-only
	STATUS	mandatory
	DESCRIPTION
		" Adapter Check Code of most recent (last) occurrence. "
	::= { wfTokenRingEntry 39 }

wfTokenRingLineErrors OBJECT-TYPE
	SYNTAX	Counter
	ACCESS	read-only
	STATUS	mandatory
	DESCRIPTION
		" Number of frames copied or repeated by this station with bad
		   format or an FCS error.
		"
	::= { wfTokenRingEntry 40 }

wfTokenRingBurstErrors OBJECT-TYPE
	SYNTAX	Counter
	ACCESS	read-only
	STATUS	mandatory
	DESCRIPTION
		" Number of errored frames with no transition for 5 1/2 bit times. "
	::= { wfTokenRingEntry 41 }

wfTokenRingAriFciErrors OBJECT-TYPE
	SYNTAX	Counter
	ACCESS	read-only
	STATUS	mandatory
	DESCRIPTION
		" Number of occurrences of this station receiving both an AMP MAC
		   frame and a SMP MAC frame with the a & c bits clear or more than
		   one SMP MAC frame with the a & c bits clear without an intervening
		   AMP MAC frame.  This condition indicates that the up-stream
		   neighbor is unable to set the a & c bits in a frame that it has
		   copied.
		"
	::= { wfTokenRingEntry 42 }

wfTokenRingLostFrameErrors OBJECT-TYPE
	SYNTAX	Counter
	ACCESS	read-only
	STATUS	mandatory
	DESCRIPTION
		" Number of frames being stripped which are missing their tails. "
	::= { wfTokenRingEntry 43 }

wfTokenRingRxCongestionErrors OBJECT-TYPE
	SYNTAX	Counter
	ACCESS	read-only
	STATUS	mandatory
	DESCRIPTION
		" Number of frames dropped due to receive congestion. "
	::= { wfTokenRingEntry 44 }

wfTokenRingFrameCopiedErrors OBJECT-TYPE
	SYNTAX	Counter
	ACCESS	read-only
	STATUS	mandatory
	DESCRIPTION
		" Number of specifically addressed frames for this station that had
		   their a & c bits previously set.
		"
	::= { wfTokenRingEntry 45 }

wfTokenRingTokenErrors OBJECT-TYPE
	SYNTAX	Counter
	ACCESS	read-only
	STATUS	mandatory
	DESCRIPTION
		" Number of token protocol errors. Only relevant when this station is
		   the active monitor.
		"
	::= { wfTokenRingEntry 46 }

wfTokenRingDmaBusErrors OBJECT-TYPE
	SYNTAX	Counter
	ACCESS	read-only
	STATUS	mandatory
	DESCRIPTION
		" Number of bus errors during DMA that do not exceed threshold. "
	::= { wfTokenRingEntry 47 }

wfTokenRingDmaParityErrors OBJECT-TYPE
	SYNTAX	Counter
	ACCESS	read-only
	STATUS	mandatory
	DESCRIPTION
		" Number of parity errors during DMA that do not exceed threshold. "
	::= { wfTokenRingEntry 48 }

wfTokenRingSrbNotFreeCmdAborts OBJECT-TYPE
	SYNTAX	Counter
	ACCESS	read-only
	STATUS	mandatory
	DESCRIPTION
		" Number of host to adapter commands aborted because of in-completed in
		   process commands.
		"
	::= { wfTokenRingEntry 49 }

wfTokenRingRxProcessings OBJECT-TYPE
	SYNTAX	Counter
	ACCESS	read-only
	STATUS	mandatory
	DESCRIPTION
		" Number of processings of received frames (similar to RINT). "
	::= { wfTokenRingEntry 50 }

wfTokenRingTxProcessings OBJECT-TYPE
	SYNTAX	Counter
	ACCESS	read-only
	STATUS	mandatory
	DESCRIPTION
		" Number of processings of frames for transmit. "
	::= { wfTokenRingEntry 51 }

wfTokenRingTxCmplProcessings OBJECT-TYPE
	SYNTAX	Counter
	ACCESS	read-only
	STATUS	mandatory
	DESCRIPTION
		" Number of processings of transmitted frames (similar to TINT). "
	::= { wfTokenRingEntry 52 }

wfTokenRingRxTimeouts OBJECT-TYPE
	SYNTAX	Counter
	ACCESS	read-only
	STATUS	mandatory
	DESCRIPTION
		" Number of re-initializations due to receiver time-outs. "
	::= { wfTokenRingEntry 53 }

wfTokenRingCmdTimeouts OBJECT-TYPE
	SYNTAX	Counter
	ACCESS	read-only
	STATUS	mandatory
	DESCRIPTION
		" Number of re-initializations due to command time-outs. "
	::= { wfTokenRingEntry 54 }

wfTokenRingRxHostIntErrors OBJECT-TYPE
	SYNTAX	Counter
	ACCESS	read-only
	STATUS	mandatory
	DESCRIPTION
		" Number of re-initializations due to receive host interface errors. "
	::= { wfTokenRingEntry 55 }

wfTokenRingRxTxBufferSize OBJECT-TYPE
	SYNTAX	INTEGER
	ACCESS	read-only
	STATUS	mandatory
	DESCRIPTION
		" Internal Adapter RAM buffer size. "
	::= { wfTokenRingEntry 56 }

wfVinesBase	OBJECT IDENTIFIER ::= { wfVinesGroup 1 }

wfVinesBaseDelete OBJECT-TYPE
	SYNTAX	INTEGER {
		created(1),
		deleted(2)
	}
	ACCESS	read-write
	STATUS	mandatory
	DESCRIPTION
		"
		  Create/Delete parameter.  This value determines whether or not VINES
		  is configured on this slot.
		     "
	DEFVAL	{ created }
	::= { wfVinesBase 1 }

wfVinesBaseDisable OBJECT-TYPE
	SYNTAX	INTEGER {
		enabled(1),
		disabled(2)
	}
	ACCESS	read-write
	STATUS	mandatory
	DESCRIPTION
		"
		  This parameter determines whether or not VINES is to startup.
		     "
	DEFVAL	{ enabled }
	::= { wfVinesBase 2 }

wfVinesBaseState OBJECT-TYPE
	SYNTAX	INTEGER {
		up(1),
		down(2),
		init(3),
		notpresent(4)
	}
	ACCESS	read-only
	STATUS	mandatory
	DESCRIPTION
		"
		  This parameter reflects the current state of VINES.
		     "
	DEFVAL	{ notpresent }
	::= { wfVinesBase 3 }

wfVinesBaseUserNetid OBJECT-TYPE
	SYNTAX	INTEGER {
		minimum(1),
		maximum(2097151)
	}
	ACCESS	read-write
	STATUS	mandatory
	DESCRIPTION
		"
		  The network ID as defined by the user.  A null value indicates
		  that the user is not configuring a Network ID and that the
		  the router should assign it.
		     "
	::= { wfVinesBase 4 }

wfVinesBaseRouterNetid OBJECT-TYPE
	SYNTAX	Counter
	ACCESS	read-only
	STATUS	mandatory
	DESCRIPTION
		"
		  The network ID as defined by the router.  If the user configures
		  a Network ID in the above attribute, we will take that value
		  and add in the Wellfleet code for VINES and save it here.
		     "
	::= { wfVinesBase 5 }

wfVinesBaseBcastClass OBJECT-TYPE
	SYNTAX	INTEGER {
		bcast(1),
		chrg(2),
		cost(3),
		lans(4),
		srvr(5),
		nochrg(6),
		locost(7),
		alllans(8)
	}
	ACCESS	read-write
	STATUS	mandatory
	DESCRIPTION
		"
		  The broadcast modifier.  This value defines the
		  class of broadcast packets that are originated
		  by this node.
		     "
	DEFVAL	{ bcast }
	::= { wfVinesBase 6 }

wfVinesIp	OBJECT IDENTIFIER ::= { wfVinesGroup 2 }

wfVinesIpTotIn OBJECT-TYPE
	SYNTAX	Counter
	ACCESS	read-only
	STATUS	mandatory
	DESCRIPTION
		"
		  The total number of VINES IP packets received.
		     "
	::= { wfVinesIp 1 }

wfVinesIpTotOut OBJECT-TYPE
	SYNTAX	Counter
	ACCESS	read-only
	STATUS	mandatory
	DESCRIPTION
		"
		  The total number of VINES IP packets sent.
		     "
	::= { wfVinesIp 2 }

wfVinesIpBad OBJECT-TYPE
	SYNTAX	Counter
	ACCESS	read-only
	STATUS	mandatory
	DESCRIPTION
		"
		  The total number of badly formed packets that were received. 
		  This field is incremented when a packet is received with an 
		  improper checksum.  
		     "
	::= { wfVinesIp 3 }

wfVinesIpRouted OBJECT-TYPE
	SYNTAX	Counter
	ACCESS	read-only
	STATUS	mandatory
	DESCRIPTION
		"
		  The total number of packets received that were routed to another
		  node.  This statistic includes the number of IP packets
		  encapsulated within routed VINES IP headers.  Each routed packet
		  counts as both an incoming and outgoing packet.
		     "
	::= { wfVinesIp 4 }

wfVinesIpRoutedHWM OBJECT-TYPE
	SYNTAX	INTEGER
	ACCESS	read-only
	STATUS	mandatory
	DESCRIPTION
		"
		  The largest number of packets routed in one second since the server
		  was last booted.
		     "
	::= { wfVinesIp 5 }

wfVinesIpBcast OBJECT-TYPE
	SYNTAX	Counter
	ACCESS	read-only
	STATUS	mandatory
	DESCRIPTION
		"
		  The number of VINES IP broadcast packets sent, both locally
		  generated and routed from other nodes.  
		     "
	::= { wfVinesIp 6 }

wfVinesIpBcastHWM OBJECT-TYPE
	SYNTAX	INTEGER
	ACCESS	read-only
	STATUS	mandatory
	DESCRIPTION
		"
		  The largest number of packets broadcast in one second since the server
		  was last booted.
		     "
	::= { wfVinesIp 7 }

wfVinesIpReass OBJECT-TYPE
	SYNTAX	Counter
	ACCESS	read-only
	STATUS	mandatory
	DESCRIPTION
		"
		  The number of times that packets were reassembled.  Reassemblies
		  result from the transmission of packets that must be broken into
		  smaller pieces, then reassembled due to differences in transmission
		  media.
		  "
	::= { wfVinesIp 8 }

wfVinesIpFrags OBJECT-TYPE
	SYNTAX	Counter
	ACCESS	read-only
	STATUS	mandatory
	DESCRIPTION
		"
		  The number of packet fragmentations performed.
		     "
	::= { wfVinesIp 9 }

wfVinesIpToDodIP OBJECT-TYPE
	SYNTAX	Counter
	ACCESS	read-only
	STATUS	mandatory
	DESCRIPTION
		"
		  The number of packets that VINES IP passed to IP for encapsulation in
		  IP headers.  These packets were initially handled by VINES IP, but
		  were passed to IP for routing.  If the TCP/IP Server-to-Server
		  option is not installed, this value will be zero.
		     "
	::= { wfVinesIp 10 }

wfVinesIpFromDodIP OBJECT-TYPE
	SYNTAX	Counter
	ACCESS	read-only
	STATUS	mandatory
	DESCRIPTION
		"
		  The number of packets that VINES IP received from IP to be 
		  decapsulated into VINES packets.  IP initially handled these packets,
		  but had to pass them on to VINES IP for routing.  If the server is
		  not running a TCP/IP option, this value will be zero.
		     "
	::= { wfVinesIp 11 }

wfVinesRtpNbr	OBJECT IDENTIFIER ::= { wfVinesGroup 3 }

wfVinesRtpNbrNumber OBJECT-TYPE
	SYNTAX	INTEGER
	ACCESS	read-only
	STATUS	mandatory
	DESCRIPTION
		" Number of entries in the Table of Neighbors. "
	::= { wfVinesRtpNbr 1 }

wfVinesRtpNbrTable OBJECT-TYPE
	SYNTAX	SEQUENCE OF WfVinesRtpNbrEntry
	ACCESS	not-accessible
	STATUS	mandatory
	DESCRIPTION
		" This is the Table of Neighbors. "
	::= { wfVinesGroup 4 }

wfVinesRtpNbrEntry OBJECT-TYPE
	SYNTAX	WfVinesRtpNbrEntry
	ACCESS	not-accessible
	STATUS	mandatory
	DESCRIPTION
		" An entry in the Table of Neighbors. "
	INDEX	{ wfVinesRtpNbrNetId }
	::= { wfVinesRtpNbrTable 1 }

WfVinesRtpNbrEntry ::= SEQUENCE {
	wfVinesRtpNbrNetId
		Counter,
	wfVinesRtpNbrSubNetId
		INTEGER,
	wfVinesRtpNbrType
		INTEGER,
	wfVinesRtpNbrIfType
		INTEGER,
	wfVinesRtpNbrRemAdr
		OCTET STRING,
	wfVinesRtpNbrLocAdr
		OCTET STRING,
	wfVinesRtpNbrLocSlot
		INTEGER,
	wfVinesRtpNbrLocLine
		INTEGER,
	wfVinesRtpNbrSvrName
		OCTET STRING,
	wfVinesRtpNbrCost
		INTEGER
}

wfVinesRtpNbrNetId OBJECT-TYPE
	SYNTAX	Counter
	ACCESS	read-only
	STATUS	mandatory
	DESCRIPTION
		" The network ID of this neighbor. "
	::= { wfVinesRtpNbrEntry 1 }

wfVinesRtpNbrSubNetId OBJECT-TYPE
	SYNTAX	INTEGER
	ACCESS	read-only
	STATUS	mandatory
	DESCRIPTION
		" The subnetwork ID of this neighbor. "
	::= { wfVinesRtpNbrEntry 2 }

wfVinesRtpNbrType OBJECT-TYPE
	SYNTAX	INTEGER {
		workst(1),
		server(2)
	}
	ACCESS	read-only
	STATUS	mandatory
	DESCRIPTION
		" The type of node: client or server. "
	::= { wfVinesRtpNbrEntry 3 }

wfVinesRtpNbrIfType OBJECT-TYPE
	SYNTAX	INTEGER {
		enet(1),
		tr4k(2),
		tr16k(3),
		hdlc1200(4),
		hdlc4800(5),
		hdlc9600(6),
		hdlc56000(7),
		async1200(8),
		async4800(9),
		async9600(10),
		async56000(11),
		x251200(12),
		x254800(13),
		x259600(14),
		x2556000(15),
		t145k(16),
		t1128k(17),
		t1192k(18),
		t1256k(19),
		t1320k(20),
		t1384k(21),
		t1448k(22),
		t1512k(23),
		t1576k(24),
		t1640k(25),
		t1704k(26),
		t1896k(27),
		t11088k(28),
		t11344k(29),
		tunnel(30),
		fddi(31)
	}
	ACCESS	read-only
	STATUS	mandatory
	DESCRIPTION
		" This describes the type of interface. "
	::= { wfVinesRtpNbrEntry 4 }

wfVinesRtpNbrRemAdr OBJECT-TYPE
	SYNTAX	OCTET STRING
	ACCESS	read-only
	STATUS	mandatory
	DESCRIPTION
		" Remote MAC address. "
	::= { wfVinesRtpNbrEntry 5 }

wfVinesRtpNbrLocAdr OBJECT-TYPE
	SYNTAX	OCTET STRING
	ACCESS	read-only
	STATUS	mandatory
	DESCRIPTION
		" Local MAC address. "
	::= { wfVinesRtpNbrEntry 6 }

wfVinesRtpNbrLocSlot OBJECT-TYPE
	SYNTAX	INTEGER
	ACCESS	read-only
	STATUS	mandatory
	DESCRIPTION
		" Slot connected to this neighbor. "
	::= { wfVinesRtpNbrEntry 7 }

wfVinesRtpNbrLocLine OBJECT-TYPE
	SYNTAX	INTEGER
	ACCESS	read-only
	STATUS	mandatory
	DESCRIPTION
		" Line connected to this neighbor. "
	::= { wfVinesRtpNbrEntry 8 }

wfVinesRtpNbrSvrName OBJECT-TYPE
	SYNTAX	OCTET STRING
	ACCESS	read-only
	STATUS	mandatory
	DESCRIPTION
		" Name of the server (N/A). "
	::= { wfVinesRtpNbrEntry 9 }

wfVinesRtpNbrCost OBJECT-TYPE
	SYNTAX	INTEGER
	ACCESS	read-only
	STATUS	mandatory
	DESCRIPTION
		" Cost for this neighbor. "
	::= { wfVinesRtpNbrEntry 10 }

wfVinesRtpRt	OBJECT IDENTIFIER ::= { wfVinesGroup 5 }

wfVinesRtpRtNumber OBJECT-TYPE
	SYNTAX	INTEGER
	ACCESS	read-only
	STATUS	mandatory
	DESCRIPTION
		" Number of entries in the Table of Networks. "
	::= { wfVinesRtpRt 1 }

wfVinesRtpRtTable OBJECT-TYPE
	SYNTAX	SEQUENCE OF WfVinesRtpRtEntry
	ACCESS	not-accessible
	STATUS	mandatory
	DESCRIPTION
		" This is the Table of Networks. "
	::= { wfVinesGroup 6 }

wfVinesRtpRtEntry OBJECT-TYPE
	SYNTAX	WfVinesRtpRtEntry
	ACCESS	not-accessible
	STATUS	mandatory
	DESCRIPTION
		" An entry in the Table of Networks. "
	INDEX	{ wfVinesRtpRtNetid }
	::= { wfVinesRtpRtTable 1 }

WfVinesRtpRtEntry ::= SEQUENCE {
	wfVinesRtpRtNetid
		Counter,
	wfVinesRtpRtMetric
		INTEGER,
	wfVinesRtpRtIdle
		INTEGER,
	wfVinesRtpRtGateNetid
		Counter,
	wfVinesRtpRtSvrName
		OCTET STRING,
	wfVinesRtpRtGateSvrName
		OCTET STRING
}

wfVinesRtpRtNetid OBJECT-TYPE
	SYNTAX	Counter
	ACCESS	read-only
	STATUS	mandatory
	DESCRIPTION
		" The network ID number. "
	::= { wfVinesRtpRtEntry 1 }

wfVinesRtpRtMetric OBJECT-TYPE
	SYNTAX	INTEGER
	ACCESS	read-only
	STATUS	mandatory
	DESCRIPTION
		" The routing metric to get to this network. "
	::= { wfVinesRtpRtEntry 2 }

wfVinesRtpRtIdle OBJECT-TYPE
	SYNTAX	INTEGER
	ACCESS	read-only
	STATUS	mandatory
	DESCRIPTION
		" The idle time for this network. "
	::= { wfVinesRtpRtEntry 3 }

wfVinesRtpRtGateNetid OBJECT-TYPE
	SYNTAX	Counter
	ACCESS	read-only
	STATUS	mandatory
	DESCRIPTION
		" The network ID of the gateway to this network. "
	::= { wfVinesRtpRtEntry 4 }

wfVinesRtpRtSvrName OBJECT-TYPE
	SYNTAX	OCTET STRING
	ACCESS	read-only
	STATUS	mandatory
	DESCRIPTION
		" The servers name (N/A). "
	::= { wfVinesRtpRtEntry 5 }

wfVinesRtpRtGateSvrName OBJECT-TYPE
	SYNTAX	OCTET STRING
	ACCESS	read-only
	STATUS	mandatory
	DESCRIPTION
		" The name of the gateway server. "
	::= { wfVinesRtpRtEntry 6 }

wfVinesIf	OBJECT IDENTIFIER ::= { wfVinesGroup 7 }

wfVinesIfNumber OBJECT-TYPE
	SYNTAX	INTEGER
	ACCESS	read-only
	STATUS	mandatory
	DESCRIPTION
		" This is the number of entries in the Interfaces Table. "
	::= { wfVinesIf 1 }

wfVinesIfTable OBJECT-TYPE
	SYNTAX	SEQUENCE OF WfVinesIfEntry
	ACCESS	not-accessible
	STATUS	mandatory
	DESCRIPTION
		" This is the Table of Interfaces. "
	::= { wfVinesGroup 8 }

wfVinesIfEntry OBJECT-TYPE
	SYNTAX	WfVinesIfEntry
	ACCESS	not-accessible
	STATUS	mandatory
	DESCRIPTION
		" An entry to the Interface Table. "
	INDEX	{ wfVinesIfCct }
	::= { wfVinesIfTable 1 }

WfVinesIfEntry ::= SEQUENCE {
	wfVinesIfDelete
		INTEGER,
	wfVinesIfDisable
		INTEGER,
	wfVinesIfState
		INTEGER,
	wfVinesIfSlot
		INTEGER,
	wfVinesIfLine
		INTEGER,
	wfVinesIfCct
		INTEGER,
	wfVinesIfSession
		INTEGER,
	wfVinesIfType
		INTEGER,
	wfVinesIfDescr
		OCTET STRING,
	wfVinesIfAdr
		OCTET STRING,
	wfVinesIfDodIpDisable
		INTEGER,
	wfVinesIfArpDisable
		INTEGER,
	wfVinesIfTrEndStation
		INTEGER,
	wfVinesIfInPkts
		Counter,
	wfVinesIfInErrs
		Counter,
	wfVinesIfOutPkts
		Counter,
	wfVinesIfOutErrs
		Counter,
	wfVinesIfInMsgs
		Counter,
	wfVinesIfMux
		INTEGER,
	wfVinesIfFwdDrops
		Counter,
	wfVinesIfZeroHopDrops
		Counter,
	wfVinesIfIcpInErrorNotifs
		Counter,
	wfVinesIfIcpInMetricNotifs
		Counter,
	wfVinesIfIcpInErrors
		Counter,
	wfVinesIfIcpOutErrorNotifs
		Counter,
	wfVinesIfIcpOutMetricNotifs
		Counter,
	wfVinesIfArpInQueries
		Counter,
	wfVinesIfArpInAssgReqs
		Counter,
	wfVinesIfArpInErrors
		Counter,
	wfVinesIfArpOutServRsps
		Counter,
	wfVinesIfArpOutAssgRsps
		Counter,
	wfVinesIfInRedirects
		Counter,
	wfVinesIfOutRedirects
		Counter,
	wfVinesIfEchoInPkts
		Counter,
	wfVinesIfEchoOutPkts
		Counter,
	wfVinesIfReassFails
		Counter,
	wfVinesIfRemClientPrivDisable
		INTEGER
}

wfVinesIfDelete OBJECT-TYPE
	SYNTAX	INTEGER {
		created(1),
		deleted(2)
	}
	ACCESS	read-write
	STATUS	mandatory
	DESCRIPTION
		"
		  Create/Delete parameter.  Users perform an SNMP set command to
		  create/delete a VINES interface. 
		     "
	DEFVAL	{ created }
	::= { wfVinesIfEntry 1 }

wfVinesIfDisable OBJECT-TYPE
	SYNTAX	INTEGER {
		enabled(1),
		disabled(2)
	}
	ACCESS	read-write
	STATUS	mandatory
	DESCRIPTION
		"
		  Enable/Disable parameter.  Users perform an SNMP set command to
		  enable/disable a VINES interface. 
		     "
	DEFVAL	{ enabled }
	::= { wfVinesIfEntry 2 }

wfVinesIfState OBJECT-TYPE
	SYNTAX	INTEGER {
		up(1),
		down(2),
		init(3),
		notpresent(4)
	}
	ACCESS	read-only
	STATUS	mandatory
	DESCRIPTION
		"
		  This parameter reflects the current state of the VINES interface.
		     "
	DEFVAL	{ notpresent }
	::= { wfVinesIfEntry 3 }

wfVinesIfSlot OBJECT-TYPE
	SYNTAX	INTEGER
	ACCESS	read-only
	STATUS	mandatory
	DESCRIPTION
		" The slot on which this interface is configured. "
	::= { wfVinesIfEntry 4 }

wfVinesIfLine OBJECT-TYPE
	SYNTAX	INTEGER
	ACCESS	read-only
	STATUS	mandatory
	DESCRIPTION
		" The line on which this interface is configured. "
	::= { wfVinesIfEntry 5 }

wfVinesIfCct OBJECT-TYPE
	SYNTAX	INTEGER
	ACCESS	read-only
	STATUS	mandatory
	DESCRIPTION
		" The circuit number for this interface. "
	::= { wfVinesIfEntry 6 }

wfVinesIfSession OBJECT-TYPE
	SYNTAX	INTEGER
	ACCESS	read-only
	STATUS	mandatory
	DESCRIPTION
		" The session number for this interface. "
	::= { wfVinesIfEntry 7 }

wfVinesIfType OBJECT-TYPE
	SYNTAX	INTEGER {
		enet(1),
		tr4k(2),
		tr16k(3),
		hdlc1200(4),
		hdlc4800(5),
		hdlc9600(6),
		hdlc56000(7),
		async1200(8),
		async4800(9),
		async9600(10),
		async56000(11),
		x251200(12),
		x254800(13),
		x259600(14),
		x2556000(15),
		t145k(16),
		t1128k(17),
		t1192k(18),
		t1256k(19),
		t1320k(20),
		t1384k(21),
		t1448k(22),
		t1512k(23),
		t1576k(24),
		t1640k(25),
		t1704k(26),
		t1896k(27),
		t11088k(28),
		t11344k(29),
		tunnel(30),
		fddi(31)
	}
	ACCESS	read-write
	STATUS	mandatory
	DESCRIPTION
		" The type of interface this is. "
	DEFVAL	{ enet }
	::= { wfVinesIfEntry 8 }

wfVinesIfDescr OBJECT-TYPE
	SYNTAX	OCTET STRING
	ACCESS	read-only
	STATUS	mandatory
	DESCRIPTION
		" Description of this interface. "
	::= { wfVinesIfEntry 9 }

wfVinesIfAdr OBJECT-TYPE
	SYNTAX	OCTET STRING
	ACCESS	read-only
	STATUS	mandatory
	DESCRIPTION
		" The MAC address of this interface. "
	::= { wfVinesIfEntry 10 }

wfVinesIfDodIpDisable OBJECT-TYPE
	SYNTAX	INTEGER {
		enabled(1),
		disabled(2)
	}
	ACCESS	read-write
	STATUS	mandatory
	DESCRIPTION
		"
		  This parameter indicates if this interface is enabled to  encapsulate 
		  VINES packets over DoD IP.
		     "
	DEFVAL	{ disabled }
	::= { wfVinesIfEntry 11 }

wfVinesIfArpDisable OBJECT-TYPE
	SYNTAX	INTEGER {
		enabled(1),
		disabled(2)
	}
	ACCESS	read-write
	STATUS	mandatory
	DESCRIPTION
		"
		  This parameter indicates if this interface is enabled to support 
		  VINES ARP. 
		     "
	DEFVAL	{ disabled }
	::= { wfVinesIfEntry 12 }

wfVinesIfTrEndStation OBJECT-TYPE
	SYNTAX	INTEGER {
		enabled(1),
		disabled(2)
	}
	ACCESS	read-write
	STATUS	mandatory
	DESCRIPTION
		"
		  This parameter indicates if this interface is enabled for source
		  routing end station support. 
		     "
	DEFVAL	{ disabled }
	::= { wfVinesIfEntry 13 }

wfVinesIfInPkts OBJECT-TYPE
	SYNTAX	Counter
	ACCESS	read-only
	STATUS	mandatory
	DESCRIPTION
		" The number of packets received on this interface. "
	::= { wfVinesIfEntry 14 }

wfVinesIfInErrs OBJECT-TYPE
	SYNTAX	Counter
	ACCESS	read-only
	STATUS	mandatory
	DESCRIPTION
		" The number of packets received with errors. "
	::= { wfVinesIfEntry 15 }

wfVinesIfOutPkts OBJECT-TYPE
	SYNTAX	Counter
	ACCESS	read-only
	STATUS	mandatory
	DESCRIPTION
		" The number of packets transmitted on this interface."
	::= { wfVinesIfEntry 16 }

wfVinesIfOutErrs OBJECT-TYPE
	SYNTAX	Counter
	ACCESS	read-only
	STATUS	mandatory
	DESCRIPTION
		" The number of errors on packets transmitted. "
	::= { wfVinesIfEntry 17 }

wfVinesIfInMsgs OBJECT-TYPE
	SYNTAX	Counter
	ACCESS	read-only
	STATUS	mandatory
	DESCRIPTION
		" The number of messages received on this interface. "
	::= { wfVinesIfEntry 18 }

wfVinesIfMux OBJECT-TYPE
	SYNTAX	INTEGER {
		enet(1),
		snap(2)
	}
	ACCESS	read-write
	STATUS	mandatory
	DESCRIPTION
		"
		  Muxing scheme for this interface.  VINES currently only supports
		  Ethernet encapsulation, but they plan to switch to SNAP.
		     "
	DEFVAL	{ enet }
	::= { wfVinesIfEntry 19 }

wfVinesIfFwdDrops OBJECT-TYPE
	SYNTAX	Counter
	ACCESS	read-only
	STATUS	mandatory
	DESCRIPTION
		"
		  The number of pakets that were dropped because of no forwarding 
		  information for the destination.
		     "
	::= { wfVinesIfEntry 20 }

wfVinesIfZeroHopDrops OBJECT-TYPE
	SYNTAX	Counter
	ACCESS	read-only
	STATUS	mandatory
	DESCRIPTION
		" The number of pakets that were dropped because of a zero hop count. "
	::= { wfVinesIfEntry 21 }

wfVinesIfIcpInErrorNotifs OBJECT-TYPE
	SYNTAX	Counter
	ACCESS	read-only
	STATUS	mandatory
	DESCRIPTION
		" The number of ICP error notification packets received. "
	::= { wfVinesIfEntry 22 }

wfVinesIfIcpInMetricNotifs OBJECT-TYPE
	SYNTAX	Counter
	ACCESS	read-only
	STATUS	mandatory
	DESCRIPTION
		" The number of ICP metric notification packets received. "
	::= { wfVinesIfEntry 23 }

wfVinesIfIcpInErrors OBJECT-TYPE
	SYNTAX	Counter
	ACCESS	read-only
	STATUS	mandatory
	DESCRIPTION
		" The number of ICP packets received with errors. "
	::= { wfVinesIfEntry 24 }

wfVinesIfIcpOutErrorNotifs OBJECT-TYPE
	SYNTAX	Counter
	ACCESS	read-only
	STATUS	mandatory
	DESCRIPTION
		" The number of ICP error notification packets transmitted. "
	::= { wfVinesIfEntry 25 }

wfVinesIfIcpOutMetricNotifs OBJECT-TYPE
	SYNTAX	Counter
	ACCESS	read-only
	STATUS	mandatory
	DESCRIPTION
		" The number of ICP metric notification packets transmitted. "
	::= { wfVinesIfEntry 26 }

wfVinesIfArpInQueries OBJECT-TYPE
	SYNTAX	Counter
	ACCESS	read-only
	STATUS	mandatory
	DESCRIPTION
		" The number of ARP queries received. "
	::= { wfVinesIfEntry 27 }

wfVinesIfArpInAssgReqs OBJECT-TYPE
	SYNTAX	Counter
	ACCESS	read-only
	STATUS	mandatory
	DESCRIPTION
		" The number of ARP assignment requests received. "
	::= { wfVinesIfEntry 28 }

wfVinesIfArpInErrors OBJECT-TYPE
	SYNTAX	Counter
	ACCESS	read-only
	STATUS	mandatory
	DESCRIPTION
		" The number of ARP packets received with errors. "
	::= { wfVinesIfEntry 29 }

wfVinesIfArpOutServRsps OBJECT-TYPE
	SYNTAX	Counter
	ACCESS	read-only
	STATUS	mandatory
	DESCRIPTION
		" The number of ARP service responses sent. "
	::= { wfVinesIfEntry 30 }

wfVinesIfArpOutAssgRsps OBJECT-TYPE
	SYNTAX	Counter
	ACCESS	read-only
	STATUS	mandatory
	DESCRIPTION
		" The number of ARP assignment responses sent. "
	::= { wfVinesIfEntry 31 }

wfVinesIfInRedirects OBJECT-TYPE
	SYNTAX	Counter
	ACCESS	read-only
	STATUS	mandatory
	DESCRIPTION
		" The number of Redirect packets received. "
	::= { wfVinesIfEntry 32 }

wfVinesIfOutRedirects OBJECT-TYPE
	SYNTAX	Counter
	ACCESS	read-only
	STATUS	mandatory
	DESCRIPTION
		" The number of Redirect packets sent. "
	::= { wfVinesIfEntry 33 }

wfVinesIfEchoInPkts OBJECT-TYPE
	SYNTAX	Counter
	ACCESS	read-only
	STATUS	mandatory
	DESCRIPTION
		" The number of Echo packets received. "
	::= { wfVinesIfEntry 34 }

wfVinesIfEchoOutPkts OBJECT-TYPE
	SYNTAX	Counter
	ACCESS	read-only
	STATUS	mandatory
	DESCRIPTION
		" The number of Echo packets sent. "
	::= { wfVinesIfEntry 35 }

wfVinesIfReassFails OBJECT-TYPE
	SYNTAX	Counter
	ACCESS	read-only
	STATUS	mandatory
	DESCRIPTION
		" The number of packet reassemblies that failed. "
	::= { wfVinesIfEntry 36 }

wfVinesIfRemClientPrivDisable OBJECT-TYPE
	SYNTAX	INTEGER {
		enabled(1),
		disabled(2)
	}
	ACCESS	read-write
	STATUS	mandatory
	DESCRIPTION
		"
		  This parameter indicates that this interface will allow remote
		  clients privileges on this segment.  This means that a client
		  is not restricted to being within one hop of a VINES server. 
		     "
	DEFVAL	{ disabled }
	::= { wfVinesIfEntry 37 }

wfVinesIfX25VC	OBJECT IDENTIFIER ::= { wfVinesGroup 9 }

wfVinesIfX25VCNumber OBJECT-TYPE
	SYNTAX	INTEGER
	ACCESS	read-only
	STATUS	mandatory
	DESCRIPTION
		" This is the number of entries in the X.25 Virtual Circuit Table. "
	::= { wfVinesIfX25VC 1 }

wfVinesIfX25VCTable OBJECT-TYPE
	SYNTAX	SEQUENCE OF WfVinesIfX25VCEntry
	ACCESS	not-accessible
	STATUS	mandatory
	DESCRIPTION
		" This is the Table of X.25 Virtual Circuits. "
	::= { wfVinesGroup 10 }

wfVinesIfX25VCEntry OBJECT-TYPE
	SYNTAX	WfVinesIfX25VCEntry
	ACCESS	not-accessible
	STATUS	mandatory
	DESCRIPTION
		" An entry in the Table of X.25 Virtual Circuits. "
	INDEX	{ wfVinesIfX25VCCct }
	::= { wfVinesIfX25VCTable 1 }

WfVinesIfX25VCEntry ::= SEQUENCE {
	wfVinesIfX25VCSlot
		INTEGER,
	wfVinesIfX25VCLine
		INTEGER,
	wfVinesIfX25VCCct
		INTEGER,
	wfVinesIfX25VCSession
		INTEGER,
	wfVinesIfX25VCTotIn
		Counter,
	wfVinesIfX25VCTotOut
		Counter,
	wfVinesIfX25VCInErrs
		Counter,
	wfVinesIfX25VCOutErrs
		Counter,
	wfVinesIfX25VCPktsOut
		Counter,
	wfVinesIfX25VCPktsAwaitAck
		INTEGER,
	wfVinesIfX25VCBytesOut
		Counter,
	wfVinesIfX25VCBytesAwaitAck
		INTEGER,
	wfVinesIfX25VCPktsIn
		Counter,
	wfVinesIfX25VCBytesIn
		Counter,
	wfVinesIfX25VCResetsIn
		Counter,
	wfVinesIfX25VCResetsOut
		Counter
}

wfVinesIfX25VCSlot OBJECT-TYPE
	SYNTAX	INTEGER
	ACCESS	read-only
	STATUS	mandatory
	DESCRIPTION
		"
		  The number of the slot in which the card is installed.
		     "
	::= { wfVinesIfX25VCEntry 1 }

wfVinesIfX25VCLine OBJECT-TYPE
	SYNTAX	INTEGER
	ACCESS	read-only
	STATUS	mandatory
	DESCRIPTION
		"
		  For a serial line, this is the number of the line on the card.
		     "
	::= { wfVinesIfX25VCEntry 2 }

wfVinesIfX25VCCct OBJECT-TYPE
	SYNTAX	INTEGER
	ACCESS	read-only
	STATUS	mandatory
	DESCRIPTION
		"
		  Local circuit number for this Virtual Circuit.
		     "
	::= { wfVinesIfX25VCEntry 3 }

wfVinesIfX25VCSession OBJECT-TYPE
	SYNTAX	INTEGER
	ACCESS	read-only
	STATUS	mandatory
	DESCRIPTION
		"
		  Local session number for this Virtual Circuit.
		     "
	::= { wfVinesIfX25VCEntry 4 }

wfVinesIfX25VCTotIn OBJECT-TYPE
	SYNTAX	Counter
	ACCESS	read-only
	STATUS	mandatory
	DESCRIPTION
		"
		  The total number of VINES IP packets received on this VC.
		  Depending on the size of the X.25 packets received, more than one
		  X.25 packet can make up a VINES IP packet.
		     "
	::= { wfVinesIfX25VCEntry 5 }

wfVinesIfX25VCTotOut OBJECT-TYPE
	SYNTAX	Counter
	ACCESS	read-only
	STATUS	mandatory
	DESCRIPTION
		"
		  The total number of VINES IP packets sent on this VC.  Depending
		  on the size of the X.25 packets sent, more than one X.25 packet can
		  make up a VINES IP packet.
		     "
	::= { wfVinesIfX25VCEntry 6 }

wfVinesIfX25VCInErrs OBJECT-TYPE
	SYNTAX	Counter
	ACCESS	read-only
	STATUS	mandatory
	DESCRIPTION
		"
		  The total number of input errors.
		     "
	::= { wfVinesIfX25VCEntry 7 }

wfVinesIfX25VCOutErrs OBJECT-TYPE
	SYNTAX	Counter
	ACCESS	read-only
	STATUS	mandatory
	DESCRIPTION
		"
		  The total number of output errors.
		     "
	::= { wfVinesIfX25VCEntry 8 }

wfVinesIfX25VCPktsOut OBJECT-TYPE
	SYNTAX	Counter
	ACCESS	read-only
	STATUS	mandatory
	DESCRIPTION
		"
		  The total number of X.25 packets transmitted on this VC.
		     "
	::= { wfVinesIfX25VCEntry 9 }

wfVinesIfX25VCPktsAwaitAck OBJECT-TYPE
	SYNTAX	INTEGER
	ACCESS	read-only
	STATUS	mandatory
	DESCRIPTION
		"
		  Total number of X.25 packets transmitted on this VC waiting for ACK.
		     "
	::= { wfVinesIfX25VCEntry 10 }

wfVinesIfX25VCBytesOut OBJECT-TYPE
	SYNTAX	Counter
	ACCESS	read-only
	STATUS	mandatory
	DESCRIPTION
		"
		  Total Bytes transmitted on this VC.
		     "
	::= { wfVinesIfX25VCEntry 11 }

wfVinesIfX25VCBytesAwaitAck OBJECT-TYPE
	SYNTAX	INTEGER
	ACCESS	read-only
	STATUS	mandatory
	DESCRIPTION
		"
		  Total bytes transmitted on this VC that are waiting for ACK.
		     "
	::= { wfVinesIfX25VCEntry 12 }

wfVinesIfX25VCPktsIn OBJECT-TYPE
	SYNTAX	Counter
	ACCESS	read-only
	STATUS	mandatory
	DESCRIPTION
		"
		  Total X.25 packets received on this VC.
		     "
	::= { wfVinesIfX25VCEntry 13 }

wfVinesIfX25VCBytesIn OBJECT-TYPE
	SYNTAX	Counter
	ACCESS	read-only
	STATUS	mandatory
	DESCRIPTION
		"
		  Total Bytes received on this VC.
		     "
	::= { wfVinesIfX25VCEntry 14 }

wfVinesIfX25VCResetsIn OBJECT-TYPE
	SYNTAX	Counter
	ACCESS	read-only
	STATUS	mandatory
	DESCRIPTION
		"
		  Number of X.25 reset packets received on this VC.
		     "
	::= { wfVinesIfX25VCEntry 15 }

wfVinesIfX25VCResetsOut OBJECT-TYPE
	SYNTAX	Counter
	ACCESS	read-only
	STATUS	mandatory
	DESCRIPTION
		"
		  Number of X.25 reset packets transmitted on this VC.
		     "
	::= { wfVinesIfX25VCEntry 16 }

wfVinesTrafficFilterTable OBJECT-TYPE
	SYNTAX	SEQUENCE OF WfVinesTrafficFilterEntry
	ACCESS	not-accessible
	STATUS	mandatory
	DESCRIPTION
		" VINES Traffic Filters "
	::= { wfVinesGroup 11 }

wfVinesTrafficFilterEntry OBJECT-TYPE
	SYNTAX	WfVinesTrafficFilterEntry
	ACCESS	not-accessible
	STATUS	mandatory
	DESCRIPTION
		" An entry in WfVinesTrafficFilterTable. "
	INDEX	{ wfVinesTrafficFilterCircuit,
		wfVinesTrafficFilterRuleNumber,
		wfVinesTrafficFilterFragment }
	::= { wfVinesTrafficFilterTable 1 }

WfVinesTrafficFilterEntry ::= SEQUENCE {
	wfVinesTrafficFilterCreate
		INTEGER,
	wfVinesTrafficFilterEnable
		INTEGER,
	wfVinesTrafficFilterStatus
		INTEGER,
	wfVinesTrafficFilterCounter
		Counter,
	wfVinesTrafficFilterDefinition
		OCTET STRING,
	wfVinesTrafficFilterReserved
		INTEGER,
	wfVinesTrafficFilterCircuit
		INTEGER,
	wfVinesTrafficFilterRuleNumber
		INTEGER,
	wfVinesTrafficFilterFragment
		INTEGER
}

wfVinesTrafficFilterCreate OBJECT-TYPE
	SYNTAX	INTEGER {
		created(1),
		deleted(2)
	}
	ACCESS	read-write
	STATUS	mandatory
	DESCRIPTION
		" Defines the existence of the traffic filter rule:
		  created - traffic filter exists
		  delete - traffic filter does not exist and can be deleted. "
	DEFVAL	{ created }
	::= { wfVinesTrafficFilterEntry 1 }

wfVinesTrafficFilterEnable OBJECT-TYPE
	SYNTAX	INTEGER {
		enabled(1),
		disabled(2)
	}
	ACCESS	read-write
	STATUS	mandatory
	DESCRIPTION
		" Defines whether or not the traffic filter rule should be used:
		  enabled - activate the rule.
		  disabled - inactivate the rule. "
	DEFVAL	{ enabled }
	::= { wfVinesTrafficFilterEntry 2 }

wfVinesTrafficFilterStatus OBJECT-TYPE
	SYNTAX	INTEGER {
		active(1),
		error(2),
		inactive(3)
	}
	ACCESS	read-only
	STATUS	mandatory
	DESCRIPTION
		" Defines the current status of the traffic filter:
		  inactive - the rule is not in use.
		  active - the rule is being used.
		  error - the application detected an error in the rule. "
	DEFVAL	{ inactive }
	::= { wfVinesTrafficFilterEntry 3 }

wfVinesTrafficFilterCounter OBJECT-TYPE
	SYNTAX	Counter
	ACCESS	read-only
	STATUS	mandatory
	DESCRIPTION
		" The number of received packets that have
		           matched this rule. "
	::= { wfVinesTrafficFilterEntry 4 }

wfVinesTrafficFilterDefinition OBJECT-TYPE
	SYNTAX	OCTET STRING
	ACCESS	read-write
	STATUS	mandatory
	DESCRIPTION
		" The filter rule definition. "
	::= { wfVinesTrafficFilterEntry 5 }

wfVinesTrafficFilterReserved OBJECT-TYPE
	SYNTAX	INTEGER
	ACCESS	not-accessible
	STATUS	mandatory
	DESCRIPTION
		" Reserved field. "
	::= { wfVinesTrafficFilterEntry 6 }

wfVinesTrafficFilterCircuit OBJECT-TYPE
	SYNTAX	INTEGER
	ACCESS	read-only
	STATUS	mandatory
	DESCRIPTION
		" The ID of the Circuit to which the
		    filter is applied. "
	::= { wfVinesTrafficFilterEntry 7 }

wfVinesTrafficFilterRuleNumber OBJECT-TYPE
	SYNTAX	INTEGER
	ACCESS	read-only
	STATUS	mandatory
	DESCRIPTION
		" ID for the rule. "
	::= { wfVinesTrafficFilterEntry 8 }

wfVinesTrafficFilterFragment OBJECT-TYPE
	SYNTAX	INTEGER
	ACCESS	read-only
	STATUS	mandatory
	DESCRIPTION
		" Fragment number - for large rules. "
	::= { wfVinesTrafficFilterEntry 9 }

wfVinesNameTable OBJECT-TYPE
	SYNTAX	SEQUENCE OF WfVinesNameEntry
	ACCESS	not-accessible
	STATUS	mandatory
	DESCRIPTION
		" This is the Name-to-Address Binding Table. "
	::= { wfVinesGroup 12 }

wfVinesNameEntry OBJECT-TYPE
	SYNTAX	WfVinesNameEntry
	ACCESS	not-accessible
	STATUS	mandatory
	DESCRIPTION
		" An entry in the Table of Names. "
	INDEX	{ wfVinesNameNetid }
	::= { wfVinesNameTable 1 }

WfVinesNameEntry ::= SEQUENCE {
	wfVinesNameDelete
		INTEGER,
	wfVinesNameDisable
		INTEGER,
	wfVinesNameNetid
		Counter,
	wfVinesNameHost
		DisplayString,
	wfVinesNameSubNetid
		INTEGER
}

wfVinesNameDelete OBJECT-TYPE
	SYNTAX	INTEGER {
		created(1),
		deleted(2)
	}
	ACCESS	read-write
	STATUS	mandatory
	DESCRIPTION
		"
		  Create/Delete parameter.  Users perform an SNMP set command to
		  create/delete this name. 
		     "
	DEFVAL	{ created }
	::= { wfVinesNameEntry 1 }

wfVinesNameDisable OBJECT-TYPE
	SYNTAX	INTEGER {
		enabled(1),
		disabled(2)
	}
	ACCESS	read-write
	STATUS	mandatory
	DESCRIPTION
		"
		  Enable/Disable parameter.  Users perform an SNMP set command to
		  enable/disable a name. 
		     "
	DEFVAL	{ enabled }
	::= { wfVinesNameEntry 2 }

wfVinesNameNetid OBJECT-TYPE
	SYNTAX	Counter
	ACCESS	read-write
	STATUS	mandatory
	DESCRIPTION
		" This is the network number for the host. "
	::= { wfVinesNameEntry 3 }

wfVinesNameHost OBJECT-TYPE
	SYNTAX	DisplayString
	ACCESS	read-write
	STATUS	mandatory
	DESCRIPTION
		" This is the name of the host. "
	::= { wfVinesNameEntry 4 }

wfVinesNameSubNetid OBJECT-TYPE
	SYNTAX	INTEGER
	ACCESS	read-write
	STATUS	mandatory
	DESCRIPTION
		" This is the subnetwork number for the host. "
	::= { wfVinesNameEntry 5 }

wfVinesArp	OBJECT IDENTIFIER ::= { wfVinesGroup 13 }

wfVinesArpDelete OBJECT-TYPE
	SYNTAX	INTEGER {
		created(1),
		deleted(2)
	}
	ACCESS	read-write
	STATUS	mandatory
	DESCRIPTION
		"Create/Delete parameter. Default is created.
		     Users perform an SNMP SET operation on this
		     object in order to create/delete ARP."
	DEFVAL	{ created }
	::= { wfVinesArp 1 }

wfVinesArpDisable OBJECT-TYPE
	SYNTAX	INTEGER {
		enabled(1),
		disabled(2)
	}
	ACCESS	read-write
	STATUS	mandatory
	DESCRIPTION
		" Enable/Disable Parameter indicates whether
		       this ARP record is enabled or disabled. "
	DEFVAL	{ enabled }
	::= { wfVinesArp 2 }

wfVinesArpState OBJECT-TYPE
	SYNTAX	INTEGER {
		up(1),
		down(2)
	}
	ACCESS	read-only
	STATUS	mandatory
	DESCRIPTION
		" State of ARP. "
	DEFVAL	{ down }
	::= { wfVinesArp 3 }

wfVinesArpSubnetid OBJECT-TYPE
	SYNTAX	INTEGER
	ACCESS	read-only
	STATUS	mandatory
	DESCRIPTION
		"
		  The next subnetwork ID to be assigned. 
		     "
	::= { wfVinesArp 4 }

wfVinesArpSubnetBlock OBJECT-TYPE
	SYNTAX	INTEGER {
		minimum(1),
		default(2),
		maximum(32)
	}
	ACCESS	read-write
	STATUS	mandatory
	DESCRIPTION
		"
		  The size of the block of subnet ids a slot can grab. 
		     "
	DEFVAL	{ default }
	::= { wfVinesArp 5 }

wfVinesArpAssignDeniedPkts OBJECT-TYPE
	SYNTAX	Counter
	ACCESS	read-only
	STATUS	mandatory
	DESCRIPTION
		"
		  Number of ARP Assignment packets received for which we
		  didn't have a free subnet number.
		     "
	::= { wfVinesArp 6 }

wfXnsBase	OBJECT IDENTIFIER ::= { wfXnsGroup 1 }

wfXnsBaseDelete OBJECT-TYPE
	SYNTAX	INTEGER {
		created(1),
		deleted(2)
	}
	ACCESS	read-write
	STATUS	mandatory
	DESCRIPTION
		"Create/Delete parameter. Default is created.
		     Users perform an SNMP SET operation on this
		     object in order to create/delete XNS."
	DEFVAL	{ created }
	::= { wfXnsBase 1 }

wfXnsBaseDisable OBJECT-TYPE
	SYNTAX	INTEGER {
		enabled(1),
		disabled(2)
	}
	ACCESS	read-write
	STATUS	mandatory
	DESCRIPTION
		"Enable/Disable parameter. Default is enabled.
		     Users perform an SNMP SET operation on this
		     object in order to enable/disable XNS."
	DEFVAL	{ enabled }
	::= { wfXnsBase 2 }

wfXnsBaseState OBJECT-TYPE
	SYNTAX	INTEGER {
		up(1),
		down(2),
		init(3),
		notpresent(4)
	}
	ACCESS	read-only
	STATUS	mandatory
	DESCRIPTION
		"The current state of the entire XNS."
	DEFVAL	{ notpresent }
	::= { wfXnsBase 3 }

wfXnsBaseHostNumber OBJECT-TYPE
	SYNTAX	OCTET STRING
	ACCESS	read-write
	STATUS	mandatory
	DESCRIPTION
		" Host Number of Router and potential MAC address of box."
	::= { wfXnsBase 4 }

wfXnsBaseRtEntryTable OBJECT-TYPE
	SYNTAX	SEQUENCE OF WfXnsBaseRtEntry
	ACCESS	not-accessible
	STATUS	mandatory
	DESCRIPTION
		" The table of Elements in XNS's routing table "
	::= { wfXnsGroup 2 }

wfXnsBaseRtEntry OBJECT-TYPE
	SYNTAX	WfXnsBaseRtEntry
	ACCESS	not-accessible
	STATUS	mandatory
	DESCRIPTION
		" An entry in the Routing Table "
	INDEX	{ wfXnsBaseRouteDest }
	::= { wfXnsBaseRtEntryTable 1 }

WfXnsBaseRtEntry ::= SEQUENCE {
	wfXnsBaseRouteDest
		OCTET STRING,
	wfXnsBaseRouteIfIndex
		INTEGER,
	wfXnsBaseRouteMetric
		INTEGER,
	wfXnsBaseRouteNextHopNetwork
		OCTET STRING,
	wfXnsBaseRouteNextHopHost
		OCTET STRING,
	wfXnsBaseRouteType
		INTEGER,
	wfXnsBaseRouteProto
		INTEGER,
	wfXnsBaseRouteAge
		INTEGER,
	wfXnsBaseRouteInfo
		OCTET STRING
}

wfXnsBaseRouteDest OBJECT-TYPE
	SYNTAX	OCTET STRING
	ACCESS	read-only
	STATUS	mandatory
	DESCRIPTION
		" The destination XNS address of this route. An
		     entry with a value of 0.0.0.0 is considered a
		     default route.  Multiple routes to a single
		     destination can appear in the table, but access to
		     such multiple entries is dependent on the table-
		     access mechanisms defined by the network
		     management protocol in use."
	::= { wfXnsBaseRtEntry 1 }

wfXnsBaseRouteIfIndex OBJECT-TYPE
	SYNTAX	INTEGER
	ACCESS	read-only
	STATUS	mandatory
	DESCRIPTION
		"The index value which uniquely identifies the
		     local interface through which the next hop of this
		     route should be reached.  The interface identified
		     by a particular value of this index is the same
		     interface as identified by the same value of
		     ifIndex."
	::= { wfXnsBaseRtEntry 2 }

wfXnsBaseRouteMetric OBJECT-TYPE
	SYNTAX	INTEGER
	ACCESS	read-only
	STATUS	mandatory
	DESCRIPTION
		"The primary routing metric for this route. The
		     semantics of this metric are determined by the
		     routing-protocol specified in the route's
		     ipRouteProto value.  If this metric is not used,
		     its value should be set to -1."
	::= { wfXnsBaseRtEntry 3 }

wfXnsBaseRouteNextHopNetwork OBJECT-TYPE
	SYNTAX	OCTET STRING
	ACCESS	read-only
	STATUS	mandatory
	DESCRIPTION
		"(In the case of a route bound to an interface
		     which is realized via a broadcast media, the value
		     of this field is the agent's XNS address on that
		     interface.)"
	::= { wfXnsBaseRtEntry 4 }

wfXnsBaseRouteNextHopHost OBJECT-TYPE
	SYNTAX	OCTET STRING
	ACCESS	read-only
	STATUS	mandatory
	DESCRIPTION
		"
		       Full network.host_id address of nexthop host for
		       this network.
		     "
	::= { wfXnsBaseRtEntry 5 }

wfXnsBaseRouteType OBJECT-TYPE
	SYNTAX	INTEGER {
		other(1),
		invalid(2),
		direct(3),
		indirect(4),
		static(5)
	}
	ACCESS	read-only
	STATUS	mandatory
	DESCRIPTION
		"The type of route. Note that the values
		     direct(3) and indirect(4) refer to the notion of
		     direct and indirect routing in the XNS
		     architecture.
		     Setting this object to the value invalid(2) has
		     the effect of invalidating the corresponding entry
		     in the ipRouteTable object.  That is, it
		     effectively dissasociates the destination
		     identified with said entry from the route
		     identified with said entry.  It is an
		     implementation-specific matter as to whether the
		     agent removes an invalidated entry from the table.
		     nagement stations must be prepared
		     to receive tabular information from agents that
		     corresponds to entries not currently in use.
		     Proper interpretation of such entries requires
		     examination of the relevant ipRouteType object."
	::= { wfXnsBaseRtEntry 6 }

wfXnsBaseRouteProto OBJECT-TYPE
	SYNTAX	INTEGER {
		other(1),
		local(2),
		netmgmt(3),
		rip(4)
	}
	ACCESS	read-only
	STATUS	mandatory
	DESCRIPTION
		"The routing mechanism via which this route was
		     learned.  Inclusion of values for gateway routing
		     protocols is not intended to imply that hosts
		     should support those protocols."
	::= { wfXnsBaseRtEntry 7 }

wfXnsBaseRouteAge OBJECT-TYPE
	SYNTAX	INTEGER
	ACCESS	read-only
	STATUS	mandatory
	DESCRIPTION
		"The number of seconds since this route was last
		     updated or otherwise determined to be correct.
		     Note that no semantics of `too old' can be implied
		     except through knowledge of the routing protocol
		     by which the route was learned."
	::= { wfXnsBaseRtEntry 8 }

wfXnsBaseRouteInfo OBJECT-TYPE
	SYNTAX	OCTET STRING
	ACCESS	read-only
	STATUS	mandatory
	DESCRIPTION
		" A user-defined string which describes this Route entry "
	::= { wfXnsBaseRtEntry 9 }

wfXnsInterfaceTable OBJECT-TYPE
	SYNTAX	SEQUENCE OF WfXnsInterfaceEntry
	ACCESS	not-accessible
	STATUS	mandatory
	DESCRIPTION
		" The network interface record "
	::= { wfXnsGroup 3 }

wfXnsInterfaceEntry OBJECT-TYPE
	SYNTAX	WfXnsInterfaceEntry
	ACCESS	not-accessible
	STATUS	mandatory
	DESCRIPTION
		" An entry in the Routing Table "
	INDEX	{ wfXnsInterfaceNetworkNumber,
		wfXnsInterfaceCircuit }
	::= { wfXnsInterfaceTable 1 }

WfXnsInterfaceEntry ::= SEQUENCE {
	wfXnsInterfaceIndex
		INTEGER,
	wfXnsInterfaceDelete
		INTEGER,
	wfXnsInterfaceDisable
		INTEGER,
	wfXnsInterfaceState
		INTEGER,
	wfXnsInterfaceCircuit
		INTEGER,
	wfXnsInterfaceNetworkNumber
		OCTET STRING,
	wfXnsInterfaceCost
		INTEGER,
	wfXnsInterfaceXsumOn
		INTEGER,
	wfXnsInterfaceEncaps
		INTEGER,
	wfXnsInterfaceMacAddress
		OCTET STRING,
	wfXnsInterfaceSMDSGroupAddress
		OCTET STRING,
	wfXnsInterfaceMaxInfo
		INTEGER,
	wfXnsInterfaceExtServer
		INTEGER,
	wfXnsInterfaceExServNetwork
		OCTET STRING,
	wfXnsInterfaceExServHostId
		OCTET STRING,
	wfXnsInterfaceExServPktType
		OCTET STRING,
	wfXnsInterfaceExServSockNm
		OCTET STRING,
	wfXnsInterfaceInReceives
		Counter,
	wfXnsInterfaceInHdrErrors
		Counter,
	wfXnsInterfaceInAddrErrors
		Counter,
	wfXnsInterfaceForwDatagrams
		Counter,
	wfXnsInterfaceInUnknownProtos
		Counter,
	wfXnsInterfaceInDiscards
		Counter,
	wfXnsInterfaceInDelivers
		Counter,
	wfXnsInterfaceOutRequests
		Counter,
	wfXnsInterfaceOutDiscards
		Counter,
	wfXnsInterfaceOutNoRoutes
		Counter,
	wfXnsInterfaceFRBcast
		OCTET STRING,
	wfXnsInterfaceFRMcast
		OCTET STRING
}

wfXnsInterfaceIndex OBJECT-TYPE
	SYNTAX	INTEGER
	ACCESS	read-only
	STATUS	mandatory
	DESCRIPTION
		"A unique value for each XNS interface. Its value
		    ranges between 1 and the value of MAXCIRCUITS."
	::= { wfXnsInterfaceEntry 1 }

wfXnsInterfaceDelete OBJECT-TYPE
	SYNTAX	INTEGER {
		created(1),
		deleted(2)
	}
	ACCESS	read-write
	STATUS	mandatory
	DESCRIPTION
		"Create/Delete parameter. Default is created.
		     Users perform an SNMP SET operation on this
		     object in order to create/delete an XNS interface."
	DEFVAL	{ created }
	::= { wfXnsInterfaceEntry 2 }

wfXnsInterfaceDisable OBJECT-TYPE
	SYNTAX	INTEGER {
		enabled(1),
		disabled(2)
	}
	ACCESS	read-write
	STATUS	mandatory
	DESCRIPTION
		"Enable/Disable parameter. Default is enabled.
		     Users perform an SNMP SET operation on this
		     object in order to enable/disable an XNS interface."
	DEFVAL	{ enabled }
	::= { wfXnsInterfaceEntry 3 }

wfXnsInterfaceState OBJECT-TYPE
	SYNTAX	INTEGER {
		up(1),
		down(2),
		init(3),
		notpresent(4)
	}
	ACCESS	read-only
	STATUS	mandatory
	DESCRIPTION
		"The current state of the XNS interface"
	DEFVAL	{ notpresent }
	::= { wfXnsInterfaceEntry 4 }

wfXnsInterfaceCircuit OBJECT-TYPE
	SYNTAX	INTEGER
	ACCESS	read-only
	STATUS	mandatory
	DESCRIPTION
		" The Circuit Number that this interface runs over"
	::= { wfXnsInterfaceEntry 5 }

wfXnsInterfaceNetworkNumber OBJECT-TYPE
	SYNTAX	OCTET STRING
	ACCESS	read-only
	STATUS	mandatory
	DESCRIPTION
		" The XNS Address to which this entry's addressing information
		       pertains "
	::= { wfXnsInterfaceEntry 6 }

wfXnsInterfaceCost OBJECT-TYPE
	SYNTAX	INTEGER
	ACCESS	read-write
	STATUS	mandatory
	DESCRIPTION
		" The Cost associated with the XNS Address of this entry "
	::= { wfXnsInterfaceEntry 7 }

wfXnsInterfaceXsumOn OBJECT-TYPE
	SYNTAX	INTEGER {
		enabled(1),
		disabled(2)
	}
	ACCESS	read-write
	STATUS	mandatory
	DESCRIPTION
		" Flag for checksums "
	DEFVAL	{ enabled }
	::= { wfXnsInterfaceEntry 8 }

wfXnsInterfaceEncaps OBJECT-TYPE
	SYNTAX	INTEGER {
		ethernet(1),
		snap(2)
	}
	ACCESS	read-only
	STATUS	mandatory
	DESCRIPTION
		" If changed while router is running yowsa !!!!           "
	DEFVAL	{ ethernet }
	::= { wfXnsInterfaceEntry 9 }

wfXnsInterfaceMacAddress OBJECT-TYPE
	SYNTAX	OCTET STRING
	ACCESS	read-write
	STATUS	mandatory
	DESCRIPTION
		"
		       The MacAddress of this interface 
		       this port will receive or transmit.
		     "
	::= { wfXnsInterfaceEntry 10 }

wfXnsInterfaceSMDSGroupAddress OBJECT-TYPE
	SYNTAX	OCTET STRING
	ACCESS	read-write
	STATUS	mandatory
	DESCRIPTION
		"
		       The SMDS Group Address of this interface 
		       this port will receive or transmit.
		     "
	::= { wfXnsInterfaceEntry 11 }

wfXnsInterfaceMaxInfo OBJECT-TYPE
	SYNTAX	INTEGER
	ACCESS	read-only
	STATUS	mandatory
	DESCRIPTION
		"
		         The maximum size of the INFO (non-MAC) field 
		         that this port will receive or transmit.
		        "
	::= { wfXnsInterfaceEntry 12 }

wfXnsInterfaceExtServer OBJECT-TYPE
	SYNTAX	INTEGER {
		enabled(1),
		disabled(2)
	}
	ACCESS	read-write
	STATUS	mandatory
	DESCRIPTION
		"
		          Flag indicating if this interface has External server 
		          capabilities turned on. Allows interface to pass on
		          defined packets, such as PEP/TP requests, to a 
		          remote server not located on local network.
		         "
	DEFVAL	{ disabled }
	::= { wfXnsInterfaceEntry 13 }

wfXnsInterfaceExServNetwork OBJECT-TYPE
	SYNTAX	OCTET STRING
	ACCESS	read-write
	STATUS	mandatory
	DESCRIPTION
		"
		          The Network address of the remote server.
		        "
	::= { wfXnsInterfaceEntry 14 }

wfXnsInterfaceExServHostId OBJECT-TYPE
	SYNTAX	OCTET STRING
	ACCESS	read-write
	STATUS	mandatory
	DESCRIPTION
		"
		          The Host ID of the remote server.
		        "
	::= { wfXnsInterfaceEntry 15 }

wfXnsInterfaceExServPktType OBJECT-TYPE
	SYNTAX	OCTET STRING
	ACCESS	read-write
	STATUS	mandatory
	DESCRIPTION
		"
		          The packet type of the requests which are to be
		          passed on to the specified remote server.
		        "
	::= { wfXnsInterfaceEntry 16 }

wfXnsInterfaceExServSockNm OBJECT-TYPE
	SYNTAX	OCTET STRING
	ACCESS	read-write
	STATUS	mandatory
	DESCRIPTION
		"
		          The destination socket number of the requests which 
		          are to be passed on to the specified remote server.
		          If no socket number is specified then all packets
		          of the specified type that this interface receives
		          will be forwarded to specified remote server.
		        "
	::= { wfXnsInterfaceEntry 17 }

wfXnsInterfaceInReceives OBJECT-TYPE
	SYNTAX	Counter
	ACCESS	read-only
	STATUS	mandatory
	DESCRIPTION
		"The total number of input datagrams received from
		         interfaces, including those received in error."
	::= { wfXnsInterfaceEntry 18 }

wfXnsInterfaceInHdrErrors OBJECT-TYPE
	SYNTAX	Counter
	ACCESS	read-only
	STATUS	mandatory
	DESCRIPTION
		"
		           The number of input datagrams discarded due to
		           errors in their XNS headers, including bad
		           checksums, version number mismatch, other format
		           errors, time-to-live exceeded, errors discovered
		           in processing their XNS options, etc.
		         "
	::= { wfXnsInterfaceEntry 19 }

wfXnsInterfaceInAddrErrors OBJECT-TYPE
	SYNTAX	Counter
	ACCESS	read-only
	STATUS	mandatory
	DESCRIPTION
		"
		          The number of input datagrams discarded because
		          the XNS address in their XNS header's destination
		          field was not a valid address to be received at
		          this entity.  This count includes invalid
		          addresses (e.g., 0.0.0.0) and addresses of
		          unsupported Classes (e.g., Class E).  For entities
		          which are not XNS Gateways and therefore do not
		          forward datagrams, this counter includes datagrams
		          discarded because the destination address was not
		          a local address.
		        "
	::= { wfXnsInterfaceEntry 20 }

wfXnsInterfaceForwDatagrams OBJECT-TYPE
	SYNTAX	Counter
	ACCESS	read-only
	STATUS	mandatory
	DESCRIPTION
		"
		          The number of input datagrams for which this
		          entity was not their final XNS destination, as a
		          result of which an attempt was made to find a
		          route to forward them to that final destination.
		          In entities which do not act as XNS Gateways, this
		          counter will include only those packets which were
		          Source-Routed via this entity, and the Source-
		          Route option processing was successful.
		         "
	::= { wfXnsInterfaceEntry 21 }

wfXnsInterfaceInUnknownProtos OBJECT-TYPE
	SYNTAX	Counter
	ACCESS	read-only
	STATUS	mandatory
	DESCRIPTION
		"
		         The number of locally-addressed datagrams
		         received successfully but discarded because of an
		         unknown or unsupported protocol.
		        "
	::= { wfXnsInterfaceEntry 22 }

wfXnsInterfaceInDiscards OBJECT-TYPE
	SYNTAX	Counter
	ACCESS	read-only
	STATUS	mandatory
	DESCRIPTION
		"
		          The number of input XNS datagrams for which no
		          problems were encountered to prevent their
		          continued processing, but which were discarded
		          (e.g., for lack of buffer space).  Note that this
		          counter does not include any datagrams discarded
		          while awaiting re-assembly.
		        "
	::= { wfXnsInterfaceEntry 23 }

wfXnsInterfaceInDelivers OBJECT-TYPE
	SYNTAX	Counter
	ACCESS	read-only
	STATUS	mandatory
	DESCRIPTION
		"
		          The total number of input datagrams successfully
		          delivered to XNS user-protocols (including ICMP).
		        "
	::= { wfXnsInterfaceEntry 24 }

wfXnsInterfaceOutRequests OBJECT-TYPE
	SYNTAX	Counter
	ACCESS	read-only
	STATUS	mandatory
	DESCRIPTION
		"
		         The total number of XNS datagrams which local XNS
		         user-protocols supplied to XNS in
		         requests for transmission.  Note that this counter
		         does not include any datagrams counted in 
		         XnsInteraceFwdDatagrams.
		       "
	::= { wfXnsInterfaceEntry 25 }

wfXnsInterfaceOutDiscards OBJECT-TYPE
	SYNTAX	Counter
	ACCESS	read-only
	STATUS	mandatory
	DESCRIPTION
		"
		          The number of output XNS datagrams for which no
		          problem was encountered to prevent their
		          transmission to their destination, but which were
		          discarded (e.g., for lack of buffer space).  Note
		          that this counter would include datagrams counted
		          in XnsForwDatagrams if any such packets met this
		          (discretionary) discard criterion.
		        "
	::= { wfXnsInterfaceEntry 26 }

wfXnsInterfaceOutNoRoutes OBJECT-TYPE
	SYNTAX	Counter
	ACCESS	read-only
	STATUS	mandatory
	DESCRIPTION
		"
		          The number of XNS datagrams discarded because no
		          route could be found to transmit them to their
		          destination.  Note that this counter includes any
		          packets counted in ipForwDatagrams which meet this
		          `no-route' criterion.  Note that this includes any
		          datagarms which a host cannot route because all of
		          its default gateways are down.
		        "
	::= { wfXnsInterfaceEntry 27 }

wfXnsInterfaceFRBcast OBJECT-TYPE
	SYNTAX	OCTET STRING
	ACCESS	read-write
	STATUS	mandatory
	DESCRIPTION
		" Configurable Frame Relay broadcast address "
	::= { wfXnsInterfaceEntry 28 }

wfXnsInterfaceFRMcast OBJECT-TYPE
	SYNTAX	OCTET STRING
	ACCESS	read-write
	STATUS	mandatory
	DESCRIPTION
		" Configurable Frame Relay multicast address "
	::= { wfXnsInterfaceEntry 29 }

wfXnsRipIntfTable OBJECT-TYPE
	SYNTAX	SEQUENCE OF WfXnsRipIntfEntry
	ACCESS	not-accessible
	STATUS	mandatory
	DESCRIPTION
		" The list of RIP interfaces "
	::= { wfXnsGroup 4 }

wfXnsRipIntfEntry OBJECT-TYPE
	SYNTAX	WfXnsRipIntfEntry
	ACCESS	not-accessible
	STATUS	mandatory
	DESCRIPTION
		" An entry in the Routing Table "
	INDEX	{ wfXnsRipInterfaceIndex }
	::= { wfXnsRipIntfTable 1 }

WfXnsRipIntfEntry ::= SEQUENCE {
	wfXnsRipInterfaceDelete
		INTEGER,
	wfXnsRipInterfaceDisable
		INTEGER,
	wfXnsRipInterfaceState
		INTEGER,
	wfXnsRipInterfaceIndex
		OCTET STRING,
	wfXnsRipInterfaceSupply
		INTEGER,
	wfXnsRipInterfaceListen
		INTEGER
}

wfXnsRipInterfaceDelete OBJECT-TYPE
	SYNTAX	INTEGER {
		created(1),
		deleted(2)
	}
	ACCESS	read-write
	STATUS	mandatory
	DESCRIPTION
		"Create/Delete parameter. Default is created.
		     Users perform an SNMP SET operation on this
		     object in order to create/delete an RIP Interface instance."
	DEFVAL	{ created }
	::= { wfXnsRipIntfEntry 1 }

wfXnsRipInterfaceDisable OBJECT-TYPE
	SYNTAX	INTEGER {
		enabled(1),
		disabled(2)
	}
	ACCESS	read-write
	STATUS	mandatory
	DESCRIPTION
		"Enable/Disable parameter. Default is enabled.
		     Users perform an SNMP SET operation on this
		     object in order to enable/disable a RIP instance."
	DEFVAL	{ enabled }
	::= { wfXnsRipIntfEntry 2 }

wfXnsRipInterfaceState OBJECT-TYPE
	SYNTAX	INTEGER {
		up(1),
		down(2),
		init(3),
		notpresent(4)
	}
	ACCESS	read-only
	STATUS	mandatory
	DESCRIPTION
		"The current state of RIP on this interface."
	DEFVAL	{ notpresent }
	::= { wfXnsRipIntfEntry 3 }

wfXnsRipInterfaceIndex OBJECT-TYPE
	SYNTAX	OCTET STRING
	ACCESS	read-only
	STATUS	mandatory
	DESCRIPTION
		"The XNS interface to run RIP on."
	::= { wfXnsRipIntfEntry 4 }

wfXnsRipInterfaceSupply OBJECT-TYPE
	SYNTAX	INTEGER {
		enabled(1),
		disabled(2)
	}
	ACCESS	read-write
	STATUS	mandatory
	DESCRIPTION
		"Transmit RIP packets."
	DEFVAL	{ enabled }
	::= { wfXnsRipIntfEntry 5 }

wfXnsRipInterfaceListen OBJECT-TYPE
	SYNTAX	INTEGER {
		enabled(1),
		disabled(2)
	}
	ACCESS	read-write
	STATUS	mandatory
	DESCRIPTION
		"Receive RIP packets."
	DEFVAL	{ enabled }
	::= { wfXnsRipIntfEntry 6 }

wfXnsAdjacentHostTable OBJECT-TYPE
	SYNTAX	SEQUENCE OF WfXnsAdjacentHostEntry
	ACCESS	not-accessible
	STATUS	mandatory
	DESCRIPTION
		"  must be configured for a nexthop host.                     "
	::= { wfXnsGroup 5 }

wfXnsAdjacentHostEntry OBJECT-TYPE
	SYNTAX	WfXnsAdjacentHostEntry
	ACCESS	not-accessible
	STATUS	mandatory
	DESCRIPTION
		" An entry in the Adjacent Host Table "
	INDEX	{ wfXnsAhTargHostNetwork,
		wfXnsAhTargHostId }
	::= { wfXnsAdjacentHostTable 1 }

WfXnsAdjacentHostEntry ::= SEQUENCE {
	wfXnsAhDelete
		INTEGER,
	wfXnsAhDisable
		INTEGER,
	wfXnsAhTargHostNetwork
		OCTET STRING,
	wfXnsAhTargHostId
		OCTET STRING,
	wfXnsAhNextHopIntf
		OCTET STRING,
	wfXnsAhDlci
		OCTET STRING
}

wfXnsAhDelete OBJECT-TYPE
	SYNTAX	INTEGER {
		created(1),
		deleted(2)
	}
	ACCESS	read-write
	STATUS	mandatory
	DESCRIPTION
		"Create/Delete parameter. Default is created.
		     Users perform an SNMP SET operation on this
		     object in order to create/delete the IPX
		     Static Host."
	DEFVAL	{ created }
	::= { wfXnsAdjacentHostEntry 1 }

wfXnsAhDisable OBJECT-TYPE
	SYNTAX	INTEGER {
		enabled(1),
		disabled(2)
	}
	ACCESS	read-write
	STATUS	mandatory
	DESCRIPTION
		"Enable/Disable parameter. Default is enabled.
		     Users perform an SNMP SET operation on this
		     object in order to enable/disable this IPX
		     Static Route."
	DEFVAL	{ enabled }
	::= { wfXnsAdjacentHostEntry 2 }

wfXnsAhTargHostNetwork OBJECT-TYPE
	SYNTAX	OCTET STRING
	ACCESS	read-only
	STATUS	mandatory
	DESCRIPTION
		"The network address of the static host. "
	::= { wfXnsAdjacentHostEntry 3 }

wfXnsAhTargHostId OBJECT-TYPE
	SYNTAX	OCTET STRING
	ACCESS	read-only
	STATUS	mandatory
	DESCRIPTION
		" The Address of this static host. "
	::= { wfXnsAdjacentHostEntry 4 }

wfXnsAhNextHopIntf OBJECT-TYPE
	SYNTAX	OCTET STRING
	ACCESS	read-write
	STATUS	mandatory
	DESCRIPTION
		" The Next Hop Interface Network Address "
	::= { wfXnsAdjacentHostEntry 5 }

wfXnsAhDlci OBJECT-TYPE
	SYNTAX	OCTET STRING
	ACCESS	read-write
	STATUS	mandatory
	DESCRIPTION
		" The next Hop Host address "
	::= { wfXnsAdjacentHostEntry 6 }

wfXnsStaticRouteTable OBJECT-TYPE
	SYNTAX	SEQUENCE OF WfXnsStaticRouteEntry
	ACCESS	not-accessible
	STATUS	mandatory
	DESCRIPTION
		" The list of Adjacent Hosts used for Configuring XNS "
	::= { wfXnsGroup 6 }

wfXnsStaticRouteEntry OBJECT-TYPE
	SYNTAX	WfXnsStaticRouteEntry
	ACCESS	not-accessible
	STATUS	mandatory
	DESCRIPTION
		" An entry in the Host Table "
	INDEX	{ wfXnsSrTargNetwork,
		wfXnsSrNextHopNetwork }
	::= { wfXnsStaticRouteTable 1 }

WfXnsStaticRouteEntry ::= SEQUENCE {
	wfXnsSrDelete
		INTEGER,
	wfXnsSrDisable
		INTEGER,
	wfXnsSrTargNetwork
		OCTET STRING,
	wfXnsSrCost
		INTEGER,
	wfXnsSrNextHopNetwork
		OCTET STRING,
	wfXnsSrNextHopHost
		OCTET STRING,
	wfXnsSrTargNetworkRt
		INTEGER
}

wfXnsSrDelete OBJECT-TYPE
	SYNTAX	INTEGER {
		created(1),
		deleted(2)
	}
	ACCESS	read-write
	STATUS	mandatory
	DESCRIPTION
		"Create/Delete parameter. Default is created.
		     Users perform an SNMP SET operation on this
		     object in order to create/delete the XNS
		     Static Route."
	DEFVAL	{ created }
	::= { wfXnsStaticRouteEntry 1 }

wfXnsSrDisable OBJECT-TYPE
	SYNTAX	INTEGER {
		enabled(1),
		disabled(2)
	}
	ACCESS	read-write
	STATUS	mandatory
	DESCRIPTION
		"Enable/Disable parameter. Default is enabled.
		     Users perform an SNMP SET operation on this
		     object in order to enable/disable this XNS
		     Static Route."
	DEFVAL	{ enabled }
	::= { wfXnsStaticRouteEntry 2 }

wfXnsSrTargNetwork OBJECT-TYPE
	SYNTAX	OCTET STRING
	ACCESS	read-only
	STATUS	mandatory
	DESCRIPTION
		" The Address of this static route "
	::= { wfXnsStaticRouteEntry 3 }

wfXnsSrCost OBJECT-TYPE
	SYNTAX	INTEGER
	ACCESS	read-write
	STATUS	mandatory
	DESCRIPTION
		" The Cost of this Static Route "
	::= { wfXnsStaticRouteEntry 4 }

wfXnsSrNextHopNetwork OBJECT-TYPE
	SYNTAX	OCTET STRING
	ACCESS	read-only
	STATUS	mandatory
	DESCRIPTION
		" The Next Hop XNS Address "
	::= { wfXnsStaticRouteEntry 5 }

wfXnsSrNextHopHost OBJECT-TYPE
	SYNTAX	OCTET STRING
	ACCESS	read-write
	STATUS	mandatory
	DESCRIPTION
		" The next Hop Host address "
	::= { wfXnsStaticRouteEntry 6 }

wfXnsSrTargNetworkRt OBJECT-TYPE
	SYNTAX	INTEGER
	ACCESS	read-only
	STATUS	mandatory
	DESCRIPTION
		" The Route Identifier Which numbered route this is to be "
	::= { wfXnsStaticRouteEntry 7 }

wfXnsTrafficFilterTable OBJECT-TYPE
	SYNTAX	SEQUENCE OF WfXnsTrafficFilterEntry
	ACCESS	not-accessible
	STATUS	mandatory
	DESCRIPTION
		" XNS Traffic Filters "
	::= { wfXnsGroup 7 }

wfXnsTrafficFilterEntry OBJECT-TYPE
	SYNTAX	WfXnsTrafficFilterEntry
	ACCESS	not-accessible
	STATUS	mandatory
	DESCRIPTION
		" A traffic filter definition "
	INDEX	{ wfXnsTrafficFilterInterface,
		wfXnsTrafficFilterCircuit,
		wfXnsTrafficFilterRuleNumber,
		wfXnsTrafficFilterFragment }
	::= { wfXnsTrafficFilterTable 1 }

WfXnsTrafficFilterEntry ::= SEQUENCE {
	wfXnsTrafficFilterCreate
		INTEGER,
	wfXnsTrafficFilterEnable
		INTEGER,
	wfXnsTrafficFilterStatus
		INTEGER,
	wfXnsTrafficFilterCounter
		Counter,
	wfXnsTrafficFilterDefinition
		Opaque,
	wfXnsTrafficFilterReserved
		INTEGER,
	wfXnsTrafficFilterInterface
		OCTET STRING,
	wfXnsTrafficFilterCircuit
		INTEGER,
	wfXnsTrafficFilterRuleNumber
		INTEGER,
	wfXnsTrafficFilterFragment
		INTEGER
}

wfXnsTrafficFilterCreate OBJECT-TYPE
	SYNTAX	INTEGER {
		created(1),
		deleted(2)
	}
	ACCESS	read-write
	STATUS	mandatory
	DESCRIPTION
		" Defines the existence of the traffic filter rule:
		               created - traffic filter exists
		               delete - traffic filter does not exist and can be deleted.
		        "
	DEFVAL	{ created }
	::= { wfXnsTrafficFilterEntry 1 }

wfXnsTrafficFilterEnable OBJECT-TYPE
	SYNTAX	INTEGER {
		enabled(1),
		disabled(2)
	}
	ACCESS	read-write
	STATUS	mandatory
	DESCRIPTION
		"
		                Defines whether or not the traffic filter rule should be used:
		                enabled - activate the rule.
		                disabled - inactivate the rule.
		        "
	DEFVAL	{ enabled }
	::= { wfXnsTrafficFilterEntry 2 }

wfXnsTrafficFilterStatus OBJECT-TYPE
	SYNTAX	INTEGER {
		active(1),
		error(2),
		inactive(3)
	}
	ACCESS	read-only
	STATUS	mandatory
	DESCRIPTION
		" Defines the current status of the traffic filter:
		                inactive - the rule is not in use.
		                active - the rule is being used.
		                error - the application detected an error in the rule. "
	DEFVAL	{ inactive }
	::= { wfXnsTrafficFilterEntry 3 }

wfXnsTrafficFilterCounter OBJECT-TYPE
	SYNTAX	Counter
	ACCESS	read-only
	STATUS	mandatory
	DESCRIPTION
		" The number of received packets that have
		           matched this rule. "
	::= { wfXnsTrafficFilterEntry 4 }

wfXnsTrafficFilterDefinition OBJECT-TYPE
	SYNTAX	Opaque
	ACCESS	read-write
	STATUS	mandatory
	DESCRIPTION
		" The filter rule definition. "
	::= { wfXnsTrafficFilterEntry 5 }

wfXnsTrafficFilterReserved OBJECT-TYPE
	SYNTAX	INTEGER
	ACCESS	not-accessible
	STATUS	mandatory
	DESCRIPTION
		" Reserved field. "
	::= { wfXnsTrafficFilterEntry 6 }

wfXnsTrafficFilterInterface OBJECT-TYPE
	SYNTAX	OCTET STRING
	ACCESS	read-only
	STATUS	mandatory
	DESCRIPTION
		"
		           The network address of the XNS
		           interface to which this filter is applied.
		         "
	::= { wfXnsTrafficFilterEntry 7 }

wfXnsTrafficFilterCircuit OBJECT-TYPE
	SYNTAX	INTEGER
	ACCESS	read-only
	STATUS	mandatory
	DESCRIPTION
		"
		           The ID of the Circuit to which the
		           filter is applied.
		         "
	::= { wfXnsTrafficFilterEntry 8 }

wfXnsTrafficFilterRuleNumber OBJECT-TYPE
	SYNTAX	INTEGER
	ACCESS	read-only
	STATUS	mandatory
	DESCRIPTION
		" ID for the rule. "
	::= { wfXnsTrafficFilterEntry 9 }

wfXnsTrafficFilterFragment OBJECT-TYPE
	SYNTAX	INTEGER
	ACCESS	read-only
	STATUS	mandatory
	DESCRIPTION
		" Fragment number - for large rules. "
	::= { wfXnsTrafficFilterEntry 10 }

END
