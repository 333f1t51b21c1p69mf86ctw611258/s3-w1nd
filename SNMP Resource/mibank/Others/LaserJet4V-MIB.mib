-- (C)  COPYRIGHT HEWLETT-PACKARD COMPANY 1997.
--
-- LaserJet 4V Printer Model Specific MIB.
--
-- Generated on August 4, 1997.
--
-- Company names and product names mentioned herein may be
-- trademarks, and/or registered trademarks of their respective
-- companies.
--
-- For interal and external use.
--
-- This MIB describes all the printer model specific
-- objects suppported by the LaserJet 4V printer                             
-- when networked connected using a JetDirect print
-- server.
--
-- The following MIB also contain objects supported
-- by a JetDirect connected LaserJet 4V printer:
--                                                                           
-- rfc 1213 MIB II
--
-- This MIB complies with the following RFCs:
--
-- rfc 1157 Simple Network Management Protocol
-- rfc 1155 Structure of Management Information
--
-- Notes:
--
-- 1) At the time this MIB was published, a
--    defect existed where the printer would not correctly
--    handle an SNMP get next request.  The printer
--    behavior is correct for tabular objects, but not
--    scalar objects.  For example, energy-star, sleep-mode,
--    and on-off-line are all scalars with OIDS:
--
--    energy-star { dm 1 1 1 1 }
--    sleep-mode  { dm 1 1 1 2 }
--    on-off-line { dm 1 2 2 5 }
--
--    These three objects are the first three objects supported
--    under the dm tree.
--
--    The printer operation (using OpenView tools as an
--    example) is:
--
--      snmpnext hpb18207 .1.3.6.1.4.1.11.2.3.9.4.2.1.1.1.2.0
--
--    with a reply of:
--
--      hp.nm.hpsystem.net-peripheral.netdm.dm.device.system.status-system.
--      on-off-line.0 : INTEGER: eOnline
--
--    which the printer handles correctly.
--
--    However, if the zero is left off the end, then the printer operation
--    is:
--
--      snmpnext hpb18207 .1.3.6.1.4.1.11.2.3.9.4.2.1.1.1.2
--
--    with a reply of:
--
--      hp.nm.hpsystem.net-peripheral.netdm.dm.device.system.status-system.
--      on-off-line.0 : INTEGER: eOnline
--
--    which is incorrect.  The object that should have been returned is
--    the energy-star object, not the on-off-line object.
--
--    Since the OpenView MIB Browser uses the get next command in an
--    attempt to retrieve all the supported objects under the specified OID
--                                                  =======================
--    (object identifier) and the printer returns an object that is not under
--    the specified OID, the MIB Browser assumes there are no objects
--    supported under the specified OID and reports "no value (s) returned for
--    query".
--
--    If you use an SNMP tool other than OpenView MIB Browser to do a get,
--    the printer properly responds.
--
--    Retrieving tables using the OpenView MIB Browser works fine.  Only
--    retrieving scalar objects fails.
--
-- 2) Proprietary Objects containing a string which are defined in this 
--    MIB use the first two bytes to hold the symbol set used to encode
--    the string.  The Roman-8 symbol set has a hex encoding of 0x0115.
--    Other symbol sets are listed in the PCL 5 Comparison Guide in table
--    C-1 Symbol Set Values.  Standard Printer MIB (prt...objects) and 
--    Host Resources MIB (hr...objects) strings do not contain symbol 
--    set information.
--
-- 3) Some of the objects included are only supported if an accessory
--    is installed.  These accessories include:
--      MIO/EIO based accessories
--      SIMM/DIMM based accessories
--      Mass storage devices
--      Paper handling accessories
--      Adobe PostScript accessory
--
--

LaserJet4V-MIB DEFINITIONS ::= BEGIN

IMPORTS OBJECT-TYPE, enterprises FROM RFC1155-SMI;

hp OBJECT IDENTIFIER ::= { enterprises 11 }
nm OBJECT IDENTIFIER ::= { hp 2 }
hpsystem OBJECT IDENTIFIER ::= { nm 3 }
net-peripheral OBJECT IDENTIFIER ::= { hpsystem 9 }
netdm OBJECT IDENTIFIER ::= { net-peripheral 4 }
dm OBJECT IDENTIFIER ::= {  netdm 2}

DisplayString ::= OCTET STRING

device                                 OBJECT IDENTIFIER ::=  { dm 1 } 
system                                 OBJECT IDENTIFIER ::=  { device 1 } 
settings-system                        OBJECT IDENTIFIER ::=  { system 1 } 
status-system                          OBJECT IDENTIFIER ::=  { system 2 } 
display                                OBJECT IDENTIFIER ::=  { status-system 20 } 
display-status                         OBJECT IDENTIFIER ::=  { display 1 } 
status-message                         OBJECT IDENTIFIER ::=  { display 2 } 
status-message1                        OBJECT IDENTIFIER ::=  { status-message 1 } 
id                                     OBJECT IDENTIFIER ::=  { system 3 } 
interface                              OBJECT IDENTIFIER ::=  { system 4 } 
simm                                   OBJECT IDENTIFIER ::=  { interface 1 } 
simm1                                  OBJECT IDENTIFIER ::=  { simm 1 } 
simm2                                  OBJECT IDENTIFIER ::=  { simm 2 } 
simm3                                  OBJECT IDENTIFIER ::=  { simm 3 } 
simm4                                  OBJECT IDENTIFIER ::=  { simm 4 } 
at                                     OBJECT IDENTIFIER ::=  { interface 2 } 
at1                                    OBJECT IDENTIFIER ::=  { at 1 } 
test                                   OBJECT IDENTIFIER ::=  { system 5 } 
job                                    OBJECT IDENTIFIER ::=  { system 6 } 
settings-job                           OBJECT IDENTIFIER ::=  { job 1 } 
file-system                            OBJECT IDENTIFIER ::=  { system 10 } 
file-systems                           OBJECT IDENTIFIER ::=  { file-system 3 } 
file-system1                           OBJECT IDENTIFIER ::=  { file-systems 1 } 
errorlog                               OBJECT IDENTIFIER ::=  { system 11 } 
error1                                 OBJECT IDENTIFIER ::=  { errorlog 1 } 
error2                                 OBJECT IDENTIFIER ::=  { errorlog 2 } 
error3                                 OBJECT IDENTIFIER ::=  { errorlog 3 } 
error4                                 OBJECT IDENTIFIER ::=  { errorlog 4 } 
error5                                 OBJECT IDENTIFIER ::=  { errorlog 5 } 
source-subsystem                       OBJECT IDENTIFIER ::=  { device 2 } 
io                                     OBJECT IDENTIFIER ::=  { source-subsystem 1 } 
settings-io                            OBJECT IDENTIFIER ::=  { io 1 } 
status-io                              OBJECT IDENTIFIER ::=  { io 2 } 
port1                                  OBJECT IDENTIFIER ::=  { io 3 } 
parallel                               OBJECT IDENTIFIER ::=  { port1 1 } 
processing-subsystem                   OBJECT IDENTIFIER ::=  { device 3 } 
pdl                                    OBJECT IDENTIFIER ::=  { processing-subsystem 3 } 
settings-pdl                           OBJECT IDENTIFIER ::=  { pdl 1 } 
status-pdl                             OBJECT IDENTIFIER ::=  { pdl 2 } 
pdl-pcl                                OBJECT IDENTIFIER ::=  { pdl 3 } 
pdl-postscript                         OBJECT IDENTIFIER ::=  { pdl 4 } 
pdl-esc-p                              OBJECT IDENTIFIER ::=  { pdl 5 } 
pjl                                    OBJECT IDENTIFIER ::=  { processing-subsystem 5 } 
destination-subsystem                  OBJECT IDENTIFIER ::=  { device 4 } 
print-engine                           OBJECT IDENTIFIER ::=  { destination-subsystem 1 } 
status-prt-eng                         OBJECT IDENTIFIER ::=  { print-engine 2 } 
intray                                 OBJECT IDENTIFIER ::=  { print-engine 3 } 
settings-intray                        OBJECT IDENTIFIER ::=  { intray 1 } 
status-intray                          OBJECT IDENTIFIER ::=  { intray 2 } 
intrays                                OBJECT IDENTIFIER ::=  { intray 3 } 
intray1                                OBJECT IDENTIFIER ::=  { intrays 1 } 
intray2                                OBJECT IDENTIFIER ::=  { intrays 2 } 
intray3                                OBJECT IDENTIFIER ::=  { intrays 3 } 
outbin                                 OBJECT IDENTIFIER ::=  { print-engine 4 } 
outbins                                OBJECT IDENTIFIER ::=  { outbin 3 } 
outbin1                                OBJECT IDENTIFIER ::=  { outbins 1 } 
marking-agent                          OBJECT IDENTIFIER ::=  { print-engine 5 } 
settings-marking-agent                 OBJECT IDENTIFIER ::=  { marking-agent 1 } 
imaging                                OBJECT IDENTIFIER ::=  { print-engine 6 } 


energy-star OBJECT-TYPE
    SYNTAX  INTEGER
    ACCESS  read-write
    STATUS  optional
    DESCRIPTION
                "Returns or changes the Energy Star sleep value.  If the
                value is greater than zero, then the device will go into
                energy saving sleep mode after the print engine has been
                idle for the number of seconds specified by this object.
                A value of zero means Energy Star is disabled and the
                device will not go to sleep based on print engine idle
                time.  The value must be non-negative.
                Additional information:
                Returns or changes the Energy Star sleep value.
                The device will go into energy saving sleep
                mode after the print engine has been idle for
                the number of seconds specified by this
                object. LaserJet 4V only supports values of 0, 900, 1800,
                3600, 7200, and 10800.  A value of 0 means
                never go to sleep based on print engine idle
                time.  Setting to an unsupported value causes 
              	the printer to substitute in a snapped value (listed
                			below) and to return <noError>
                			status.  
                			The snapped values are as follow:  
                			<=0 snap to 0  
                			>=1 and <=1349 snap to 900   
                			>=1350 and <=2699 snap to 1800  
                			>=2700 and <=5399 snap to 3600  
                			>=5400 and <=8999 snap to 7200  
                			>=9000 snap to 10800"
::= { settings-system 1 }
               
               
sleep-mode OBJECT-TYPE
    SYNTAX  INTEGER {
		   eFalse(1),
		   eTrue(2)
		   }
    ACCESS  read-write
    STATUS  optional
    DESCRIPTION
                "Returns eTrue if the device is in energy saving sleep
                mode, otherwise returns eFalse.  Setting SLEEP-MODE to
                eFalse causes the device to wake up, if it is in sleep
                mode.  Setting SLEEP-MODE to eTrue causes the device to
                go into sleep mode.
                Additional information:
                Setting to eTrue while printer is already in 
               	the Sleep Mode will not change the printer's
               	current state and should return <noError> status."
::= { settings-system 2 }
               
               
control-panel-lock OBJECT-TYPE
    SYNTAX  INTEGER {
		   eDisabled(1),
		   eEnabled(2)
		   }
    ACCESS  read-write
    STATUS  optional
    DESCRIPTION
                "Device control panel lock.  A value of eDisabled means
                the control panel is unlocked and the device's
                configuration can be modified from the control panel.  A
                value of eEnabled means the control panel is locked,
                thus the device's configuration cannot be modified from
                the control panel."
::= { settings-system 8 }
               
               
localization-language OBJECT-TYPE
    SYNTAX  INTEGER {
		   eEnglish(1),
		   eFrench(2),
		   eGerman(3),
		   eSpanish(4),
		   eItalian(5),
		   eSwedish(6),
		   eDanish(7),
		   eNorwegian(8),
		   eDutch(9),
		   eFinnish(10),
		   eJapanese(11),
		   ePortuguese(12),
		   ePolish(13),
		   eTurkish(14)
		   }
    ACCESS  read-only
    STATUS  optional
    DESCRIPTION
                "Localization language used by the device for device
                generated PML strings, control panel messages, and text
                contained in any of the printer generated printed pages.
                The order is the same order that is defined in MIO.
                Since the MIO values start at zero, one has been added
                to each value."
::= { status-system 1 }
               
               
not-ready-printer OBJECT-TYPE
    SYNTAX  OCTET STRING
    ACCESS  read-only
    STATUS  mandatory
    DESCRIPTION
                "Indicates if any of the sub-systems in the printer are
                not ready.  A sub-system is not ready if the sub-system
                is unable to perform its function until some sort of
                intervention occurs.  If there are no items in the NOT-
                READY-PRINTER collection (i.e. no bits are set), then
                all printer sub- systems are ready.  Each sub-system has
                a sub-system specific not ready object.  If a sub-system
                specific not ready object contains any items, then the
                associated item will be in the NOT-READY collection."
::= { status-system 2 }
               
               
not-ready-controller OBJECT-TYPE
    SYNTAX  OCTET STRING
    ACCESS  read-only
    STATUS  optional
    DESCRIPTION
                "Indicates if the hardware controller sub-system in the
                device is not ready.  If there are no items in the
                collection (i.e. no bits are set), then the hardware
                controller sub-system is ready.  If there is an item
                present, then the item indicates what is causing the
                hardware controller sub-system to be not ready.  If the
                cControllerFailure item is in the collection, then a
                hardware error was detected on the main controller PC
                board, sometimes called the formatter or the logic
                broad.  Example controller hardware errors include DRAM
                controller failure, clock failure, memory parity error,
                and ROM CRC error.  The cFirmwareFailure item is in the
                collection if a firmware/software error was detected.
                Device specific detailed error information can be
                retrieved from the error log objects, if the device
                supports those objects.  The POS will list which device
                failures cause each item to be included in the
                collection.
                Additional information:
                A controller failure occurrence will set the 
               	cControllerFailure bit (bit 1). The controller 
               	failures are: 62.X Service, 63 Service, 65 Service,
               	67 Service, 68 Service, and 68 Error.  
               	A SIMM failure occurrence will set the cSIMMFailure
               	bit (bit 2).  The SIMM failures are 61.X Service,
               	53-XY-ZZ Error, and 72 Service.  
               	A DISK failure occurrence will set the cATFailure 
               	bit (bit 3).  The DISK failure is FS DISK FAILURE."
::= { status-system 3 }
               
               
not-idle OBJECT-TYPE
    SYNTAX  OCTET STRING
    ACCESS  read-only
    STATUS  optional
    DESCRIPTION
                "Indicates if any of the sub-systems in the device are
                not idle.  The I/O source sub-system is considered not
                idle if there is unprocessed PDL data in the device.
                The PDL processing sub-system is considered not idle if
                the device is processing a print job.  The print engine
                destination sub-system is considered not idle if media
                is moving (i.e. the device is printing).  [other text
                here describing what causes the other sub-systems to be
                considered not idle]."
::= { status-system 4 }
               
               
on-off-line OBJECT-TYPE
    SYNTAX  INTEGER {
		   eOnline(1),
		   eOffline(2),
		   eOfflineAtEndOfJob(3)
		   }
    ACCESS  read-write
    STATUS  optional
    DESCRIPTION
                "To bring the PDL processing sub-system on or off line.
                If the device is a printer, then the printer does not
                process print job data when the printer is off line.
                PML communication persists.
                Additional information:
                Setting to eOnline while the printer's current 
          	state is Online will not change the current state 
               	and should return <noError> status.  
               	Setting to eOffline while printer's current state is
               	Offline will not change the current state and should
               	return <noError> status.  
               	Setting to eOfflineAtEndOfJob when not in a job and
               	the current state is Online will cause the printer to 
               	change to the Offline state immediately."
::= { status-system 5 }
               
               
continue OBJECT-TYPE
    SYNTAX  INTEGER {
		   eTrue(1)
		   }
    ACCESS  write-only
    STATUS  optional
    DESCRIPTION
                "A device can support a class of errors called
                continuable errors.  When a continuable error is
                encountered, the device requires a continue event to
                occur before the device will continue operation.  One
                continue event is setting the CONTINUE object to eTrue.
                Devices can support other continue events, like auto-
                continue.  A continue event causes the continuable error
                to be acknowledged, thus allowing the device to
                continue.  Each device needs to list the continuable
                errors.  If the device doesn't currently have an
                unacknowledged continuable error, the response will
                contain <genErr>.
                Additional information:
                LaserJet 4V supports a class of errors called
                continuable errors.  When a continuable error is
                encountered, LaserJet 4V requires a continue event to
                occur before it will continue operation.  One 
                continue event is setting the CONTINUE object to 
                eTrue.  Devices can support other continue events, 
                like auto-continue.  A continue event causes the 
                continuable error to be acknowledged, thus allowing 
                LaserJet 4V to continue.  If LaserJet 4V doesn't currently 
                have an unacknowledged continuable error, the 
                response will contain <noError> status.  The following is 
                a list of continuable errors in LaserJet 4V:  
                
                NOT-READY-DESTINATION-PRINT-ENGINE cMarkingAgentOut  
                NOT-READY-DESTINATION-PRINT-ENGINE cManualFeedMedia  
                NOT-READY-DESTINATION-PRINT-ENGINE cRequestedMediaUnavailable  
                NOT-READY-PROCESSING-PDL           cSoftResourceMemoryOverflow  
                NOT-READY-PROCESSING-PDL           cPrintDataMemoryOverflow  
                NOT-READY-SOURCE-IO                cDataError  
                NOT-READY-SOURCE-IO                cDataOverrun  
                NOT-READY-SOURCE-IO                cAbnormalConnectionClose  
                NOT-READY-LASER-PRINT-ENGINE       cPrintOverrun  
                SIMMx-TYPE                         eUnknown  
                SIMMx-TYPE                         eUnSupported  
                NOT-READY-CONTROLLER               cATFailure"
::= { status-system 6 }
               
               
auto-continue OBJECT-TYPE
    SYNTAX  INTEGER {
		   eOff(1),
		   eOn(2)
		   }
    ACCESS  read-write
    STATUS  optional
    DESCRIPTION
                "Indicates if the device will automatically continue
                after encountering a continuable error.  If AUTO-
                CONTINUE is set to eOn, the device will automatically
                generate continue event to acknowledge continuable
                errors.  If AUTO-CONTINUE is set to eOff, then some
                other continue event will have to acknowledge the
                continuable error."
::= { status-system 7 }
               
               
user-nvram-reset OBJECT-TYPE
    SYNTAX  INTEGER {
		   eTrue(1)
		   }
    ACCESS  write-only
    STATUS  optional
    DESCRIPTION
                "Setting to eTrue causes all user NVRAM settings to
                factory default settings.  May also perform POWER-ON-
                RESET functionality thus loosing print job data.  The
                POS will list which objects are effected by a user NVRAM
                reset.  Some items are NVRAM settings, but not user
                controllable, so this action may not cause all of NVRAM
                to be reset.  Some examples of NVRAM settings that may
                not be affected are page count, internally used pen
                information, line configuration information, etc.
                Additional information:
                Setting to eTrue returns the NVRAM items listed
           	below to their factory default values.  Performs
                the same function as the 'MENU RESET' function
                supported by the control panel except when printer
               	is in Offline state, setting this OID to eTrue will
               	not take the printer to the Online state.  
                DEFAULT-COPIES  
                DEFAULT-MEDIA-SIZE  
                DEFAULT-ORIENTATION  
                DEFAULT-LINES-PER-PAGE  
                DEFAULT-MANUAL-FEED  
                DEFAULT-RET  
                DEFAULT-PRINT-QUALITY  
                PCL-DEFAULT-FONT-SOURCE  
                PCL-DEFAULT-FONT-NUMBER  
                PCL-DEFAULT-FONT-HEIGHT  
                PCL-DEFAULT-FONT-WIDTH  
                PCL-DEFAULT-SYMBOL-SET  
                DEFAULT-VERTICAL-BLACK-RESOLUTION  
                DEFAULT-HORIZONTAL-BLACK-RESOLUTION  
                DEFAULT-PDL  
                CONTEXT-SENSITIVE-PDL-SELECTION  
                ENERGY-STAR  
                IO-TIMEOUT  
                DEFAULT-PAGE-PROTECT  
                POSTSCRIPT-JAM-RECOVERY (PostScript installed)  
               	POSTSCRIPT-PRINT-ERRORS (PostScript installed)"
::= { status-system 12 }
               
               
display-column-size OBJECT-TYPE
    SYNTAX  INTEGER
    ACCESS  read-only
    STATUS  optional
    DESCRIPTION
                "Indicates the number of characters displayable on each
                row of the printer's display."
::= { display-status 1 }
               
               
display-number-of-rows OBJECT-TYPE
    SYNTAX  INTEGER
    ACCESS  read-only
    STATUS  optional
    DESCRIPTION
                "Indicates the number of rows displayable on the
                printer's display."
::= { display-status 2 }
               
               
status-msg-line1-part1 OBJECT-TYPE
    SYNTAX  DisplayString 
    ACCESS  read-only
    STATUS  optional
    DESCRIPTION
                "First part of the first line of the printer's status
                message.
                Additional information:
                In the Offline state, device only returns 
               	00 OFFLINE and not the actual content of control panel
                display." 
::= { status-message1 1 }
               
               
total-ram-size OBJECT-TYPE
    SYNTAX  INTEGER
    ACCESS  read-only
    STATUS  optional
    DESCRIPTION
                "Identifies total amount of RAM, in bytes, available to
                the controller for general computing."
::= { status-system 21 }
               
               
status-printer OBJECT-TYPE
    SYNTAX  OCTET STRING
    ACCESS  read-only
    STATUS  mandatory
    DESCRIPTION
                "Indicates if any of the sub-systems in the device in a
                warning condition.  A warning condition exists if the
                sub-system is useable, but not at its highest state of
                functionality."
::= { status-system 22 }
               
               
status-controller OBJECT-TYPE
    SYNTAX  OCTET STRING
    ACCESS  read-only
    STATUS  optional
    DESCRIPTION
                "Indicates if the hardware controller sub-system in a
                warning condition."
::= { status-system 23 }
               
               
model-number OBJECT-TYPE
    SYNTAX  DisplayString
    ACCESS  read-only
    STATUS  optional
    DESCRIPTION
                "Identifies the device model number as listed in the HP
                corporate price list (e.g.  C2121A for DeskJet 500C).
                The string is as specific as possible.  Products should
                note in POS if the model number on the CPL changes but
                the device reports the previous model number.  If the
                model number changes based on the installed options, the
                POS should indicate if only the base model number is
                returned, or if the device senses the installed options
                and returns the correct model number.  If possible,
                encode the model number in a symbol set (like Roman-8)
                that matches the ASCII character set and limit the
                characters used to ASCII characters.
                Additional information:
                The string is as specific as possible.  The 
                CPL model number will change for an LaserJet 4V when it
            	is configured as a Dune but only the base product 
               	model number is reported.  If possible, encode the
               	model number in a symbol set (like Roman-8) that 
               	matches the ASCII character set and limit the 
               	characters used to ASCII characters."
::= { id 1 }
               
               
model-name OBJECT-TYPE
    SYNTAX  DisplayString 
    ACCESS  read-only
    STATUS  mandatory
    DESCRIPTION
                "Identifies the device model name (e.g.  ``DeskJet
                1200C'').  The string is as specific as possible.
                Capitalization and spacing should match family naming
                conventions.  Products should note in POS if the model
                name on the HP corporate price list changes but the
                device reports the previous device name.  If the model
                name changes based on the installed options, the POS
                should indicate if only the base model name is returned,
                or if the device senses the installed options and
                returns the correct model name.  If possible, encode the
                model name in a symbol set (like Roman-8) that matches
                the ASCII character set and limit the characters used to
                ASCII characters.
                Additional information:
                Even though the name of the Dune product 
                changes to LaserJet 4MV, LaserJet 4V will only report
               	the base product name LaserJet 4V.  If possible,
               	encode the model name in a symbol set (like Roman-8)
               	that matches the ASCII character set and limit the
               	characters used to ASCII characters."
::= { id 2 }
               
               
serial-number OBJECT-TYPE
    SYNTAX  DisplayString 
    ACCESS  read-only
    STATUS  optional
    DESCRIPTION
                "Identifies the serial number for the device.  If the
                SERIAL-NUMBER object is set by the user, then setting
                the object does not need to be protected.  If the
                SERIAL-NUMBER object is set at the factory, then the
                SERVICE-PASSWORD object must be set correctly before the
                SERIAL-NUMBER object is writable.  If this is a writable
                object, the POS should indicate the maximum supported
                string length.  If possible, encode the serial number in
                a symbol set (like Roman-8) that matches the ASCII
                character set and limit the characters used to ASCII
                characters."
::= { id 3 }
               
               
fw-rom-datecode OBJECT-TYPE
    SYNTAX  DisplayString 
    ACCESS  read-only
    STATUS  optional
    DESCRIPTION
                "Identifies the base system firmware date code.  The date
                code will be encoded in the yyyymmdd format.  There may
                be several versions of the base system firmware.  The
                date code associated with the version of the base system
                firmware that is being used is reported.  There may be
                other date code objects for other specific modules such
                as fonts, localization modules, etc.  ; these other
                datecode objects are device specific."
::= { id 5 }
               
               
device-name OBJECT-TYPE
    SYNTAX  DisplayString 
    ACCESS  read-write
    STATUS  optional
    DESCRIPTION
                "User defined device name.  The POS should indicate the
                maximum supported string length.  If the user entered
                string is too long, the device will store as much as
                possible and will return the <noError>.
                Additional information:
                The maximum supported string length is 32 
                characters.  If the user entered string is too long,
             	the device will store as much as possible and will
               	return the <noError> status."
::= { id 10 }
               
               
device-location OBJECT-TYPE
    SYNTAX  DisplayString
    ACCESS  read-write
    STATUS  optional
    DESCRIPTION
                "User defined device location.  The POS should indicate
                the maximum supported string length.  If the user
                entered string is too long, the device will store as
                much as possible and will return the <noError>.
                Additional information:
                The maximum supported string length is 16
               	characters.  If the user entered string is too long,
                the device will store as much as possible and will
               	return the <noError> status."
::= { id 11 }
               
               
asset-number OBJECT-TYPE
    SYNTAX  DisplayString 
    ACCESS  read-write
    STATUS  optional
    DESCRIPTION
                "User defined asset number.  The POS should indicate the
                maximum supported string length.  If the user entered
                string is too long, the device will store as much as
                possible and will return the <noError>.
                Additional information:
                The maximum supported string length is 8
                characters.  If the user entered string is too long,
               	the device will store as much as possible and will 
               	return the <noError> status."
::= { id 12 }
               
               
system-contact OBJECT-TYPE
    SYNTAX  DisplayString
    ACCESS  read-write
    STATUS  optional
    DESCRIPTION
                "User defined string containing the name of the person or
                group that is responsible for the device.  The POS
                should indicate the maximum supported string length.  If
                the user entered string is too long, the device will
                store as much as possible and will return the
                <noError>.
                Additional information:
                User defined system contact.  The maximum
                supported string length is 16 characters.  If the user
                entered string is too long, the device will store as
                much as possible and will return the
                <noError> status."
::= { id 13 }
               
               
simm1-type OBJECT-TYPE
    SYNTAX  INTEGER {
		   eEmpty(1),
		   eUnknown(2),
		   eUnSupported(3),
		   eReadOnlyMemory(4),
		   eVolatileRandomAccessMemory(5)
		   }
    ACCESS  read-only
    STATUS  optional
    DESCRIPTION
                "Returns an indication of the type of option installed in
                SIMM slot 1.  eEmpty means the device did not detect any
                option installed in the interface slot.  eUnknown means
                the device doesn't recognize the installed option.
                eUnSupported means the device recognizes the installed
                option, but does not support the option.
                eReadOnlyMemory means the installed option contains ROM
                ICs.  eVolatileRandomAccessMemory means the installed
                option contains RAM ICs that loose data when the power
                is turned off.  eNonVolatileRandomAccessMemory means
                that the installed option contains RAM ICs that do not
                loose data when the power is turned off.  eFlashMemory
                means that the installed option contains a type of non-
                volatile RAM that needs to be erased before it can be
                written.  eDiskDrive means the installed option contains
                a disk drive.  eRamRom means the installed option
                contains both volatile random access memory and read
                only memory.  eInputPHD means the installed option is an
                input paper handling device.  eOutputPHD means the
                installed option is an output paper handling device."
::= { simm1 4 }
               
               
simm1-capacity OBJECT-TYPE
    SYNTAX  INTEGER
    ACCESS  read-only
    STATUS  optional
    DESCRIPTION
                "Returns an indication of the capacity of the SIMM
                installed in SIMM slot 1.  The capacity is dependent on
                the type of option, as indicated by the SIMM1-TYPE
                object.  This object has no meaning if the installed
                option type is eUnknown or eReadOnlyMemory.  This object
                contains the size, in bytes, if the installed option
                type is eVolatileRandomAccessMemory,
                eNonVolatileRandomAccessMemory, eFlashMemory, or
                eDiskDrive.  If the type of the installed option is
                eRamRom, this object contains the size, in bytes, of the
                random access memory.  If the type of the installed
                option is eInputPHD, the capacity indicates the number
                of input trays supported by the installed option.  If
                the type of the installed option is eOutputPHD, the
                capacity indicates the number of output bins supported
                by the installed option.
                Additional information:
                Returns an indication of the capacity of the
                installed option in bytes.  This object is not
                supported unless the SIMM1-TYPE type is
                eVolatileRandomAccessMemory."
::= { simm1 5 }
               
               
simm2-type OBJECT-TYPE
    SYNTAX  INTEGER {
		   eEmpty(1),
		   eUnknown(2),
		   eUnSupported(3),
		   eReadOnlyMemory(4),
		   eVolatileRandomAccessMemory(5)
		   }
    ACCESS  read-only
    STATUS  optional
    DESCRIPTION
                "Returns an indication of the type of option installed in
                SIMM slot 2.  See SIMM1-TYPE for a description."
::= { simm2 4 }
               
               
simm2-capacity OBJECT-TYPE
    SYNTAX  INTEGER
    ACCESS  read-only
    STATUS  optional
    DESCRIPTION
                "Returns an indication of the capacity of the SIMM
                installed in SIMM slot 2.  See SIMM1-CAPACITY for a
                description.
                Additional information:
                Returns an indication of the capacity of the
                installed option in bytes.  This object is not
                supported unless the SIMM2-TYPE type is
                eVolatileRandomAccessMemory."
::= { simm2 5 }
               
               
simm3-type OBJECT-TYPE
    SYNTAX  INTEGER {
		   eEmpty(1),
		   eUnknown(2),
		   eUnSupported(3),
		   eReadOnlyMemory(4),
		   eVolatileRandomAccessMemory(5)
		   }
    ACCESS  read-only
    STATUS  optional
    DESCRIPTION
                "Returns an indication of the type of option installed in
                SIMM slot 3.  See SIMM1-TYPE for a description."
::= { simm3 4 }
               
               
simm3-capacity OBJECT-TYPE
    SYNTAX  INTEGER
    ACCESS  read-only
    STATUS  optional
    DESCRIPTION
                "Returns an indication of the capacity of the SIMM
                installed in SIMM slot 3.  See SIMM1-CAPACITY for a
                description.
                Additional information:
                Returns an indication of the capacity of the
                installed option in bytes.  This object is not
                supported unless the SIMM3-TYPE type is
                eVolatileRandomAccessMemory."
::= { simm3 5 }
               
               
simm4-type OBJECT-TYPE
    SYNTAX  INTEGER {
		   eEmpty(1),
		   eUnknown(2),
		   eUnSupported(3),
		   eReadOnlyMemory(4),
		   eVolatileRandomAccessMemory(5)
		   }
    ACCESS  read-only
    STATUS  optional
    DESCRIPTION
                "Returns an indication of the type of option installed in
                SIMM slot 4.  See SIMM1-TYPE for a description."
::= { simm4 4 }
               
               
simm4-capacity OBJECT-TYPE
    SYNTAX  INTEGER
    ACCESS  read-only
    STATUS  optional
    DESCRIPTION
                "Returns an indication of the capacity of the SIMM
                installed in SIMM slot 4.  See SIMM1-CAPACITY for a
                description.
                Additional information:
                Returns an indication of the capacity of the
                installed option in bytes.  This object is not
                supported unless the SIMM4-TYPE type is
                eVolatileRandomAccessMemory."
::= { simm4 5 }
               
               
at1-model-number OBJECT-TYPE
    SYNTAX  DisplayString 
    ACCESS  read-only
    STATUS  optional
    DESCRIPTION
                "Identifies the AT model number.  If the disk was
                manufactured by HP, then the model number is the one
                listed in the HP corporate price list.  If possible,
                encode the model number in a symbol set (like Roman-8)
                that matches the ASCII character set and limit the
                characters used to ASCII characters.
                Additional information:
                The model number is obtained from the disk
                using the IDE (Intelligent Drive Electronics) 
               	Identify command.  This objects is only supported
               	if a disk is installed.  Returns 
               	<noSuchName> status if attempting
               	to perform a Get on this OID with no disk installed.
               	Returns <noSuchName> 
               	status if attempting to perform a Set, EnableTrap, or
               	DisableTrap on this OID with no disk installed."
::= { at1 1 }
               
               
at1-model-name OBJECT-TYPE
    SYNTAX  DisplayString
    ACCESS  read-only
    STATUS  optional
    DESCRIPTION
                "Returns product information identifying the AT storage
                device.  Example: C3014A
                Additional information:
                The product information is obtained from the
               	disk using the IDE (Intelligent Drive Electronics)
               	Identify command.  This objects is only supported
               	if a disk is installed.  Returns 
               	<noSuchName> status if attempting
               	to perform a Get on this OID with no disk installed.
               	Returns <noSuchName> 
                status if attempting to perform a Set, EnableTrap, or
               	DisableTrap on this OID with no disk installed."
::= { at1 2 }
               
               
at1-manufacturing-info OBJECT-TYPE
    SYNTAX  DisplayString
    ACCESS  read-only
    STATUS  optional
    DESCRIPTION
                "Returns information describing the manufacture of this
                particular AT.  May include serial number and firmware
                revision.
                Additional information:
                Returns the model number, serial number, and
              	firmware revision of the installed disk.  This
                information is obtained from the disk using the
                IDE (Intelligent Drive Electronics) Identify
                command.  Example:  HP C3014A JP932412W9 K2A4A059.
               	This objects is only supported if a disk is installed.
               	Returns <noSuchName> status if
               	attempting to perform a Get on this OID with no disk 
                installed.
               	Returns <noSuchName> 
               	status if attempting to perform a Set, EnableTrap, or
               	DisableTrap on this OID with no disk installed."
::= { at1 3 }
               
               
at1-type OBJECT-TYPE
    SYNTAX  INTEGER {
		   eEmpty(1),
		   eDiskDrive(8)
		   }
    ACCESS  read-only
    STATUS  optional
    DESCRIPTION
                "Returns an indication of the type of option installed in
                this particular AT interface.  See SIMM1-TYPE for an
                explanation of the enumerations.
                Additional information:
                eEmpty means the device did not detect any AT.
                eDiskDrive means the AT contains a disk drive."
::= { at1 4 }
               
               
at1-capacity OBJECT-TYPE
    SYNTAX  INTEGER
    ACCESS  read-only
    STATUS  optional
    DESCRIPTION
                "Returns an indication of the capacity of the installed
                option.  See SIMM1-CAPACITY for an explanation of the
                meaning of the value of this object.
                Additional information:
                This object contains the size, in bytes, of 
               	the installed disk option.  This objects is only 
               	supported if a disk is installed.
               	Returns <noSuchName> status if
               	attempting to perform a Get on this OID with no disk 
               	installed.
               	Returns <noSuchName> 
               	status if attempting to perform a Set, EnableTrap, or
               	DisableTrap on this OID with no disk installed."
::= { at1 5 }
               
               
self-test OBJECT-TYPE
    SYNTAX  INTEGER {
		   eNotInASelfTest(1),
		   eDestructiveSelfTest(3)
		   }
    ACCESS  read-write
    STATUS  optional
    DESCRIPTION
                "Writing this object allows a device self test to be
                started.  Reading this object provides an indication
                what self-test is currently executing, if any.  Actual
                self-test operation is device specific.  A self test may
                not be allowed at any arbitrary time.  If the device
                supports the requested self test, but can not start the
                execution of the self test when requested, the device
                will respond with <genErr>.  If a non-destructive 
                self test is being started, the device
                will generate a response before the self test is
                completed.
                RECOMMENDATION:  If the device is ready (i.e. the NOT-
                READY object does not contain any items, except maybe
                being off-line) and is idle (i.e. the NOT-IDLE object
                does not contain any items), this request should always
                succeed.  This provides a mechanism for driver writers
                to always determine if the action will succeed or not.
                Additional information:
                After the self-test is complete a 
               	configuration page will be printed.  This is the
                recommended way to cause a configuration page to be
                printed.  A continuous self test cannot be started
                or terminated using this OID.  A self test is not be 
                allowed at any arbitrary time.  If the requested self 
                test cannot be started LaserJet 4V will respond with 
                <genErr> status.  No response will be generated 
                because of the destructive nature of
                this test.  Can only be started if LaserJet 4V is ready
                (except for being offline), offline, and idle.  If 
                LaserJet 4V is ready (i.e. the NOT-READY object does 
                not contain any items, except for being off-line), 
                is offline, and is idle (i.e. the NOT-IDLE object 
                does not contain any items), this request should 
                always succeed.  This provides a mechanism for driver 
                writers to always determine if the action will 
                succeed or not."
::= { test 1 }
               
               
print-internal-page OBJECT-TYPE
    SYNTAX  INTEGER {
		   eNotPrintingAPage(1),
		   ePrintingAnUnknownInternalPage(2),
		   ePCLDemoPage2(301),
		   ePCLFontList1(350),
		   ePostScriptDemoPage1-ConfigurationPage(400),
		   ePostScriptDemoPage2(401),
		   ePostScriptFontList1(450)
		   }
    ACCESS  read-write
    STATUS  optional
    DESCRIPTION
                "Writing this object to a value other than
                eNotPrintingAnInternalPage causes the device to attempt
                to print an internally generated page.  Reading this
                object provides an indication what internally generated
                page is currently being printed, if any.  The actual
                page is device specific.  Some devices may support
                continuously printing an internally generated page.
                Setting this object to eNotPrintingAnInternalPage
                terminates continuously printing internally generated
                pages.  An internally generated page may not be allowed
                to be printed at any arbitrary time; under what
                conditions it will succeed or fail is device specific.
                If the device supports the requested page, but can not
                start printing the page when requested, the device will
                respond with <genErr>.
                RECOMMENDATION:  If the device is ready (i.e. the NOT-
                READY object does not contain any items, except maybe
                being off-line) and is idle (i.e. the NOT-IDLE object
                does not contain any items), this request should always
                succeed.  This provides a mechanism for driver writers
                to always determine if the action will succeed or not.
                Additional information:
                ePCLDemoPage1-ConfigurationPage (the PCL
                test page) is not supported.  The PCL
                configuration page is generated by using
                the SELF-TEST OID above.  ePCLDemoPage2
                is the PCL Demo page, and ePCLFontList1
                is the PCL typeface list.
                ePostScriptDemoPage1-ConfigurationPage is
                the PostScript configuration page.  The
                ePostScriptDemoPage2 is the same PostScript demo
                page that can be printed via the control
                panel.  ePostScriptFontList1 is the
                PostScript typeface list.  LaserJet 4V does
                not support continuously printing a demo
                page.  A page is not allowed at any
                arbitrary time.  LaserJet 4V must be ready
                (except for being offline), offline, and idle
                before a page can be printed. If the
                requested page cannot start printing when
                requested, LaserJet 4V will respond with
                <genErr> status.  IfLaserJet 4V is ready (i.e. the NOT-READY
                object does not contain any items, except
                being off-line). offline, and is idle (i.e. the
                NOT-IDLE object does not contain any
                items), this request should always
                succeed.  This provides a mechanism for
                driver writers to always determine if the
                action will succeed or not.
                When PostScript option is not installed, LaserJet 4V will
                respond with <genErr> status for any attempt to write this object to 
               	ePostScriptDemoPage1-ConfigurationPage,
               	ePostScriptDemoPage2, and ePostScriptFontList1."
::= { test 2 }
               
               
clearable-warning OBJECT-TYPE
    SYNTAX  INTEGER {
		   eOn(2),
		   eJob(3)
		   }
    ACCESS  read-only
    STATUS  optional
    DESCRIPTION
                "Returns or controls how the device will track clearable
                warnings.  A clearable warning indicates a transient
                event in the device.  The device will continue after the
                transient event occurs.  If CLEARABLE-WARNING is eOff,
                the device does not track clearable warnings.  If
                CLEARABLE-WARNING is eOn, all clearable warnings will be
                tracked until cleared (acknowledged).  If CLEARABLE-
                WARNING is eJob, a clearable warning generated due to an
                event that occurs because of the print job being
                processed will be automatically cleared when the device
                has finished processing the job.  Example clearable
                warning events include the device altering resolution or
                page protection due to memory constraints.  The POS will
                document what transient events are treated as clearable
                warnings.
                Additional information:
                Returns information on how the device will track
                clearable warnings.  A clearable warning indicates a
                transient event in the device.  The device will
                continue after the transient event occurs.  If
                CLEARABLE-WARNING is eOn, all clearable warnings
                will be tracked until cleared (acknowledged).  If
                CLEARABLE-WARNING is eJob, a clearable warning
                generated due to an event that occurs because of the
                print job being processed will be automatically cleared
                when the device has finished processing the job.
                Example clearable warning events include the device
                altering resolution or page protection due to memory
                constraints. " 
::= { settings-job 1 }
               
               
file-system1-initialized OBJECT-TYPE
    SYNTAX  INTEGER {
		   eFalse(1),
		   eTrue(2)
		   }
    ACCESS  read-only
    STATUS  optional
    DESCRIPTION
                "Returns eTrue if a file system has been written to the
                mass storage device(s) which will hold file data
                contained in this file system.  Returns eFalse
                otherwise.  Each POS needs to specify the relationship
                between file systems and the physical storage devices
                that can hold the data contained in those file systems.
                Additional information:
                This objects is only supported if a disk is 
                installed.  
                Returns <noSuchName> status if
               	attempting to perform a Get on this OID with no disk 
               	installed.
               	Returns <noSuchName> 
               	status if attempting to perform a Set, EnableTrap, or
               	DisableTrap on this OID with no disk installed."
::= { file-system1 1 }
               
               
file-system1-capacity OBJECT-TYPE
    SYNTAX  INTEGER
    ACCESS  read-only
    STATUS  optional
    DESCRIPTION
                "Returns the total size, in bytes, of the mass storage
                space configured to hold the file data (and file system
                information) assoicated with files stored in this file
                system.  This refers to hardware capacity, independent
                of any space consumed by the file system overhead or
                user files.
                Additional information:
                This objects is only supported if a disk is
               	installed.  
               	Returns <noSuchName> status if
               	attempting to perform a Get on this OID with no disk 
               	installed.
               	Returns <noSuchName> 
               	status if attempting to perform a Set, EnableTrap, or
               	DisableTrap on this OID with no disk installed."
::= { file-system1 2 }
               
               
file-system1-free-space OBJECT-TYPE
    SYNTAX  INTEGER
    ACCESS  read-only
    STATUS  optional
    DESCRIPTION
                "Returns the total amount, in bytes, of unused storage
                space currently available to this file system.
                Additional information:
                This objects is only supported if a disk is
               	installed.  
               	Returns <noSuchName> status if
               	attempting to perform a Get on this OID with no disk 
               	installed.
               	Returns <noSuchName> 
               	status if attempting to perform a Set, EnableTrap, or
               	DisableTrap on this OID with no disk installed."
::= { file-system1 3 }
               
               
file-system1-write-protect OBJECT-TYPE
    SYNTAX  INTEGER {
		   eDisabled(1),
		   eEnabled(2)
		   }
    ACCESS  read-write
    STATUS  optional
    DESCRIPTION
                "Supports write-protecting the file system.  Setting
                FILE-SYSTEM-WRITE-PROTECT to eEnabled blocks any
                modification of the contents of the file system.
                Setting FILE-SYSTEM-WRITE-PROTECT to eDisabled allows
                modification of the contents of the file system.
                Additional information:
                This objects is only supported if a disk is
               	installed.
               	Returns <noSuchName> status if
               	attempting to perform a Get, or Set on this OID 
               	with no disk installed.
               	Returns <noSuchName> 
               	status if attempting to perform an EnableTrap, or
               	DisableTrap on this OID with no disk installed."
::= { file-system1 4 }
               
               
error1-time-stamp OBJECT-TYPE
    SYNTAX  INTEGER
    ACCESS  read-only
    STATUS  optional
    DESCRIPTION
                "Contains some sort of time stamp indicating when error 1
                occurred.  Example time stamps include the actual time
                the error occurred (in seconds since Jan. 1, 1970), and
                the total engine page count.  The device POS documents
                the meaning of the time stamp.
                Additional information:
                Contains a time stamp indicating when error 1 
                occurred.  In LaserJet 4V this item contains the engine 
                page count when the error occurred."
::= { error1 1 }
               
               
error1-code OBJECT-TYPE
    SYNTAX  INTEGER
    ACCESS  read-only
    STATUS  optional
    DESCRIPTION
                "Contains a device specific error code.  Each device POS
                should list what errors are logged to the error log and
                the meaning of each supported error code value.
                Additional information:
                Contains a device specific error code."
::= { error1 2 }
               
               
error2-time-stamp OBJECT-TYPE
    SYNTAX  INTEGER
    ACCESS  read-only
    STATUS  optional
    DESCRIPTION
                "Contains some sort of time stamp indicating when error 2
                occurred.  Example time stamps include the actual time
                the error occurred (in seconds since Jan. 1, 1970), and
                the total engine page count.  The device POS documents
                the meaning of the time stamp.
                Additional information:
                Contains a time stamp indicating when error 2
                occurred.  In LaserJet 4V this item contains the engine
                page count when the error occurred."
::= { error2 1 }
               
               
error2-code OBJECT-TYPE
    SYNTAX  INTEGER
    ACCESS  read-only
    STATUS  optional
    DESCRIPTION
                "Contains a device specific error code.  Each device POS
                should list what errors are logged to the error log and
                the meaning of each supported error code value.
                Additional information:
                Same as ERROR1-CODE."
::= { error2 2 }
               
               
error3-time-stamp OBJECT-TYPE
    SYNTAX  INTEGER
    ACCESS  read-only
    STATUS  optional
    DESCRIPTION
                "Contains some sort of time stamp indicating when error 3
                occurred.  Example time stamps include the actual time
                the error occurred (in seconds since Jan. 1, 1970), and
                the total engine page count.  The device POS documents
                the meaning of the time stamp.
                Additional information:
                Contains a time stamp indicating when error 3
                occurred.  In LaserJet 4V this item contains the engine
                page count when the error occurred."
::= { error3 1 }
               
               
error3-code OBJECT-TYPE
    SYNTAX  INTEGER
    ACCESS  read-only
    STATUS  optional
    DESCRIPTION
                "Contains a device specific error code.  Each device POS
                should list what errors are logged to the error log and
                the meaning of each supported error code value.
                Additional information:
                Same as ERROR1-CODE."
::= { error3 2 }
               
               
error4-time-stamp OBJECT-TYPE
    SYNTAX  INTEGER
    ACCESS  read-only
    STATUS  optional
    DESCRIPTION
                "Contains some sort of time stamp indicating when error 4
                occurred.  Example time stamps include the actual time
                the error occurred (in seconds since Jan. 1, 1970), and
                the total engine page count.  The device POS documents
                the meaning of the time stamp.
                Additional information:
                Contains a time stamp indicating when error 4
                occurred.  In LaserJet 4V this item contains the engine
                page count when the error occurred."
::= { error4 1 }
               
               
error4-code OBJECT-TYPE
    SYNTAX  INTEGER
    ACCESS  read-only
    STATUS  optional
    DESCRIPTION
                "Contains a device specific error code.  Each device POS
                should list what errors are logged to the error log and
                the meaning of each supported error code value.
                Additional information:
                Same as ERROR1-CODE."
::= { error4 2 }
               
               
error5-time-stamp OBJECT-TYPE
    SYNTAX  INTEGER
    ACCESS  read-only
    STATUS  optional
    DESCRIPTION
                "Contains some sort of time stamp indicating when error 5
                occurred.  Example time stamps include the actual time
                the error occurred (in seconds since Jan. 1, 1970), and
                the total engine page count.  The device POS documents
                the meaning of the time stamp.
                Additional information:
                Contains a time stamp indicating when error 5
                occurred.  In LaserJet 4V this item contains the engine
                page count when the error occurred."
::= { error5 1 }
               
               
error5-code OBJECT-TYPE
    SYNTAX  INTEGER
    ACCESS  read-only
    STATUS  optional
    DESCRIPTION
                "Contains a device specific error code.  Each device POS
                should list what errors are logged to the error log and
                the meaning of each supported error code value.
                Additional information:
                Same as ERROR1-CODE."
::= { error5 2 }
               
               
io-timeout OBJECT-TYPE
    SYNTAX  INTEGER
    ACCESS  read-write
    STATUS  optional
    DESCRIPTION
                "The amount of time, in seconds, to wait for more print
                job data to be received before an I/O timeout occurs.
                The I/O channel being timed is the I/O channel that
                received the data associated with the current print job.
                If an I/O timeout occurs, the PDL processing sub-system
                assumes all the data associated with the current print
                job has been received, and processes the end of job in
                an PDL specific manner.  The POS specifies the supported
                values.
                Additional information:
                The amount of time, in seconds, to wait
                for more print job data to be received before an I/O
                timeout occurs.  The I/O channel being timed is the I/O
                channel that received the data associated with the
                current print job.  If an I/O timeout occurs, the PDL
                processing sub-system assumes all the data associated
                with the current print job has been received, and
                processes the end of job in an PDL specific manner.
                In LaserJet 4V the supported values are 5 to 300 seconds.
                Setting to a value outside the supported range returns
                			<badValue> status."
::= { settings-io 1 }
               
               
io-switch OBJECT-TYPE
    SYNTAX  INTEGER {
		   eYes(1)
		   }
    ACCESS  read-only
    STATUS  optional
    DESCRIPTION
                "Indicates if the device will switch between I/O channels
                when a job boundary is encountered and print job data is
                available on another I/O channel."
::= { settings-io 2 }
               
               
io-buffering OBJECT-TYPE
    SYNTAX  INTEGER {
		   eOff(1),
		   eOn(2),
		   eAuto(3)
		   }
    ACCESS  read-only
    STATUS  optional
    DESCRIPTION
                "Returns or controls the manner in which the device
                performs I/O data buffering.  I/O data buffering allows
                additional print job data to be buffered by the I/O sub-
                system in an effort to allow the computer sending the
                data to perform other tasks and to keep the PDL
                processing sub-system busy.  eOff, I/O buffering is
                disabled.  When eOn, I/O buffering is enabled and the
                IO-BUFFER-SIZE object controls the amount of memory set
                aside for I/O buffer.  When eAuto, I/O buffering is
                enabled and the I/O buffer size is determined
                automatically by the device and the IO-BUFFER-SIZE
                object is not used.
                Additional information:
                Returns the manner in which the device
                performs I/O data buffering.  I/O data buffering allows
                additional print job data to be buffered by the I/O 
               	sub- system in an effort to allow the computer sending
               	the data to perform other tasks and to keep the PDL
                processing sub-system busy.  eOff, I/O buffering is
                disabled.  When eOn, I/O buffering is enabled and the
                IO-BUFFER-SIZE object controls the amount of memory set
                aside for I/O buffer.  When eAuto, I/O buffering is
                enabled and the I/O buffer size is determined
                automatically by the device and the IO-BUFFER-SIZE
                object is not used."
::= { settings-io 5 }
               
               
io-buffer-size OBJECT-TYPE
    SYNTAX  INTEGER
    ACCESS  read-only
    STATUS  optional
    DESCRIPTION
                "Returns or configures the amount of memory, in bytes,
                dedicated to I/O print job data buffering.  Attempting
                to set to an unsupported value causes the device to use
                the closest supported value.  Each device POS should
                document the list of supported values.
                Additional information:
                Returns the amount of memory, in bytes, 
                dedicated to I/O print job data buffering.
                In LaserJet 4V the minimum supported value is 10,000.  
                The maximum supported value is dependent on total 
                memory installed and the amount of memory currently 
                being used by other memory consumers.  
               	Between the values of 10,000 and 90,000 only even 
               	increments of 10.000 are supported.  
               	From 100,000 to the maximum only even increments of 
               	100.000 are supported."
::= { settings-io 6 }
               
               
maximum-io-buffering-memory OBJECT-TYPE
    SYNTAX  INTEGER
    ACCESS  read-only
    STATUS  optional
    DESCRIPTION
                "Returns the maximum amount of additional memory, in
                bytes, that can be dedicated to buffering print job
                data."
::= { settings-io 7 }
               
               
not-ready-source-io OBJECT-TYPE
    SYNTAX  OCTET STRING
    ACCESS  read-only
    STATUS  optional
    DESCRIPTION
                "Indicates if the I/O sub-system in the device is not
                ready.  If there are no items in the collection (i.e. no
                bits are set), then the I/O sub-system is ready.  If
                there is an item present, then the item indicates what
                is causing the I/O sub-system to be not ready.  If the
                I/O sub-system is not ready due to a soft error, the
                soft error is considered to be an auto-continuable
                error, thus it can be acknowledged by setting the
                CONTINUE object to eTrue."
::= { status-io 1 }
               
               
status-source-io OBJECT-TYPE
    SYNTAX  OCTET STRING
    ACCESS  read-only
    STATUS  optional
    DESCRIPTION
                "Indicates if the I/O sub-system in a warning condition."
::= { status-io 2 }
               
               
parallel-speed OBJECT-TYPE
    SYNTAX  INTEGER {
		   eSlow(1),
		   eFast(2)
		   }
    ACCESS  read-write
    STATUS  optional
    DESCRIPTION
                "Returns or changes the maximum parallel I/O port speed.
                An eSlow setting causes a 10 us busy pulse per received
                byte of data.  An eFast setting causes a 1.5 us busy
                pulse per received byte of data.  In rare cases, setting
                this value to eFast can cause the parallel port to no
                longer transfer data reliably."
::= { parallel 4 }
               
               
parallel-bidirectionality OBJECT-TYPE
    SYNTAX  INTEGER {
		   eUnidirectional(1),
		   eBidirectional(2)
		   }
    ACCESS  read-write
    STATUS  optional
    DESCRIPTION
                "Returns or changes whether the parallel I/O port
                supports bidirectional communication."
::= { parallel 5 }
               
               
default-orientation OBJECT-TYPE
    SYNTAX  INTEGER {
		   ePortrait(1),
		   eLandscape(2)
		   }
    ACCESS  read-write
    STATUS  optional
    DESCRIPTION
                "Returns or changes the default orientation.  The list of
                supported values should be documented in the device
                POS."
::= { settings-pdl 2 }
               
               
default-copies OBJECT-TYPE
    SYNTAX  INTEGER
    ACCESS  read-write
    STATUS  optional
    DESCRIPTION
                "Returns or changes default copies.  Default copies is
                the default values used by the PDL to control the number
                of copies of each page in the print job that are
                printed.  The print job can override this value.  The
                list of supported values should be documented in the
                device POS.
                Additional information:
                Returns or changes default copies.  Default
                copies is the default values used by the PDL to
                control the number of copies of each page in the
                print job that are printed.  The print job can
                override this value.  The supported values are 1
                through 999. Setting to an unsupported value causes 
              	the printer to substitute in a snap value 
               	(listed below) and to return 
               	<noError> status.  
               	The snap are as follow:  
               	<1 snaps to 1  
               	>999 snaps to 999"
::= { settings-pdl 4 }
               
               
form-feed OBJECT-TYPE
    SYNTAX  INTEGER {
		   eTrue(1)
		   }
    ACCESS  write-only
    STATUS  optional
    DESCRIPTION
                "Instructs the PDL processing sub-system to finishing
                processing the current page of the current job.  Form
                feed is also known as close page or eject page.  If the
                PDL processing sub-system is in a FORM-FEED-NEEDED
                state, this causes the device to flush or finish
                processing the current page of the current job.  If the
                device is not in the FORM-FEED-NEEDED state, an
                <genErr> will occur.
                Additional information:
                Instructs the PDL processing sub-system to 
                finish processing the current page of the current job.  
                Form feed is also known as close page or eject page.  
                If the PDL processing sub-system is in a FORM-FEED-NEEDED
                state, this causes the device to flush or finish
                processing the current page of the current job.  If the
                device is not in the FORM-FEED-NEEDED state, a status
                <genErr> will be returned.  The 
                printer must be offline before attempting
                to perform a form feed, otherwise a status
                <genErr> will be returned."
::= { settings-pdl 5 }
               
               
resource-saving OBJECT-TYPE
    SYNTAX  INTEGER {
		   eOff(1),
		   eOn(2),
		   eAuto(3)
		   }
    ACCESS  read-only
    STATUS  optional
    DESCRIPTION
                "Returns or changes PDL resource saving.  Resource saving
                stores a PDL's permanent soft resources, like fonts,
                even when another PDL is active.  Resource saving is
                also called environment saving.  When eOff, resource
                saving is disabled.  When ON, resource saving is enabled
                and memory is set aside for each PDL based on that PDL's
                resource saving memory size object, to store that PDL's
                permanent soft resources.  When eAuto, resource saving
                is enabled and memory space for each installed PDL is
                determined automatically.  The device POS should
                document what values are legal when only one PDL is
                installed.
                Additional information:
                When PCL is the only PDL installed in
                LaserJet 4V eOn is not a legal value.  When PostScript
                is installed and less than 12 Meg of DRAM is present
                resource saving is not available. When at least 12 Meg
                of memory is installed with PostScript then resource
                saving becomes available and all three values are
                legal.
               	This object is only supported if PostScript option
               	is installed.
               	Returns <noSuchName> status if 
               	attempting to perform a Get on this OID with no 
               	PostScript option installed.
               	Returns <noSuchName>
               	status if attempting to perform a Set, EnableTrap, or
               	DisableTrap on this OID with no PostScript option 
               	installed."
::= { settings-pdl 6 }
               
               
maximum-resource-saving-memory OBJECT-TYPE
    SYNTAX  INTEGER
    ACCESS  read-only
    STATUS  optional
    DESCRIPTION
                "Returns the maximum amount of additional memory, in
                bytes, that can be dedicated to holding PDL permanent
                soft resources."
::= { settings-pdl 7 }
               
               
default-vertical-black-resolution OBJECT-TYPE
    SYNTAX  INTEGER
    ACCESS  read-write
    STATUS  optional
    DESCRIPTION
                "Returns or changes the value of the default vertical
                black resolution.  The units are dots per inch.
                Additional information:
                In LaserJet 4V changing this OID also causes 
               	DEFAULT- HORIZONTAL-BLACK RESOLUTION to change.  
               	DEFAULT- HORIZONTAL-BLACK-RESOLUTION and
                DEFAULT-VERTICAL-BLACK-RESOLUTION must always be the 
               	same.  The supported values are 300 and 600.  
               	Setting to an unsupported value causes the printer
               	to substitute in a snap value (listed below) and 
               	to return <noError> status.  
                The snap values are as follow:  
               		<450 snap to 300  
               		>=450 snap to 600"
::= { settings-pdl 8 }
               
               
default-horizontal-black-resolution OBJECT-TYPE
    SYNTAX  INTEGER
    ACCESS  read-write
    STATUS  optional
    DESCRIPTION
                "Returns or changes the value of the default horizontal
                black resolution.  The units are dots per inch.
                Additional information:
                In LaserJet 4V changing this OID also causes 
               	DEFAULT- VERTICAL-BLACK RESOLUTION to change.  
               	DEFAULT- HORIZONTAL-BLACK-RESOLUTION and
                DEFAULT-VERTICAL-BLACK-RESOLUTION must always be the 
               	same.  The supported values are 300 and 600.
               	Setting to an unsupported value causes the printer
               	to substitute in a snap value (listed below) and to
               	return <noError> status.  
               	The snap values are as follow:  
               		<450 snap to 300  
               		>=450 snap to 600"
::= { settings-pdl 9 }
               
               
default-page-protect OBJECT-TYPE
    SYNTAX  INTEGER {
		   eOn(2),
		   eAuto(3)
		   }
    ACCESS  read-write
    STATUS  optional
    DESCRIPTION
                "Returns or changes the default page protection behavior.
                If eOff, the device does not reserve memory for holding
                the entire raster form of a processed page.  If eOn,
                then memory is reserved.  If eAuto, the device
                determines the amount of memory to reserve."
::= { settings-pdl 10 }
               
               
default-lines-per-page OBJECT-TYPE
    SYNTAX  INTEGER
    ACCESS  read-write
    STATUS  optional
    DESCRIPTION
                "Returns or changes the default number of lines per page.
                The POS indicates the supported values.  An unsupported
                value causes the printer to use the closest supported
                value, causing the printer to return the
                <noError>.
                Additional information:
                The supported values in LaserJet 4V are 5 to 128.
               	Setting to an unsupported value causes the 
               	the printer to substitute in a snap value (listed
               	below) and to return <noError>
               	status.  
               	The snap values are as follow:  
              	 	<5 snaps to 5  
               		>128 snaps to 128"
::= { settings-pdl 11 }
               
               
default-media-size OBJECT-TYPE
    SYNTAX  INTEGER {
		   eUSExecutive(1),
		   eUSLetter(2),
		   eUSLegal(3),
		   eLedger(11),
		   eISOandJISA4(26),
		   eISOandJISA3(27),
		   eJISB5(45),
		   eJISB4(46),
		   eJapanesePostcardSingle(71),
		   eJapanesePostcardDouble(72),
		   eMonarch(80),
		   eCommercial10(81),
		   eInternationalDL(90),
		   eInternationalC5(91),
		   eInternationalB5(100),
		   eCustom(101)
		   }
    ACCESS  read-write
    STATUS  optional
    DESCRIPTION
                "This indicates the default media size.  A write of an
                unsupported value cases an <badValue>.
  		Complete list of supported media sizes along
                with their dimensions are listed in the ``Media Size
                Table'' near the end of this document."
::= { settings-pdl 13 }
               
               
not-ready-processing-pdl OBJECT-TYPE
    SYNTAX  OCTET STRING
    ACCESS  read-only
    STATUS  optional
    DESCRIPTION
                "Indicates if the PDL sub-system in the device is not
                ready.  If there are no items in the collection (i.e. no
                bits are set), then the PDL sub-system is ready.  If
                there is an item present, then the item indicates what
                is causing the PDL sub-system to be not ready.  cOffLine
                indicates the PDL processing sub-system is off line.
                cPrintDataMemoryOverflow indicates the print job was
                sufficiently complex to use up all memory available for
                processing print job data.  cSoftResourceMemoryOverflow
                indicates the print job contained soft resources (fonts,
                macros, etc.) that over flowed the available memory."
::= { status-pdl 1 }
               
               
form-feed-needed OBJECT-TYPE
    SYNTAX  INTEGER {
		   eFalse(1),
		   eTrue(2)
		   }
    ACCESS  read-only
    STATUS  optional
    DESCRIPTION
                "Indicates if the PDL processing sub-system has made
                marks on the current page and the source subsystem has
                been idle for a device specific amount of time."
::= { status-pdl 2 }
               
               
pcl-datecode OBJECT-TYPE
    SYNTAX  DisplayString
    ACCESS  read-only
    STATUS  optional
    DESCRIPTION
                "This indicates the PCL firmware date code in yyyymmdd
                format."
::= { pdl-pcl 1 }
               
               
pcl-resource-saving-memory-size OBJECT-TYPE
    SYNTAX  INTEGER
    ACCESS  read-only
    STATUS  optional
    DESCRIPTION
                "Returns or changes the amount of resource saving memory
                set aside to hold permanent soft PCL resources.
                Additional information:
                Returns the amount of memory, in 
                bytes, set aside to hold permanent soft PCL 
                resources.   Additional memory may need to be installed 
               before this object is supported."
::= { pdl-pcl 2 }
               
               
pcl-name OBJECT-TYPE
    SYNTAX  DisplayString
    ACCESS  read-only
    STATUS  optional
    DESCRIPTION
                "Contains the name of the PDL.  For PCL, the name is
                `PCL'."
::= { pdl-pcl 3 }
               
               
pcl-version OBJECT-TYPE
    SYNTAX  DisplayString
    ACCESS  read-only
    STATUS  optional
    DESCRIPTION
                "Contains the PDL version."
::= { pdl-pcl 4 }
               
               
pcl-default-symbol-set OBJECT-TYPE
    SYNTAX  INTEGER {
		   eISO60DanishNorwegian(4),
		   eISO15Italian(9),
		   eISO88591Latin1ECMA94(14),
		   eISO11SwedishforNames(19),
		   eISO6ASCII(21),
		   eISO4UnitedKingdom(37),
		   eISO69French(38),
		   eISO21German(39),
		   eLegal(53),
		   eISO88592Latin2ECMA94(78),
		   eISO17Spanish(83),
		   ePSMath(173),
		   eISO88599Latin5ECMA128(174),
		   eWindows31Latin5(180),
		   eMicrosoftPublishing(202),
		   eVenturaMath(205),
		   eDeskTop(234),
		   eMath8(269),
		   eRoman8(277),
		   eWindows31Latin2(293),
		   ePC8Turkish(308),
		   eWindows30Latin1(309),
		   ePSText(330),
		   ePC8CodePage437(341),
		   ePC8DNDanishNorwegian(373),
		   ePC850Multilingual(405),
		   eVenturaInternational(426),
		   eVenturaUS(458),
		   ePiFont(501),
		   ePC852Latin2(565),
		   eWindows31J(619),
		   eWindows31Latin1(629)
		   }
    ACCESS  read-write
    STATUS  optional
    DESCRIPTION
                "Returns or changes the default PCL symbol set.  The
                enumeration values match the values supported by the PCL
                Symbol Set Code escape sequence, <ESC>*c#R.  The binary
                representation of the enumerated value is also matches
                the PML <SymbolSetValue>.
                Additional information:
                The eWindows31J enumeration is only supported
                if a Japanese font SIMM is installed."
::= { pdl-pcl 11 }
               
               
pcl-default-font-height OBJECT-TYPE
    SYNTAX  INTEGER
    ACCESS  read-write
    STATUS  optional
    DESCRIPTION
                "Returns or changes the default PCL height.  Height is an
                approximate measure of the body of the type in
                centipoints.  A centipoint is 1/7200 inch.  Height
                applies only to proportional fonts.  Point size, in
                points, can be converted to font height, in centipoints,
                by multiplying the point size by 100.  The POS indicates
                the supported values.  An unsupported value causes the
                printer to use the closest supported value, causing the
                printer to return <noError>.
                ''Closest'' means the smallest absolute difference.
                Additional information:
                In LaserJet 4V this is equivalent to 'POINT SIZE'.
               	Use the following formula to convert:  
               	PCL-DEFAULT-FONT-HEIGHT = POINT SIZE * 100  
               	Setting to an unsupported value causes the printer to
               	substitute in a snap value (listed below) and to
                return <noError> status.  
               	The snap values are as follow:  
               			<=400 snaps to 400  
               			>=99975 snaps to 99975  
                Unsupported values in the range 400 to 99975 snaps 
               	DOWN to the previous supported value
               	(i.e 25293 snaps to 25275 or 75038 snaps to 75025)."
::= { pdl-pcl 13 }
               
               
pcl-default-font-source OBJECT-TYPE
    SYNTAX  INTEGER {
		   eInternal(1),
		   ePermanentSoft(2),
		   eRomSimm1(10),
		   eRomSimm2(11),
		   eRomSimm3(12),
		   eRomSimm4(13)
		   }
    ACCESS  read-write
    STATUS  optional
    DESCRIPTION
                "Returns or changes the value of the default font source
                variable in NVRAM."
::= { pdl-pcl 14 }
               
               
pcl-default-font-number OBJECT-TYPE
    SYNTAX  INTEGER
    ACCESS  read-write
    STATUS  optional
    DESCRIPTION
                "Returns or changes the value of the default font number
                variable in NVRAM.  Writing an unsupported value causes
                the printer to generate an
                <badValue>."
::= { pdl-pcl 15 }
               
               
pcl-default-font-width OBJECT-TYPE
    SYNTAX  INTEGER
    ACCESS  read-write
    STATUS  optional
    DESCRIPTION
                "Returns or changes the default PCL font width.  Width is
                expressed as the width of a character in centipoints.  A
                centipoint is 1/7200 inch.  Width applies only to fixed
                space fonts.  Pitch, in character per inch, can be
                converted to font width, in centipoints, by dividing
                7200 by the pitch.  The POS indicates the supported
                values.  An unsupported value causes the printer to use
                the closest supported value, causing the printer to
                return <noError>.  ''Closest''
                means the smallest absolute difference.
                Additional information:
                In LaserJet 4V this is equivalent to 'PITCH'.  
                Use the following formula to convert:  
               	PCL-DEFAULT-FONT WIDTH = 7200/PITCH  
               	Setting to an unsupported value causes the printer 
               	to substitute in a snap value (listed below) and to 
               	return <noError> status.  
               	The snap values are as follow:  
               			<=44 snaps to 44  
               			>=9999 snaps to 9999"
::= { pdl-pcl 16 }
               
               
postscript-datecode OBJECT-TYPE
    SYNTAX  DisplayString
    ACCESS  read-only
    STATUS  optional
    DESCRIPTION
                "This indicates the PostScript firmware datecode in
                yyyymmdd format.
                Additional information:
                This object is only supported if PostScript
                option is installed.  
               	Returns <noSuchName> status if 
               	attempting to perform a Get on this OID with no 
               	PostScript option installed.
               	Returns <noSuchName>
               	status if attempting to perform a Set, EnableTrap, or
               	DisableTrap on this OID with no PostScript option 
               	installed."
::= { pdl-postscript 1 }
               
               
postscript-resource-saving-memory-size OBJECT-TYPE
    SYNTAX  INTEGER
    ACCESS  read-only
    STATUS  optional
    DESCRIPTION
                "Returns or changes the amount of resource saving memory
                set aside to hold permanent soft PostScript resources.
                Additional information:
                Returns the amount of memory, in
                bytes, set aside to hold permanent soft PostScript
                resources.
               	This object is only supported if PostScript option
               	is installed.
               	Return <noSuchName> status if
               	attempting to perform a Get on this OID with no
               	PostScript option installed.
               	Returns <noSuchName>
               	status if attempting to perform a Set, EnableTrap, or
               	DisableTrap on this OID with no PostScript option 
               	installed."
::= { pdl-postscript 2 }
               
               
postscript-name OBJECT-TYPE
    SYNTAX  DisplayString
    ACCESS  read-only
    STATUS  optional
    DESCRIPTION
                "Contains the name of the PDL.  For PostScript, the name
                is `PostScript'.
                Additional information:
                This object is only supported if PostScript
                option is installed.
                Returns <noSuchName> status if 
               	attempting to perform a Get on this OID with no 
               	PostScript option installed.
               	Returns an <noSuchName>
               	status if attempting to perform a Set, EnableTrap, or
               	DisableTrap on this OID with no PostScript option 
               	installed."
::= { pdl-postscript 3 }
               
               
postscript-version OBJECT-TYPE
    SYNTAX  DisplayString
    ACCESS  read-only
    STATUS  optional
    DESCRIPTION
                "Contains the PDL version.
                Additional information:
                This object is only supported if PostScript
               	option is installed.
               	Returns <noSuchName> status if 
               	attempting to perform a Get on this OID with no 
               	PostScript option installed.
               	Returns an <noSuchName>
               	status if attempting to perform a Set, EnableTrap, or
               	DisableTrap on this OID with no PostScript option 
               	installed."
::= { pdl-postscript 4 }
               
               
postscript-print-errors OBJECT-TYPE
    SYNTAX  INTEGER {
		   eOff(1),
		   eOn(2)
		   }
    ACCESS  read-write
    STATUS  optional
    DESCRIPTION
                "Returns or changes the value of the print PostScript
                errors setting.  If eOn, PostScript prints an error page
                showing the error encountered and the stack at the time
                of the error.
                Additional information:
                This object is only supported if PostScript 
                option is installed.
               	Returns <noSuchName> status if 
               	attempting to perform a Get, or Set on this OID with
               	no PostScript option installed.
               	Returns an <noSuchName>
               	status if attempting to perform an EnableTrap, or
               	DisableTrap on this OID with no PostScript option 
               	installed."
::= { pdl-postscript 11 }
               
               
postscript-jam-recovery OBJECT-TYPE
    SYNTAX  INTEGER {
		   eOff(1),
		   eOn(2)
		   }
    ACCESS  read-write
    STATUS  optional
    DESCRIPTION
                "Returns or changes the PostScript jam recovery setting.
                If eOn, then the device will reprint PostScript pages,
                if those pages jam.
                Additional information:
                This object is only supported if PostScript
               	option is installed.
               	Returns <noSuchName> status if 
               	attempting to perform a Get, or Set on this OID with
               	no PostScript option installed.
               	Returns an <noSuchName>
               	status if attempting to perform an EnableTrap, or
               	DisableTrap on this OID with no PostScript option 
               	installed."
::= { pdl-postscript 12 }
               
               
esc-p-datecode OBJECT-TYPE
    SYNTAX  DisplayString
    ACCESS  read-only
    STATUS  optional
    DESCRIPTION
                "This indicates the ESC-P PDL datecode.  The datecode
                format is yyyymmdd.
                Additional information:
                This object is only supported if ESC-P option is 
               	installed. 
               	Returns an <noSuchName> status if 
               	attempting to perform a Get on this OID with no ESC-P
               	option installed.
               	Returns <noSuchName>
               	status if attempting to perform a Set, EnableTrap, or
               	DisableTrap on this OID with no ESC-P option 
               	installed."
::= { pdl-esc-p 1 }
               
               
esc-p-name OBJECT-TYPE
    SYNTAX  DisplayString
    ACCESS  read-only
    STATUS  optional
    DESCRIPTION
                "Contains the name of the PDL.  For ESC-P, the name is
                `ESC-P'.
                Additional information:
                This object is only supported if ESC-P option is
                installed. 
               	Returns an <noSuchName> status if 
               	attempting to perform a Get on this OID with no ESC-P
               	option installed.
               	Returns <noSuchName>
               	status if attempting to perform a Set, EnableTrap, or
               	DisableTrap on this OID with no ESC-P option 
               	installed."
::= { pdl-esc-p 3 }
               
               
esc-p-version OBJECT-TYPE
    SYNTAX  DisplayString
    ACCESS  read-only
    STATUS  optional
    DESCRIPTION
                "Contains the PDL version.
                Additional information:
                This object is only supported if ESC-P option is
                installed. 
               	Returns an <noSuchName> status if 
               	attempting to perform a Get on this OID with no ESC-P
               	option installed.
               	Returns <noSuchName>
               	status if attempting to perform a Set, EnableTrap, or
               	DisableTrap on this OID with no ESC-P option 
               	installed."
::= { pdl-esc-p 4 }
               
               
pjl-password OBJECT-TYPE
    SYNTAX  INTEGER
    ACCESS  read-only
    STATUS  optional
    DESCRIPTION
                "Returns PJL password, if the password is not set (zero).
                If the password is set, then attempting to retrieve the
                password causes an <genErr> to occur
                and will return the <NullValue>."
::= { pjl 1 }
               
               
not-ready-destination-print-engine OBJECT-TYPE
    SYNTAX  OCTET STRING
    ACCESS  read-only
    STATUS  optional
    DESCRIPTION
                "Indicates if the print engine sub-system in the device
                is not ready.  If there are no items in the collection
                (i.e. no bits are set), then the print engine sub-
                system is ready.  If there is an item present, then the
                item indicates what is causing the print engine sub-
                system to be not ready.  cDoorOpen is in the collection
                if one or more access panels are open.  If the device
                contains more than one access panel, then NOT-READY-
                PRINT-ENGINE-DOOR indicates which access panel(s) are
                open.  cInternalMediaJam is in the collection if one or
                more pieces of media are jammed inside the device.  If
                the media is jammed at an input tray, cTrayMediaJam is
                in the collection, and if the device has more than one
                input tray, then NOT-READY-MEDIA-JAM-AT-TRAY indicates
                which tray has a media jam.  If the media is jammed at
                an output bin, cBinMediaJam is in the collection, and if
                the device has more than one output bin, then NOT-READY-
                MEDIA-JAM-AT-BIN indicates which bin has a media jam.
                cRequestedMediaUnavailable is in the collection if the
                current print job requires media that is not available.
                cTrayEmpty is in the collection if the current print job
                requires media from an input tray that is empty.  If the
                device has more than one input tray, then NOT-READY-
                TRAY-EMPTY indicates which tray is empty.
                cOutputBinFull is in the collection if an output bin is
                full.  If the device has more than one output bin, then
                NOT-READY-BIN-FULL indicates which bin is full.
                cManualFeedMedia is in the collection if the device is
                waiting for media to manually be fed.
                cMarkingAgentMissing is in the collection if a marking
                agent (toner cartridge, ink pen, etc.) is missing.  If
                the device has more than one marking agent, then NOT-
                READY-MARKING-AGENT-MISSING indicates which marking
                agent is missing.  cMarkingAgentOut is in the collection
                if the device is not ready due to one or more marking
                agents being low or out.  If the device has more than
                one marking agent, then NOT-READY-MARKING-AGENT-LOW-OR-
                OUT indicates which marking agent is low or out.
                cIncorrectMarkingAgent is in the collection if the
                device detects that an incorrect marking agent is
                installed.  If the device has more than one marking
                agent, then NOT-READY-INCORRECT-MARKING-AGENT indicates
                which marking agent location is loaded with the wrong
                type of marking agent.  cTrayMissing is in the
                collection if the device is not ready because one or
                more trays are not installed.  If the device has more
                than one input tray, then NOT-READY-TRAY-MISSING
                indicates which tray is missing.  cDeviceSpecific is in
                the collection if one or more items are in either NOT-
                READY-LASER-PRINT-ENGINE or NOT-READY-DESTINATION-
                INKJET-PRINT-ENGINE-NOT-READY.  cMediaPickMisfeed is in
                the collection if the print engine detects the tray is
                not empty, but can not pick up a sheet of media from
                that tray.  cMarkingAgentFailure indicates there is a
                failure with a marking agent and it may need to be
                replaced.  If the device supports more than one marking
                agent, then the NOT-READY-MARKING-AGENT-FAILURE object
                indicates all the marking agents that have failed.  The
                POS will indicate the marking agent failure recovery
                process, if any."
::= { status-prt-eng 1 }
               
               
not-ready-laser-print-engine OBJECT-TYPE
    SYNTAX  OCTET STRING
    ACCESS  read-only
    STATUS  optional
    DESCRIPTION
                "Indicates if the laser print engine sub-system in the
                device is not ready.  If there are no items in the
                collection (i.e. no bits are set), then the laser print
                engine sub-system is ready.  If there is an item
                present, then the item indicates what is causing the
                laser print engine sub-system to be not ready."
::= { status-prt-eng 3 }
               
               
total-engine-page-count OBJECT-TYPE
    SYNTAX  INTEGER
    ACCESS  read-only
    STATUS  optional
    DESCRIPTION
                "Total number of pages printed by the device.  POS
                indicates if the total engine page count is kept in
                NVRAM, and the maximum supported value before the page
                count rolls over to zero.
                Additional information:
                In LaserJet 4V the total engine page count is kept in
                NVRAM however the NVRAM value is only updated every 10
                pages.  NOTE: The value returned by this OID will be
                incremented every page but if power is lost between
                NVRAM updates up to 9 pages of the page count may be
                lost.  The page count counter will be reset to zero
                after 16,777,215 (2^24-1) pages."
::= { status-prt-eng 5 }
               
               
status-destination-print-engine OBJECT-TYPE
    SYNTAX  OCTET STRING
    ACCESS  read-only
    STATUS  optional
    DESCRIPTION
                "Indicates if part of the print engine sub-system is not
                functional, but the non-functional component(s) are not
                currently required to print."
::= { status-prt-eng 8 }
               
               
default-manual-feed OBJECT-TYPE
    SYNTAX  INTEGER {
		   eOff(1),
		   eOn(2)
		   }
    ACCESS  read-write
    STATUS  optional
    DESCRIPTION
                "Returns or changes the default manual feed value used by
                the PDLs."
::= { settings-intray 4 }
               
               
mp-tray OBJECT-TYPE
    SYNTAX  INTEGER {
		   eManual(1),
		   eCassette(2),
		   eFirst(3)
		   }
    ACCESS  read-only
    STATUS  optional
    DESCRIPTION
                "Returns or changes the value of the multi-purpose (MP)
                tray configuration variable.  The MP tray can be
                configured to operate as an additional input tray
                (eCassette), a manual feed slot (eManual), or in a
                manner compatible with the LaserJet III manual feed slot
                (eFirst).  If configured for eFirst, if media is present
                in the MP tray, that media is used (assuming the size
                matches and the print job didn't specify another tray)
                until the MP tray is empty."
::= { settings-intray 5 }
               
               
tray-lock OBJECT-TYPE
    SYNTAX  OCTET STRING
    ACCESS  read-only
    STATUS  optional
    DESCRIPTION
                "Returns or changes the list of locked input trays.  The
                printer only pulls media from a locked input tray when
                the input tray is specifically requested by the print
                job.
                Additional information:
                When MP-TRAY is eManual or eFirst only
                cInTray2Locked or cInTray3Locked can be selected and
                cInTray1Locked is illegal. It is also illegal to
                select both cInTray2Locked and cInTray3Locked.  When
                MP-TRAY is eCassette all selections and combinations
                of selections are legal."
::= { settings-intray 6 }
               
               
not-ready-tray-missing OBJECT-TYPE
    SYNTAX  OCTET STRING
    ACCESS  read-only
    STATUS  optional
    DESCRIPTION
                "Indicates which trays are not currently installed that
                is caused the device to be not ready."
::= { status-intray 1 }
               
               
not-ready-tray-empty OBJECT-TYPE
    SYNTAX  OCTET STRING
    ACCESS  read-only
    STATUS  optional
    DESCRIPTION
                "Indicates which trays contain no media  causing the
                device to be not ready.  Some devices may treat tray
                missing as a tray empty condition."
::= { status-intray 2 }
               
               
status-tray-missing OBJECT-TYPE
    SYNTAX  OCTET STRING
    ACCESS  read-only
    STATUS  optional
    DESCRIPTION
                "Indicates which trays are not currently installed that
                is caused the device to be in a warning condition."
::= { status-intray 3 }
               
               
status-tray-empty OBJECT-TYPE
    SYNTAX  OCTET STRING
    ACCESS  read-only
    STATUS  optional
    DESCRIPTION
                "Indicates which trays contain no media causing the
                device to be in a warning condition.  Some devices may
                treat tray missing as a tray empty condition."
::= { status-intray 4 }
               
               
tray1-media-size-loaded OBJECT-TYPE
    SYNTAX  INTEGER {
		   eUSExecutive(1),
		   eUSLetter(2),
		   eUSLegal(3),
		   eLedger(11),
		   eISOandJISA4(26),
		   eISOandJISA3(27),
		   eJISB5(45),
		   eJISB4(46),
		   eJapanesePostcardSingle(71),
		   eJapanesePostcardDouble(72),
		   eMonarch(80),
		   eCommercial10(81),
		   eInternationalDL(90),
		   eInternationalC5(91),
		   eInternationalB5(100),
		   eCustom(101)
		   }
    ACCESS  read-only
    STATUS  optional
    DESCRIPTION
                "Returns the media size that is currently loaded in tray
                #1.  This object can be set to indicate the media size
                currently loaded, if the printer supports input trays
                that can not sense the media size.  Complete list of
                supported media sizes along with their dimensions are
                listed in the ``Media Size Table'' near the end of this
                document."
::= { intray1 1 }
               
               
tray1-media-available OBJECT-TYPE
    SYNTAX  INTEGER(-1..100)
    ACCESS  read-only
    STATUS  optional
    DESCRIPTION
                "Returns a number that indicates how full the input tray
                is.  If the device can only detect empty / not empty the
                device returns -1 for not empty and 0 for empty.  If the
                device can determine how full the tray is, the device
                returns a percentage full from 0% to 100%
                Additional information:
                LaserJet 4V can only detect empty/not empty tray.
                It returns -1 for not empty and 0 for empty."
::= { intray1 2 }
               
               
tray1-name OBJECT-TYPE
    SYNTAX  DisplayString
    ACCESS  read-only
    STATUS  optional
    DESCRIPTION
                "Returns the device specific name for tray 1."
::= { intray1 3 }
               
               
tray2-media-size-loaded OBJECT-TYPE
    SYNTAX  INTEGER {
		   eUSLetter(2),
		   eUSLegal(3),
		   eLedger(11),
		   eISOandJISA4(26),
		   eISOandJISA3(27),
		   eJISB5(45),
		   eJISB4(46)
		   }
    ACCESS  read-only
    STATUS  optional
    DESCRIPTION
                "Returns the media size that is currently loaded in tray
                #2.  Complete list of supported media sizes along with
                their dimensions are listed in the ``Media Size Table''
                near the end of this document."
::= { intray2 1 }
               
               
tray2-media-available OBJECT-TYPE
    SYNTAX  INTEGER(-1..100)
    ACCESS  read-only
    STATUS  optional
    DESCRIPTION
                "Returns a number that indicates how full the input tray
                is.  If the device can only detect empty / not empty the
                device returns -1 for not empty and 0 for empty.  If the
                device can determine how full the tray is, the device
                returns a percentage full from 0% to 100%
                Additional information:
                LaserJet 4V can only detect empty/not empty tray.
                It returns -1 for not empty and 0 for empty."
::= { intray2 2 }
               
               
tray2-name OBJECT-TYPE
    SYNTAX  DisplayString
    ACCESS  read-only
    STATUS  optional
    DESCRIPTION
                "Returns the device specific name for tray 2."
::= { intray2 3 }
               
               
tray3-media-size-loaded OBJECT-TYPE
    SYNTAX  INTEGER {
		   eUSLetter(2),
		   eUSLegal(3),
		   eLedger(11),
		   eISOandJISA4(26),
		   eISOandJISA3(27),
		   eJISB4(46)
		   }
    ACCESS  read-only
    STATUS  optional
    DESCRIPTION
                "Returns the media size that is currently loaded in tray
                #3.  Complete list of supported media sizes along with
                their dimensions are listed in the ``Media Size Table''
                near the end of this document.
                Additional information:
                Those sizes listed in the SYNTAX
            	section above are the only sizes that are supported
               	by the LaserJet 4V Optional Lower Cassette (LC).
               	This object is only supported if a LC is installed.  
               	Returns <noSuchName> status
               	if attempting to perform a Get on this OID with 
               	no LC installed. 
               	Returns <noSuchName>
               	status if attempting to perform a Set, EnableTrap, or
               	DisableTrap on this OID with no LC installed."
::= { intray3 1 }
               
               
tray3-media-available OBJECT-TYPE
    SYNTAX  INTEGER(-1..100)
    ACCESS  read-only
    STATUS  optional
    DESCRIPTION
                "Returns a number that indicates how full the input tray
                is.  If the device can only detect empty / not empty the
                device returns -1 for not empty and 0 for empty.  If the
                device can determine how full the tray is, the device
                returns a percentage full from 0% to 100%
                Additional information:
                LaserJet 4V can only detect empty/not empty tray.
                It returns -1 for not empty and 0 for empty.
               	This object is only supported if a LC is installed.
               	Returns <noSuchName> status 
               	if attempting to perform a Get on this OID with
               	no LC installed.
                Returns <noSuchName>
               	status if attempting to perform a Set, EnableTrap, or
               	DisableTrap on this OID with no LC installed."
::= { intray3 2 }
               
               
tray3-name OBJECT-TYPE
    SYNTAX  DisplayString
    ACCESS  read-only
    STATUS  optional
    DESCRIPTION
                "Returns the device specific name for tray 3.
                Additional information:
                This object is only supported if a LC is 
               	installed.
               	Returns <noSuchName> status if
               	attempting to perform a Get on this OID with no LC 
               	installed.
                Returns <noSuchName>
                status if attempting to perform a Set, EnableTrap, or
               	DisableTrap on this OID with no LC installed."
::= { intray3 3 }
               
               
outbin1-maximum-capacity OBJECT-TYPE
    SYNTAX  INTEGER
    ACCESS  read-only
    STATUS  optional
    DESCRIPTION
                "Maximum capacity of the output bin, in sheets of 20
                pound paper."
::= { outbin1 1 }
               
               
low-marking-agent-processing OBJECT-TYPE
    SYNTAX  INTEGER {
		   eStop(1),
		   eCont(2)
		   }
    ACCESS  read-write
    STATUS  optional
    DESCRIPTION
                "Returns or changes how the device processes a low
                marking agent event.  If eCont, then the device
                continues to print.  If eStop, then the device stops
                until a continue event occurs."
::= { settings-marking-agent 3 }
               
               
default-ret OBJECT-TYPE
    SYNTAX  INTEGER {
		   eOff(1),
		   eLight(2),
		   eMedium(3),
		   eDark(4)
		   }
    ACCESS  read-write
    STATUS  optional
    DESCRIPTION
                "Returns or changes the Resolution Enhancement Technology
                setting.  Devices that only support eOff and on should
                map all other values to on and always return the same
                non-eOff value to indicate on.  The list of supported
                values should be documented in the device POS."
::= { imaging 5 }
               
               
default-print-quality OBJECT-TYPE
    SYNTAX  INTEGER(0..100)
    ACCESS  read-write
    STATUS  optional
    DESCRIPTION
                "Returns or sets the default print quality.  A value of
                zero has the lowest print quality.  A value of 100 has
                the highest print quality.  Each POS should document
                what values in the 0 to 100 range are supported.
                Additional information:
                Returns or sets the print quality versus cost 
                trade off.  In LaserJet 4V, the supported values are 0
               	and 100.  A value of zero has the lowest print 
                quality(ECONOMODE=ON), thus minimizes the consumables
               	used.  A value of 100 has the highest print quality
               	(ECONOMODE=OFF), thus uses more consumables.  Setting
               	to an unsupported value outside of the 0 to 100 range
               	causes the printer to return 
               	<badValue> status.  Setting
               	to an unsupported value inside of the 0 to 100 range
               	causes the printer to substitute in a snap value 
               	(listed below) and to return 
               	<noError> status.  
               	The snap values are as follow:  
                0 to 50 snap to 0  
               	51 to 100 snap to 100"
::= { imaging 7 }
               
               
END
