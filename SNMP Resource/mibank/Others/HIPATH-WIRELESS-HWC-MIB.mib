HIPATH-WIRELESS-HWC-MIB DEFINITIONS ::= BEGIN
 
		IMPORTS
				enterprises FROM RFC1155-SMI
			hiPathWirelessMgmt, hiPathWirelessModules			
				FROM HIPATH-WIRELESS-SMI			
			WEPKeytype			
				FROM IEEE802dot11-MIB			
			ifIndex, InterfaceIndex			
				FROM IF-MIB			
			OBJECT-GROUP, MODULE-COMPLIANCE, NOTIFICATION-GROUP			
				FROM SNMPv2-CONF			
			TimeTicks, IpAddress, Integer32, Unsigned32, Gauge32, 
			Counter64, OBJECT-TYPE, MODULE-IDENTITY, NOTIFICATION-TYPE			
				FROM SNMPv2-SMI			
			DisplayString, TruthValue, RowStatus, MacAddress, TEXTUAL-CONVENTION			
				FROM SNMPv2-TC;
	
	
--  August 13, 2008 at 14:31 GMT
-- January 15, 2007 at 13:38 GMT
-- August 11, 2007 at 16:15 GMT
-- November 26, 2007 at 16:15 GMT
-- August 13, 2008 at 14:31 GMT
		-- 1.3.6.1.4.1.4329.15.5.2
		hiPathWirelessControllerMib MODULE-IDENTITY 
			LAST-UPDATED "200808131431Z"		-- August 13, 2008 at 14:31 GMT
			ORGANIZATION 
				"Chantry Networks Inc."
			CONTACT-INFO 
				"Behrouz Sultan
				Chantry Networks, Inc.
				
				1900 Minnesota Court, Suite 125
				Mississauga ON, L5N 3C9
				
				Email: behrouz.sultan@siemens.com
				Phone 1-905-288-3537
				Fax   1-905-567-0099"
			DESCRIPTION 
				"The access controller MIB"
			REVISION "200808131431Z"		-- August 13, 2008 at 14:31 GMT
			DESCRIPTION 
				"Added DNS entries.
				 Aded DAS values
				 Added RADIUS server information"
			REVISION "200711261615Z"		-- November 26, 2007 at 16:15 GMT
			DESCRIPTION 
				"DHCP information related to the Controller was added to the MIB."
			REVISION "200708111615Z"		-- August 11, 2007 at 16:15 GMT
			DESCRIPTION 
				"Modified apTable with additional fields."
			REVISION "200701151338Z"		-- January 15, 2007 at 13:38 GMT
			DESCRIPTION 
				"Added WDS VNS."
			REVISION "200510281312Z"		-- October 28, 2005 at 13:12 GMT
			DESCRIPTION 
				"Initial version."
			::= { hiPathWirelessModules 2 }

		
	
	
--
-- Textual conventions
--
	
		LogEventSeverity ::= TEXTUAL-CONVENTION
			STATUS current
			DESCRIPTION 
				"The log event severities used in the access controller."
			SYNTAX INTEGER
				{
				critical(1),
				major(2),
				minor(3),
				information(4),
				trace(5)
				}

	
--
-- Node definitions
--
	
		-- 1.3.6.1.4.1.4329.15.3.2
		hiPathWirelessController OBJECT IDENTIFIER ::= { hiPathWirelessMgmt 2 }

		
		-- 1.3.6.1.4.1.4329.15.3.2.1
		systemObjects OBJECT IDENTIFIER ::= { hiPathWirelessController 1 }

		
		-- 1.3.6.1.4.1.4329.15.3.2.1.1
		sysSoftwareVersion OBJECT-TYPE
			SYNTAX DisplayString
			MAX-ACCESS read-only
			STATUS current
			DESCRIPTION
				"System software version."
			::= { systemObjects 1 }

		
		-- 1.3.6.1.4.1.4329.15.3.2.1.2
		sysLogLevel OBJECT-TYPE
			SYNTAX LogEventSeverity
			MAX-ACCESS read-write
			STATUS current
			DESCRIPTION
				"Sets the level of events which are written to the system
				log."
			::= { systemObjects 2 }

		
		-- 1.3.6.1.4.1.4329.15.3.2.1.3
		sysSerialNo OBJECT-TYPE
			SYNTAX OCTET STRING (SIZE (0..64))
			MAX-ACCESS read-only
			STATUS current
			DESCRIPTION
				"System serial number."
			::= { systemObjects 3 }

		
		-- 1.3.6.1.4.1.4329.15.3.2.1.4
		sysLogSupport OBJECT IDENTIFIER ::= { systemObjects 4 }

		
		-- 1.3.6.1.4.1.4329.15.3.2.1.4.1
		hiPathWirelessAppLogFacility OBJECT-TYPE
			SYNTAX INTEGER
				{
				local0(0),
				local1(1),
				local2(2),
				local3(3),
				local4(4),
				local5(5),
				local6(6)
				}
			MAX-ACCESS read-write
			STATUS current
			DESCRIPTION
				"The application log facility level for syslog."
			::= { sysLogSupport 1 }

		
		-- 1.3.6.1.4.1.4329.15.3.2.1.4.2
		serviceLogFacility OBJECT-TYPE
			SYNTAX INTEGER
				{
				local0(0),
				local1(1),
				local2(2),
				local3(3),
				local4(4),
				local5(5),
				local6(6)
				}
			MAX-ACCESS read-write
			STATUS current
			DESCRIPTION
				"The service log facility level for syslog."
			::= { sysLogSupport 2 }

		
		-- 1.3.6.1.4.1.4329.15.3.2.1.4.3
		includeAllServiceMessages OBJECT-TYPE
			SYNTAX TruthValue
			MAX-ACCESS read-write
			STATUS current
			DESCRIPTION
				"Indicates if DHCP messages should also be forwarded to syslog."
			::= { sysLogSupport 3 }

		
		-- 1.3.6.1.4.1.4329.15.3.2.1.4.4
		sysLogServersTable OBJECT-TYPE
			SYNTAX SEQUENCE OF SysLogServersEntry
			MAX-ACCESS not-accessible
			STATUS current
			DESCRIPTION
				"Table of syslog servers to forward logging messages."
			::= { sysLogSupport 4 }

		
		-- 1.3.6.1.4.1.4329.15.3.2.1.4.4.1
		sysLogServersEntry OBJECT-TYPE
			SYNTAX SysLogServersEntry
			MAX-ACCESS not-accessible
			STATUS current
			DESCRIPTION
				"Configuration information for an external syslog server."
			INDEX { sysLogServerIndex }
			::= { sysLogServersTable 1 }

		
		SysLogServersEntry ::=
			SEQUENCE { 
				sysLogServerIndex
					Integer32,
				sysLogServerEnabled
					TruthValue,
				sysLogServerIP
					IpAddress,
				sysLogServerPort
					Integer32,
				sysLogServerRowStatus
					RowStatus
			 }

		-- 1.3.6.1.4.1.4329.15.3.2.1.4.4.1.1
		sysLogServerIndex OBJECT-TYPE
			SYNTAX Integer32 (1..2147483647)
			MAX-ACCESS read-write
			STATUS current
			DESCRIPTION
				"Table index for the syslog server."
			::= { sysLogServersEntry 1 }

		
		-- 1.3.6.1.4.1.4329.15.3.2.1.4.4.1.2
		sysLogServerEnabled OBJECT-TYPE
			SYNTAX TruthValue
			MAX-ACCESS read-write
			STATUS current
			DESCRIPTION
				"Indicates if messages are to be sent to the syslog server."
			::= { sysLogServersEntry 2 }

		
		-- 1.3.6.1.4.1.4329.15.3.2.1.4.4.1.3
		sysLogServerIP OBJECT-TYPE
			SYNTAX IpAddress
			MAX-ACCESS read-write
			STATUS current
			DESCRIPTION
				"syslog server IP address."
			::= { sysLogServersEntry 3 }

		
		-- 1.3.6.1.4.1.4329.15.3.2.1.4.4.1.4
		sysLogServerPort OBJECT-TYPE
			SYNTAX Integer32
			MAX-ACCESS read-write
			STATUS current
			DESCRIPTION
				"syslog server port number."
			::= { sysLogServersEntry 4 }

		
		-- 1.3.6.1.4.1.4329.15.3.2.1.4.4.1.5
		sysLogServerRowStatus OBJECT-TYPE
			SYNTAX RowStatus
			MAX-ACCESS read-write
			STATUS current
			DESCRIPTION
				"RowStatus for operating on syslogServersTable."
			::= { sysLogServersEntry 5 }

		
		-- 1.3.6.1.4.1.4329.15.3.2.2
		dnsObjects OBJECT IDENTIFIER ::= { hiPathWirelessController 2 }

		
		-- 1.3.6.1.4.1.4329.15.3.2.2.1
		primaryDNS OBJECT-TYPE
			SYNTAX IpAddress
			MAX-ACCESS read-write
			STATUS current
			DESCRIPTION
				"Primary DNS address configured in the Controller."
			::= { dnsObjects 1 }

		
		-- 1.3.6.1.4.1.4329.15.3.2.2.2
		secondaryDNS OBJECT-TYPE
			SYNTAX IpAddress
			MAX-ACCESS read-write
			STATUS current
			DESCRIPTION
				"Secondary DNS address configured in the Controller."
			::= { dnsObjects 2 }

		
		-- 1.3.6.1.4.1.4329.15.3.2.2.3
		tertiaryDNS OBJECT-TYPE
			SYNTAX IpAddress
			MAX-ACCESS read-write
			STATUS current
			DESCRIPTION
				"Third DNS address configured in the Controller."
			::= { dnsObjects 3 }

		
		-- 1.3.6.1.4.1.4329.15.3.2.3
		mgmtPortObjects OBJECT IDENTIFIER ::= { hiPathWirelessController 3 }

		
		-- 1.3.6.1.4.1.4329.15.3.2.3.1
		mgmtPortIfIndex OBJECT-TYPE
			SYNTAX Integer32
			MAX-ACCESS read-only
			STATUS current
			DESCRIPTION
				"ifIndex of the management port."
			::= { mgmtPortObjects 1 }

		
		-- 1.3.6.1.4.1.4329.15.3.2.3.2
		mgmtPortHostname OBJECT-TYPE
			SYNTAX DisplayString
			MAX-ACCESS read-write
			STATUS current
			DESCRIPTION
				"Hostname of the management port."
			::= { mgmtPortObjects 2 }

		
		-- 1.3.6.1.4.1.4329.15.3.2.3.5
		mgmtPortDomain OBJECT-TYPE
			SYNTAX DisplayString
			MAX-ACCESS read-write
			STATUS current
			DESCRIPTION
				"Domain of the management port."
			::= { mgmtPortObjects 5 }

		
		-- 1.3.6.1.4.1.4329.15.3.2.4
		physicalPortObjects OBJECT IDENTIFIER ::= { hiPathWirelessController 4 }

		
		-- 1.3.6.1.4.1.4329.15.3.2.4.1
		physicalPortCount OBJECT-TYPE
			SYNTAX Integer32
			MAX-ACCESS read-only
			STATUS current
			DESCRIPTION
				"Number of rows in routerPortsTable."
			::= { physicalPortObjects 1 }

		
		-- 1.3.6.1.4.1.4329.15.3.2.4.2
		physicalPortsTable OBJECT-TYPE
			SYNTAX SEQUENCE OF PhysicalPortsEntry
			MAX-ACCESS not-accessible
			STATUS current
			DESCRIPTION
				"Table of router ports on the controller."
			::= { physicalPortObjects 2 }

		
		-- 1.3.6.1.4.1.4329.15.3.2.4.2.1
		physicalPortsEntry OBJECT-TYPE
			SYNTAX PhysicalPortsEntry
			MAX-ACCESS not-accessible
			STATUS current
			DESCRIPTION
				"An entry in routerPortsTable."
			INDEX { ifIndex }
			::= { physicalPortsTable 1 }

		
		PhysicalPortsEntry ::=
			SEQUENCE { 
				portMgmtTrafficEnable
					TruthValue,
				portDuplexMode
					INTEGER,
				portFunction
					INTEGER,
				portEnabled
					INTEGER,
				portName
					OCTET STRING,
				portIpAddress
					IpAddress,
				portMask
					IpAddress,
				portMacAddress
					MacAddress,
				portVlanID
					Integer32,
				portDHCPEnable
					TruthValue,
				portDHCPGateway
					DisplayString,
				portDHCPDomain
					DisplayString,
				portDHCPDefaultLease
					Integer32,
				portDHCPMaxLease
					Integer32,
				portDHCPDnsServers
					DisplayString,
				portDHCPWins
					DisplayString
			 }

		-- 1.3.6.1.4.1.4329.15.3.2.4.2.1.1
		portMgmtTrafficEnable OBJECT-TYPE
			SYNTAX TruthValue
			MAX-ACCESS read-write
			STATUS current
			DESCRIPTION
				"Determines whether controller management 
				network traffic is allowed over this interface."
			::= { physicalPortsEntry 1 }

		
		-- 1.3.6.1.4.1.4329.15.3.2.4.2.1.2
		portDuplexMode OBJECT-TYPE
			SYNTAX INTEGER
				{
				full(1),
				half(2),
				auto(3)
				}
			MAX-ACCESS read-write
			STATUS current
			DESCRIPTION
				"Duplex mode for the esa ports."
			::= { physicalPortsEntry 2 }

		
		-- 1.3.6.1.4.1.4329.15.3.2.4.2.1.3
		portFunction OBJECT-TYPE
			SYNTAX INTEGER
				{
				router(1),
				host(2),
				thirdPartyAP(3)
				}
			MAX-ACCESS read-write
			STATUS current
			DESCRIPTION
				"Specifies the behavior of the HWC physical ports."
			::= { physicalPortsEntry 3 }

		
		-- 1.3.6.1.4.1.4329.15.3.2.4.2.1.4
		portEnabled OBJECT-TYPE
			SYNTAX INTEGER
				{
				enabled(1),
				disabled(2)
				}
			MAX-ACCESS read-write
			STATUS current
			DESCRIPTION
				"If enabled, the interface administratively is enabled."
			DEFVAL { enabled }
			::= { physicalPortsEntry 4 }

		
		-- 1.3.6.1.4.1.4329.15.3.2.4.2.1.5
		portName OBJECT-TYPE
			SYNTAX OCTET STRING
			MAX-ACCESS read-only
			STATUS current
			DESCRIPTION
				"A textual string containing information about the port."
			::= { physicalPortsEntry 5 }

		
		-- 1.3.6.1.4.1.4329.15.3.2.4.2.1.6
		portIpAddress OBJECT-TYPE
			SYNTAX IpAddress
			MAX-ACCESS read-write
			STATUS current
			DESCRIPTION
				"The IP address of this port."
			::= { physicalPortsEntry 6 }

		
		-- 1.3.6.1.4.1.4329.15.3.2.4.2.1.7
		portMask OBJECT-TYPE
			SYNTAX IpAddress
			MAX-ACCESS read-write
			STATUS current
			DESCRIPTION
				"The subnet mask associated with the IP address of this port."
			::= { physicalPortsEntry 7 }

		
		-- 1.3.6.1.4.1.4329.15.3.2.4.2.1.8
		portMacAddress OBJECT-TYPE
			SYNTAX MacAddress
			MAX-ACCESS read-only
			STATUS current
			DESCRIPTION
				"Port's MAC address."
			::= { physicalPortsEntry 8 }

		
		-- 1.3.6.1.4.1.4329.15.3.2.4.2.1.9
		portVlanID OBJECT-TYPE
			SYNTAX Integer32 (-1..4094)
			MAX-ACCESS read-write
			STATUS current
			DESCRIPTION
				"External VLAN tag for the physical port for trasmitted and received packets.
				Value ranges: (-1) it is not tagged, zero(0) means reserved, 1-4094 tag value."
			DEFVAL { -1 }
			::= { physicalPortsEntry 9 }

		
		-- 1.3.6.1.4.1.4329.15.3.2.4.2.1.10
		portDHCPEnable OBJECT-TYPE
			SYNTAX TruthValue
			MAX-ACCESS read-write
			STATUS current
			DESCRIPTION
				"If enabled, the controller is configured as default DHCP server for AP."
			::= { physicalPortsEntry 10 }

		
		-- 1.3.6.1.4.1.4329.15.3.2.4.2.1.11
		portDHCPGateway OBJECT-TYPE
			SYNTAX DisplayString
			MAX-ACCESS read-write
			STATUS current
			DESCRIPTION
				"Gateway address to be supplied to the wireless clients if controller is
				configured as default DHCP server for AP."
			::= { physicalPortsEntry 11 }

		
		-- 1.3.6.1.4.1.4329.15.3.2.4.2.1.12
		portDHCPDomain OBJECT-TYPE
			SYNTAX DisplayString
			MAX-ACCESS read-write
			STATUS current
			DESCRIPTION
				"Domain name to be supplied to the wireless clients if controller is
				configured as default DHCP server for AP."
			::= { physicalPortsEntry 12 }

		
		-- 1.3.6.1.4.1.4329.15.3.2.4.2.1.13
		portDHCPDefaultLease OBJECT-TYPE
			SYNTAX Integer32
			MAX-ACCESS read-write
			STATUS current
			DESCRIPTION
				"Default DHCP lease time in seconds to be supplied to the wireless
				clients if controller is configured as default DHCP server for AP."
			::= { physicalPortsEntry 13 }

		
		-- 1.3.6.1.4.1.4329.15.3.2.4.2.1.14
		portDHCPMaxLease OBJECT-TYPE
			SYNTAX Integer32
			MAX-ACCESS read-write
			STATUS current
			DESCRIPTION
				"Maximum DHCP lease time in seconds to be supplied to the wireless
				clients if controller is configured as default DHCP server for AP."
			::= { physicalPortsEntry 14 }

		
		-- 1.3.6.1.4.1.4329.15.3.2.4.2.1.15
		portDHCPDnsServers OBJECT-TYPE
			SYNTAX DisplayString
			MAX-ACCESS read-write
			STATUS current
			DESCRIPTION
				"List of DNSs to be supplied to the wireless clients if controller is
				configured as default DHCP server for AP."
			::= { physicalPortsEntry 15 }

		
		-- 1.3.6.1.4.1.4329.15.3.2.4.2.1.16
		portDHCPWins OBJECT-TYPE
			SYNTAX DisplayString
			MAX-ACCESS read-write
			STATUS current
			DESCRIPTION
				"List of WINSs to be supplied to the wireless clients if controller is
				configured as default DHCP server for AP."
			::= { physicalPortsEntry 16 }

		
		-- 1.3.6.1.4.1.4329.15.3.2.4.3
		physicalPortsInternalVlanID OBJECT-TYPE
			SYNTAX Integer32 (-1..4094)
			MAX-ACCESS read-write
			STATUS current
			DESCRIPTION
				"Internal VLAN tag to be used for physical ports for which the exernal 
				VLAN tag have not been configured.
				Value ranges: (-1) it is not tagged, zero(0) means reserved, 1-4094 tag value."
			DEFVAL { 1 }
			::= { physicalPortObjects 3 }

		
		-- 1.3.6.1.4.1.4329.15.3.2.4.4
		physicalFlash OBJECT-TYPE
			SYNTAX INTEGER
				{
				mounted(1),
				unmounted(2)
				}
			MAX-ACCESS read-only
			STATUS current
			DESCRIPTION
				"Flash drive status."
			::= { physicalPortObjects 4 }

		
		-- 1.3.6.1.4.1.4329.15.3.2.4.5
		phyDHCPRangeTable OBJECT-TYPE
			SYNTAX SEQUENCE OF PhyDHCPRangeEntry
			MAX-ACCESS not-accessible
			STATUS current
			DESCRIPTION
				"phyDHCPRangeTable contains the IP address ranges that DHCP
				will serve to clients associated with physical ports."
			::= { physicalPortObjects 5 }

		
		-- 1.3.6.1.4.1.4329.15.3.2.4.5.1
		phyDHCPRangeEntry OBJECT-TYPE
			SYNTAX PhyDHCPRangeEntry
			MAX-ACCESS not-accessible
			STATUS current
			DESCRIPTION
				"Configuration information for a DHCP range."
			INDEX { ifIndex, phyDHCPRangeIndex }
			::= { phyDHCPRangeTable 1 }

		
		PhyDHCPRangeEntry ::=
			SEQUENCE { 
				phyDHCPRangeIndex
					Integer32,
				phyDHCPRangeStart
					IpAddress,
				phyDHCPRangeEnd
					IpAddress,
				phyDHCPRangeType
					INTEGER,
				phyDHCPRangeStatus
					RowStatus
			 }

		-- 1.3.6.1.4.1.4329.15.3.2.4.5.1.1
		phyDHCPRangeIndex OBJECT-TYPE
			SYNTAX Integer32 (1..2147483647)
			MAX-ACCESS read-write
			STATUS current
			DESCRIPTION
				"Index for the DHCP row element."
			::= { phyDHCPRangeEntry 1 }

		
		-- 1.3.6.1.4.1.4329.15.3.2.4.5.1.2
		phyDHCPRangeStart OBJECT-TYPE
			SYNTAX IpAddress
			MAX-ACCESS read-write
			STATUS current
			DESCRIPTION
				"First IP address in the range."
			::= { phyDHCPRangeEntry 2 }

		
		-- 1.3.6.1.4.1.4329.15.3.2.4.5.1.3
		phyDHCPRangeEnd OBJECT-TYPE
			SYNTAX IpAddress
			MAX-ACCESS read-write
			STATUS current
			DESCRIPTION
				"Last IP address in the range."
			::= { phyDHCPRangeEntry 3 }

		
		-- 1.3.6.1.4.1.4329.15.3.2.4.5.1.4
		phyDHCPRangeType OBJECT-TYPE
			SYNTAX INTEGER
				{
				inclusion(1),
				exclusion(2)
				}
			MAX-ACCESS read-write
			STATUS current
			DESCRIPTION
				"Determines whether addresses in the specified range will 
				be included, or excluded by the DHCP server."
			::= { phyDHCPRangeEntry 4 }

		
		-- 1.3.6.1.4.1.4329.15.3.2.4.5.1.5
		phyDHCPRangeStatus OBJECT-TYPE
			SYNTAX RowStatus
			MAX-ACCESS read-write
			STATUS current
			DESCRIPTION
				"Row status variable for row operations on the phyDHCPRangeTable"
			::= { phyDHCPRangeEntry 5 }

		
		-- 1.3.6.1.4.1.4329.15.3.2.5
		vnManagerObjects OBJECT IDENTIFIER ::= { hiPathWirelessController 5 }

		
		-- 1.3.6.1.4.1.4329.15.3.2.5.1
		vnRole OBJECT-TYPE
			SYNTAX INTEGER
				{
				none(1),
				vnMgr(2),
				vnAgent(3)
				}
			MAX-ACCESS read-write
			STATUS current
			DESCRIPTION
				"Specifies the role of this HWC in inter-HWC mobility.  
				None indicates that mobile units cannot roam to or 
				from this HWC.  In any HWC cluster, only one HWC should
				be specified as vnMgr, all others should be have 
				vnRole = vnAgent."
			::= { vnManagerObjects 1 }

		
		-- 1.3.6.1.4.1.4329.15.3.2.5.2
		vnIfIndex OBJECT-TYPE
			SYNTAX Integer32
			MAX-ACCESS read-write
			STATUS current
			DESCRIPTION
				"ifIndex of the physical port where inter-HWC tunnels terminate.
				This field has meaning if vnRole is not none(1)"
			::= { vnManagerObjects 2 }

		
		-- 1.3.6.1.4.1.4329.15.3.2.5.3
		vnHeartbeatInterval OBJECT-TYPE
			SYNTAX Integer32
			MAX-ACCESS read-write
			STATUS current
			DESCRIPTION
				"The time interval between inter-HWC polling messages.
				This field has meaning if vnRole is not none(1)"
			::= { vnManagerObjects 3 }

		
		-- 1.3.6.1.4.1.4329.15.3.2.6
		ntpObjects OBJECT IDENTIFIER ::= { hiPathWirelessController 6 }

		
		-- 1.3.6.1.4.1.4329.15.3.2.6.1
		ntpEnabled OBJECT-TYPE
			SYNTAX TruthValue
			MAX-ACCESS read-write
			STATUS current
			DESCRIPTION
				"Enable or disables support for the Network Time Protocol (NTP)."
			::= { ntpObjects 1 }

		
		-- 1.3.6.1.4.1.4329.15.3.2.6.2
		ntpTimezone OBJECT-TYPE
			SYNTAX DisplayString
			MAX-ACCESS read-write
			STATUS current
			DESCRIPTION
				"Specifies the time zone where this HWC resides."
			::= { ntpObjects 2 }

		
		-- 1.3.6.1.4.1.4329.15.3.2.6.3
		ntpTimeServer1 OBJECT-TYPE
			SYNTAX DisplayString
			MAX-ACCESS read-write
			STATUS current
			DESCRIPTION
				"Primary NTP server."
			::= { ntpObjects 3 }

		
		-- 1.3.6.1.4.1.4329.15.3.2.6.4
		ntpTimeServer2 OBJECT-TYPE
			SYNTAX DisplayString
			MAX-ACCESS read-write
			STATUS current
			DESCRIPTION
				"Secondary NTP server."
			::= { ntpObjects 4 }

		
		-- 1.3.6.1.4.1.4329.15.3.2.6.5
		ntpTimeServer3 OBJECT-TYPE
			SYNTAX DisplayString
			MAX-ACCESS read-write
			STATUS current
			DESCRIPTION
				"Tertiary NTP server."
			::= { ntpObjects 5 }

		
		-- 1.3.6.1.4.1.4329.15.3.2.6.6
		ntpServerEnabled OBJECT-TYPE
			SYNTAX TruthValue
			MAX-ACCESS read-write
			STATUS current
			DESCRIPTION
				"Enable or disables support for controller as NTP server."
			::= { ntpObjects 6 }

		
		-- 1.3.6.1.4.1.4329.15.3.2.7
		controllerStats OBJECT IDENTIFIER ::= { hiPathWirelessController 7 }

		
		-- 1.3.6.1.4.1.4329.15.3.2.7.6
		tunnelCount OBJECT-TYPE
			SYNTAX Integer32
			MAX-ACCESS read-only
			STATUS current
			DESCRIPTION
				"Number of connections to other WirelessController controllers."
			::= { controllerStats 6 }

		
		-- 1.3.6.1.4.1.4329.15.3.2.7.7
		tunnelStatsTable OBJECT-TYPE
			SYNTAX SEQUENCE OF TunnelStatsEntry
			MAX-ACCESS not-accessible
			STATUS current
			DESCRIPTION
				"tunnelStatsTable contains a list of the IP tunnels connected 
				to this HWC for use in inter-HWC mobility."
			::= { controllerStats 7 }

		
		-- 1.3.6.1.4.1.4329.15.3.2.7.7.1
		tunnelStatsEntry OBJECT-TYPE
			SYNTAX TunnelStatsEntry
			MAX-ACCESS not-accessible
			STATUS current
			DESCRIPTION
				"Statistics for a mobility tunnel."
			INDEX { tunnelStartIP, tunnelEndIP }
			::= { tunnelStatsTable 1 }

		
		TunnelStatsEntry ::=
			SEQUENCE { 
				tunnelStartIP
					IpAddress,
				tunnelStartHWC
					OCTET STRING,
				tunnelEndIP
					IpAddress,
				tunnelEndHWC
					OCTET STRING,
				tunnelStatus
					INTEGER
			 }

		-- 1.3.6.1.4.1.4329.15.3.2.7.7.1.1
		tunnelStartIP OBJECT-TYPE
			SYNTAX IpAddress
			MAX-ACCESS read-write
			STATUS current
			DESCRIPTION
				"IP address for the start of the tunnel."
			::= { tunnelStatsEntry 1 }

		
		-- 1.3.6.1.4.1.4329.15.3.2.7.7.1.2
		tunnelStartHWC OBJECT-TYPE
			SYNTAX OCTET STRING
			MAX-ACCESS read-write
			STATUS current
			DESCRIPTION
				"Name of the access controller for the start of the tunnel."
			::= { tunnelStatsEntry 2 }

		
		-- 1.3.6.1.4.1.4329.15.3.2.7.7.1.3
		tunnelEndIP OBJECT-TYPE
			SYNTAX IpAddress
			MAX-ACCESS read-write
			STATUS current
			DESCRIPTION
				"IP address for the end of the tunnel."
			::= { tunnelStatsEntry 3 }

		
		-- 1.3.6.1.4.1.4329.15.3.2.7.7.1.4
		tunnelEndHWC OBJECT-TYPE
			SYNTAX OCTET STRING
			MAX-ACCESS read-write
			STATUS current
			DESCRIPTION
				"Name of the access controller for the end of the tunnel."
			::= { tunnelStatsEntry 4 }

		
		-- 1.3.6.1.4.1.4329.15.3.2.7.7.1.5
		tunnelStatus OBJECT-TYPE
			SYNTAX INTEGER
				{
				disconnected(1),
				connected(2)
				}
			MAX-ACCESS read-write
			STATUS current
			DESCRIPTION
				"Indicates if the mobility tunnel is up or down."
			::= { tunnelStatsEntry 5 }

		
		-- 1.3.6.1.4.1.4329.15.3.3
		virtualNetworks OBJECT IDENTIFIER ::= { hiPathWirelessMgmt 3 }

		
		-- 1.3.6.1.4.1.4329.15.3.3.1
		vnsConfigObjects OBJECT IDENTIFIER ::= { virtualNetworks 1 }

		
		-- 1.3.6.1.4.1.4329.15.3.3.1.1
		vnsCount OBJECT-TYPE
			SYNTAX Integer32
			MAX-ACCESS read-only
			STATUS current
			DESCRIPTION
				"Number of VNSes defined in vnsConfigTable."
			::= { vnsConfigObjects 1 }

		
		-- 1.3.6.1.4.1.4329.15.3.3.1.2
		vnsConfigTable OBJECT-TYPE
			SYNTAX SEQUENCE OF VnsConfigEntry
			MAX-ACCESS not-accessible
			STATUS current
			DESCRIPTION
				"Contains definitions of the Virtual Network Segments 
				defined on this WirelessController."
			::= { vnsConfigObjects 2 }

		
		-- 1.3.6.1.4.1.4329.15.3.3.1.2.1
		vnsConfigEntry OBJECT-TYPE
			SYNTAX VnsConfigEntry
			MAX-ACCESS not-accessible
			STATUS current
			DESCRIPTION
				"Configuration elements for a specific Virtual Network Segment."
			INDEX { vnsIfIndex }
			::= { vnsConfigTable 1 }

		
		VnsConfigEntry ::=
			SEQUENCE { 
				vnsDescription
					DisplayString,
				vnsAssignmentMode
					INTEGER,
				vnsMUSessionTimeout
					Integer32,
				vnsAllowMulticast
					TruthValue,
				vnsSSID
					DisplayString,
				vnsDomain
					DisplayString,
				vnsDNSServers
					DisplayString,
				vnsWINSServers
					DisplayString,
				vnsAuthModel
					INTEGER,
				vnsParentIfIndex
					Integer32,
				vnsMgmtTrafficEnable
					TruthValue,
				vnsUseDHCPRelay
					INTEGER,
				vns3rdPartyAP
					TruthValue,
				vnsStatus
					RowStatus,
				vnsMode
					INTEGER,
				vnsVlanID
					Integer32,
				vnsInterfaceName
					OCTET STRING,
				vnsMgmIpAddress
					IpAddress,
				vnsSuppressSSID
					TruthValue,
				vnsEnable11hSupport
					TruthValue,
				vnsApplyPowerBackOff
					TruthValue,
				vnsProcessClientIEReq
					TruthValue,
				vnsDLSSupportEnable
					TruthValue,
				vnsDLSAddress
					DisplayString,
				vnsDLSPort
					Integer32,
				vnsRateControlProfile
					DisplayString,
				vnsSessionAvailabilityEnable
					TruthValue
			 }

		-- 1.3.6.1.4.1.4329.15.3.3.1.2.1.1
		vnsDescription OBJECT-TYPE
			SYNTAX DisplayString
			MAX-ACCESS read-write
			STATUS current
			DESCRIPTION
				"Textual description of the VNS."
			::= { vnsConfigEntry 1 }

		
		-- 1.3.6.1.4.1.4329.15.3.3.1.2.1.2
		vnsAssignmentMode OBJECT-TYPE
			SYNTAX INTEGER
				{
				ssid(1),
				aaa(2)
				}
			MAX-ACCESS read-write
			STATUS current
			DESCRIPTION
				"Determines the method by which mobile units are assigned an 
				address within this VNS.  If vnsAssignmentMode = ssid, any 
				client with an SSID matching the VNS will be assigned an 
				address from this VNS.  If vnsAssignmentMode == aaa, then
				address assignment is not completed until after the user is
				authenticated."
			::= { vnsConfigEntry 2 }

		
		-- 1.3.6.1.4.1.4329.15.3.3.1.2.1.3
		vnsMUSessionTimeout OBJECT-TYPE
			SYNTAX Integer32
			MAX-ACCESS read-write
			STATUS current
			DESCRIPTION
				"Client session idle time out, in seconds."
			::= { vnsConfigEntry 3 }

		
		-- 1.3.6.1.4.1.4329.15.3.3.1.2.1.4
		vnsAllowMulticast OBJECT-TYPE
			SYNTAX TruthValue
			MAX-ACCESS read-write
			STATUS current
			DESCRIPTION
				"When true, allows IP multicast packets to be broadcast 
				to the clients on this VNS."
			::= { vnsConfigEntry 4 }

		
		-- 1.3.6.1.4.1.4329.15.3.3.1.2.1.5
		vnsSSID OBJECT-TYPE
			SYNTAX DisplayString
			MAX-ACCESS read-write
			STATUS current
			DESCRIPTION
				"Service Set Identifier (i.e. Network Name) that will be 
				configured on the AccessPoints associated with this VNS."
			::= { vnsConfigEntry 5 }

		
		-- 1.3.6.1.4.1.4329.15.3.3.1.2.1.6
		vnsDomain OBJECT-TYPE
			SYNTAX DisplayString
			MAX-ACCESS read-write
			STATUS current
			DESCRIPTION
				"Domain name to be supplied to the wireless clients if internal DHCP address assignment."
			::= { vnsConfigEntry 6 }

		
		-- 1.3.6.1.4.1.4329.15.3.3.1.2.1.7
		vnsDNSServers OBJECT-TYPE
			SYNTAX DisplayString
			MAX-ACCESS read-write
			STATUS current
			DESCRIPTION
				"List of DNSs to be supplied to the wireless clients if internal DHCP address assignment."
			::= { vnsConfigEntry 7 }

		
		-- 1.3.6.1.4.1.4329.15.3.3.1.2.1.8
		vnsWINSServers OBJECT-TYPE
			SYNTAX DisplayString
			MAX-ACCESS read-write
			STATUS current
			DESCRIPTION
				"List of WINSs to be supplied to the wireless clients if internal DHCP address assignment."
			::= { vnsConfigEntry 8 }

		
		-- 1.3.6.1.4.1.4329.15.3.3.1.2.1.9
		vnsAuthModel OBJECT-TYPE
			SYNTAX INTEGER
				{
				none(1),
				captivePortal(2),
				dot1X(3)
				}
			MAX-ACCESS read-write
			STATUS current
			DESCRIPTION
				"vnsAuthModel specifies the authentication method used 
				for clients in the VNS.  None indicates that the VNS is
				open, and no authentication is required.
				
				vnsAuthModel=captivePortal may only be specified for 
				a VNS with vnsAssignmentMode=ssid.  Likewise, 
				vnsAuthModel=dot1X may only be specified for a VNS with
				vnsAssignmentMode=aaa."
			::= { vnsConfigEntry 9 }

		
		-- 1.3.6.1.4.1.4329.15.3.3.1.2.1.10
		vnsParentIfIndex OBJECT-TYPE
			SYNTAX Integer32
			MAX-ACCESS read-write
			STATUS current
			DESCRIPTION
				"Specifies the ifIndex of the parent VNS, if this VNS
				is a child.				
				If this is a top level VNS, vnsParentIfIndex will return 
				null or 0."
			::= { vnsConfigEntry 10 }

		
		-- 1.3.6.1.4.1.4329.15.3.3.1.2.1.11
		vnsMgmtTrafficEnable OBJECT-TYPE
			SYNTAX TruthValue
			MAX-ACCESS read-write
			STATUS current
			DESCRIPTION
				"Specifies whether clients in the VNS have access 
				to HWC management elements."
			::= { vnsConfigEntry 11 }

		
		-- 1.3.6.1.4.1.4329.15.3.3.1.2.1.12
		vnsUseDHCPRelay OBJECT-TYPE
			SYNTAX INTEGER
				{
				none(0),
				dhcpRelay(1),
				localDhcp(2)
				}
			MAX-ACCESS read-write
			STATUS current
			DESCRIPTION
				"This variable indicates what type of DHCP is used for the VNS.
				none(0): No DHCP server on the VNS.
				dhcpRelay(1): Uses DHCP relay to reach the DHCP server.
				localDhcp(2): Uses local DHCP server on the controler."
			::= { vnsConfigEntry 12 }

		
		-- 1.3.6.1.4.1.4329.15.3.3.1.2.1.13
		vns3rdPartyAP OBJECT-TYPE
			SYNTAX TruthValue
			MAX-ACCESS read-write
			STATUS current
			DESCRIPTION
				"When true, specifies that the VNS contains 3rd party 
				access points.  Only one such VNS may be defined for
				a WirelessController."
			::= { vnsConfigEntry 13 }

		
		-- 1.3.6.1.4.1.4329.15.3.3.1.2.1.14
		vnsStatus OBJECT-TYPE
			SYNTAX RowStatus
			MAX-ACCESS read-write
			STATUS current
			DESCRIPTION
				"RowStatus variable for performing row operations on 
				vnsConfigTable."
			::= { vnsConfigEntry 14 }

		
		-- 1.3.6.1.4.1.4329.15.3.3.1.2.1.15
		vnsMode OBJECT-TYPE
			SYNTAX INTEGER
				{
				routed(1),
				bridgeAtController(2),
				bridgeAtAP(3),
				wds(4)
				}
			MAX-ACCESS read-write
			STATUS current
			DESCRIPTION
				"Type of traffic for this VNS. 
				routed(1): The traffic is routed at the controller.
				bridgeAtController(2): Traffic is bridged at controller.
				bridgeAtAP(3): Traffic is bridged at Access Points.
				wds(4): Wireless Distributed System (WDS) type of VNS.
				
				If VNS is type of wds(4), then only vnsSupressSSID, 
				vnsDescription and vnsSSID has meaning."
			DEFVAL { routed }
			::= { vnsConfigEntry 15 }

		
		-- 1.3.6.1.4.1.4329.15.3.3.1.2.1.16
		vnsVlanID OBJECT-TYPE
			SYNTAX Integer32 (-1..4094)
			MAX-ACCESS read-write
			STATUS current
			DESCRIPTION
				"VLAN tag for the packets trasmitted to/from of the VNS. This value has
				meaning if vnsMode is bridgeAtController(2) or bridgeAtAP(3).
				If vnsMode = bridgeAtController(2), tagging is done at controller.
				If vnsMode = bridgeAtAP(3), tagging is done at Access Point.
				Value ranges: (-1) it is not tagged, zero(0) means reserved, 1-4094 tag value."
			DEFVAL { -1 }
			::= { vnsConfigEntry 16 }

		
		-- 1.3.6.1.4.1.4329.15.3.3.1.2.1.17
		vnsInterfaceName OBJECT-TYPE
			SYNTAX OCTET STRING
			MAX-ACCESS read-write
			STATUS current
			DESCRIPTION
				"Physical interface to be used in the controller for trasmitting/receiving packets
				for the VNS. This value has meaning if vnsMode is bridgeAtController(2)."
			::= { vnsConfigEntry 17 }

		
		-- 1.3.6.1.4.1.4329.15.3.3.1.2.1.18
		vnsMgmIpAddress OBJECT-TYPE
			SYNTAX IpAddress
			MAX-ACCESS read-write
			STATUS current
			DESCRIPTION
				"IP address of the management port associated to this VNS.
				This value has meaning if vnsMode is bridgeAtController(2)."
			::= { vnsConfigEntry 18 }

		
		-- 1.3.6.1.4.1.4329.15.3.3.1.2.1.19
		vnsSuppressSSID OBJECT-TYPE
			SYNTAX TruthValue
			MAX-ACCESS read-write
			STATUS current
			DESCRIPTION
				"If set to true, this prevents this SSID from appearing in the beacon message."
			::= { vnsConfigEntry 19 }

		
		-- 1.3.6.1.4.1.4329.15.3.3.1.2.1.20
		vnsEnable11hSupport OBJECT-TYPE
			SYNTAX TruthValue
			MAX-ACCESS read-write
			STATUS current
			DESCRIPTION
				"If true, enables 802.11h support."
			::= { vnsConfigEntry 20 }

		
		-- 1.3.6.1.4.1.4329.15.3.3.1.2.1.21
		vnsApplyPowerBackOff OBJECT-TYPE
			SYNTAX TruthValue
			MAX-ACCESS read-write
			STATUS current
			DESCRIPTION
				"Indicates whether the AP will direct 802.11h-enabled clients to
				apply the same power back-off setting that the AP is using"
			::= { vnsConfigEntry 21 }

		
		-- 1.3.6.1.4.1.4329.15.3.3.1.2.1.22
		vnsProcessClientIEReq OBJECT-TYPE
			SYNTAX TruthValue
			MAX-ACCESS read-write
			STATUS current
			DESCRIPTION
				"If true, enables support for 802.11d client information request."
			::= { vnsConfigEntry 22 }

		
		-- 1.3.6.1.4.1.4329.15.3.3.1.2.1.23
		vnsDLSSupportEnable OBJECT-TYPE
			SYNTAX TruthValue
			MAX-ACCESS read-write
			STATUS current
			DESCRIPTION
				"If true, enables support for DLS Support. This value has 
				meaning only if vnsUseDHCPRelay is selected as localDhcp(2) and
				vnsMode is select as either routed(1) or bridgeAtController(2)."
			::= { vnsConfigEntry 23 }

		
		-- 1.3.6.1.4.1.4329.15.3.3.1.2.1.24
		vnsDLSAddress OBJECT-TYPE
			SYNTAX DisplayString
			MAX-ACCESS read-write
			STATUS current
			DESCRIPTION
				"DNS IP Address for DLS associated to this VNS. It could be IP address
				or Name"
			::= { vnsConfigEntry 24 }

		
		-- 1.3.6.1.4.1.4329.15.3.3.1.2.1.25
		vnsDLSPort OBJECT-TYPE
			SYNTAX Integer32
			MAX-ACCESS read-write
			STATUS current
			DESCRIPTION
				"DNS Port for DLS associated to this VNS."
			DEFVAL { 18443 }
			::= { vnsConfigEntry 25 }

		
		-- 1.3.6.1.4.1.4329.15.3.3.1.2.1.26
		vnsRateControlProfile OBJECT-TYPE
			SYNTAX DisplayString
			MAX-ACCESS read-write
			STATUS current
			DESCRIPTION
				"The Rate Control Profile that is referenced by this VNS."
			::= { vnsConfigEntry 26 }

		
		-- 1.3.6.1.4.1.4329.15.3.3.1.2.1.27
		vnsSessionAvailabilityEnable OBJECT-TYPE
			SYNTAX TruthValue
			MAX-ACCESS read-write
			STATUS current
			DESCRIPTION
				"To indicate if Session Availability feature is enabled."
			::= { vnsConfigEntry 27 }

		
		-- 1.3.6.1.4.1.4329.15.3.3.1.3
		vnsDHCPRangeTable OBJECT-TYPE
			SYNTAX SEQUENCE OF VnsDHCPRangeEntry
			MAX-ACCESS not-accessible
			STATUS current
			DESCRIPTION
				"vnsDHCPRangeTable contains the IP address ranges that DHCP
				will serve to clients associated with this VNS."
			::= { vnsConfigObjects 3 }

		
		-- 1.3.6.1.4.1.4329.15.3.3.1.3.1
		vnsDHCPRangeEntry OBJECT-TYPE
			SYNTAX VnsDHCPRangeEntry
			MAX-ACCESS not-accessible
			STATUS current
			DESCRIPTION
				"Configuration information for a DHCP range."
			INDEX { ifIndex, vnsDHCPRangeIndex }
			::= { vnsDHCPRangeTable 1 }

		
		VnsDHCPRangeEntry ::=
			SEQUENCE { 
				vnsDHCPRangeIndex
					Integer32,
				vnsDHCPRangeStart
					IpAddress,
				vnsDHCPRangeEnd
					IpAddress,
				vnsDHCPRangeType
					INTEGER,
				vnsDHCPRangeStatus
					RowStatus
			 }

		-- 1.3.6.1.4.1.4329.15.3.3.1.3.1.1
		vnsDHCPRangeIndex OBJECT-TYPE
			SYNTAX Integer32 (1..2147483647)
			MAX-ACCESS read-write
			STATUS current
			DESCRIPTION
				"Index for the DHCP row element."
			::= { vnsDHCPRangeEntry 1 }

		
		-- 1.3.6.1.4.1.4329.15.3.3.1.3.1.2
		vnsDHCPRangeStart OBJECT-TYPE
			SYNTAX IpAddress
			MAX-ACCESS read-write
			STATUS current
			DESCRIPTION
				"First IP address in the range."
			::= { vnsDHCPRangeEntry 2 }

		
		-- 1.3.6.1.4.1.4329.15.3.3.1.3.1.3
		vnsDHCPRangeEnd OBJECT-TYPE
			SYNTAX IpAddress
			MAX-ACCESS read-write
			STATUS current
			DESCRIPTION
				"Last IP address in the range."
			::= { vnsDHCPRangeEntry 3 }

		
		-- 1.3.6.1.4.1.4329.15.3.3.1.3.1.4
		vnsDHCPRangeType OBJECT-TYPE
			SYNTAX INTEGER
				{
				inclusion(1),
				exclusion(2)
				}
			MAX-ACCESS read-write
			STATUS current
			DESCRIPTION
				"Determines whether addresses in the specified range will 
				be included, or excluded by the DHCP server."
			::= { vnsDHCPRangeEntry 4 }

		
		-- 1.3.6.1.4.1.4329.15.3.3.1.3.1.5
		vnsDHCPRangeStatus OBJECT-TYPE
			SYNTAX RowStatus
			MAX-ACCESS read-write
			STATUS current
			DESCRIPTION
				"Row status variable for row operations on the vnsDHCPRangeTable"
			::= { vnsDHCPRangeEntry 5 }

		
		-- 1.3.6.1.4.1.4329.15.3.3.1.4
		vnsCaptivePortalTable OBJECT-TYPE
			SYNTAX SEQUENCE OF VnsCaptivePortalEntry
			MAX-ACCESS not-accessible
			STATUS current
			DESCRIPTION
				"Details of the Captive Portal login page for 
				VNSes that have vnsAssignment=ssid and 
				vnsAuthModel=captivePortal."
			::= { vnsConfigObjects 4 }

		
		-- 1.3.6.1.4.1.4329.15.3.3.1.4.1
		vnsCaptivePortalEntry OBJECT-TYPE
			SYNTAX VnsCaptivePortalEntry
			MAX-ACCESS not-accessible
			STATUS current
			DESCRIPTION
				"Captive Portal Information for the VNS."
			INDEX { ifIndex }
			::= { vnsCaptivePortalTable 1 }

		
		VnsCaptivePortalEntry ::=
			SEQUENCE { 
				cpURL
					DisplayString,
				cpLoginLabel
					DisplayString,
				cpPasswordLabel
					DisplayString,
				cpHeaderURL
					DisplayString,
				cpFooterURL
					DisplayString,
				cpMessage
					DisplayString,
				cpReplaceGatewayWithFQDN
					DisplayString,
				cpDefaultRedirectionURL
					DisplayString,
				cpConnectionIP
					IpAddress,
				cpConnectionPort
					Integer32,
				cpSharedSecret
					OCTET STRING,
				cpLogOff
					INTEGER,
				cpStatusCheck
					INTEGER,
				cpType
					INTEGER
			 }

		-- 1.3.6.1.4.1.4329.15.3.3.1.4.1.1
		cpURL OBJECT-TYPE
			SYNTAX DisplayString
			MAX-ACCESS read-write
			STATUS current
			DESCRIPTION
				"Redirect URL of the Captive Portal login page."
			::= { vnsCaptivePortalEntry 1 }

		
		-- 1.3.6.1.4.1.4329.15.3.3.1.4.1.2
		cpLoginLabel OBJECT-TYPE
			SYNTAX DisplayString
			MAX-ACCESS read-write
			STATUS current
			DESCRIPTION
				"Label that appears in front of the login field
				on the Captive Portal login page."
			::= { vnsCaptivePortalEntry 2 }

		
		-- 1.3.6.1.4.1.4329.15.3.3.1.4.1.3
		cpPasswordLabel OBJECT-TYPE
			SYNTAX DisplayString
			MAX-ACCESS read-write
			STATUS current
			DESCRIPTION
				"Label that appears in front of the password field
				on the Captive Portal login page."
			::= { vnsCaptivePortalEntry 3 }

		
		-- 1.3.6.1.4.1.4329.15.3.3.1.4.1.4
		cpHeaderURL OBJECT-TYPE
			SYNTAX DisplayString
			MAX-ACCESS read-write
			STATUS current
			DESCRIPTION
				"URL of the Captive Portal header."
			::= { vnsCaptivePortalEntry 4 }

		
		-- 1.3.6.1.4.1.4329.15.3.3.1.4.1.5
		cpFooterURL OBJECT-TYPE
			SYNTAX DisplayString
			MAX-ACCESS read-write
			STATUS current
			DESCRIPTION
				"URL of the Captive Portal footer."
			::= { vnsCaptivePortalEntry 5 }

		
		-- 1.3.6.1.4.1.4329.15.3.3.1.4.1.6
		cpMessage OBJECT-TYPE
			SYNTAX DisplayString
			MAX-ACCESS read-write
			STATUS current
			DESCRIPTION
				"A welcome message, or set of instructions that is to 
				appear on the Captive Portal login page."
			::= { vnsCaptivePortalEntry 6 }

		
		-- 1.3.6.1.4.1.4329.15.3.3.1.4.1.7
		cpReplaceGatewayWithFQDN OBJECT-TYPE
			SYNTAX DisplayString
			MAX-ACCESS read-write
			STATUS current
			DESCRIPTION
				"Fully Qualified Domain Name (FQDN) to be used as the gateway IP address."
			::= { vnsCaptivePortalEntry 7 }

		
		-- 1.3.6.1.4.1.4329.15.3.3.1.4.1.8
		cpDefaultRedirectionURL OBJECT-TYPE
			SYNTAX DisplayString
			MAX-ACCESS read-write
			STATUS current
			DESCRIPTION
				"Default Redirect URL of the Captive Portal login page."
			::= { vnsCaptivePortalEntry 8 }

		
		-- 1.3.6.1.4.1.4329.15.3.3.1.4.1.9
		cpConnectionIP OBJECT-TYPE
			SYNTAX IpAddress
			MAX-ACCESS read-write
			STATUS current
			DESCRIPTION
				"IP address of the Controller interface for Captive Portal."
			::= { vnsCaptivePortalEntry 9 }

		
		-- 1.3.6.1.4.1.4329.15.3.3.1.4.1.10
		cpConnectionPort OBJECT-TYPE
			SYNTAX Integer32
			MAX-ACCESS read-write
			STATUS current
			DESCRIPTION
				"Port number on the cpConnectionIP interface."
			::= { vnsCaptivePortalEntry 10 }

		
		-- 1.3.6.1.4.1.4329.15.3.3.1.4.1.11
		cpSharedSecret OBJECT-TYPE
			SYNTAX OCTET STRING
			MAX-ACCESS read-write
			STATUS current
			DESCRIPTION
				"Secret Key to be used to encrypt the information passed between the
				Controller and the external web server. It is the password common to
				both Controller and the external web server."
			::= { vnsCaptivePortalEntry 11 }

		
		-- 1.3.6.1.4.1.4329.15.3.3.1.4.1.12
		cpLogOff OBJECT-TYPE
			SYNTAX INTEGER
				{
				off(0),
				on(1)
				}
			MAX-ACCESS read-write
			STATUS current
			DESCRIPTION
				"Toggles the display of logoff popup screen, allowing users to control their logoff."
			::= { vnsCaptivePortalEntry 12 }

		
		-- 1.3.6.1.4.1.4329.15.3.3.1.4.1.13
		cpStatusCheck OBJECT-TYPE
			SYNTAX INTEGER
				{
				off(0),
				on(1)
				}
			MAX-ACCESS read-write
			STATUS current
			DESCRIPTION
				"Toggles the display of popup window with session statistics for users to
				monitor their usage and time left in session."
			::= { vnsCaptivePortalEntry 13 }

		
		-- 1.3.6.1.4.1.4329.15.3.3.1.4.1.14
		cpType OBJECT-TYPE
			SYNTAX INTEGER
				{
				none(1),
				internal(2),
				external(4)
				}
			MAX-ACCESS read-write
			STATUS current
			DESCRIPTION
				"Type of captive portal is enabled for the selected VNS."
			::= { vnsCaptivePortalEntry 14 }

		
		-- 1.3.6.1.4.1.4329.15.3.3.1.5
		vnsRadiusServerTable OBJECT-TYPE
			SYNTAX SEQUENCE OF VnsRadiusServerEntry
			MAX-ACCESS not-accessible
			STATUS current
			DESCRIPTION
				"List of RADIUS servers to be utilized for authentication in the VNS."
			::= { vnsConfigObjects 5 }

		
		-- 1.3.6.1.4.1.4329.15.3.3.1.5.1
		vnsRadiusServerEntry OBJECT-TYPE
			SYNTAX VnsRadiusServerEntry
			MAX-ACCESS not-accessible
			STATUS current
			DESCRIPTION
				"Configuration information for a RADIUS server."
			INDEX { ifIndex, vnsRadiusServerName }
			::= { vnsRadiusServerTable 1 }

		
		VnsRadiusServerEntry ::=
			SEQUENCE { 
				vnsRadiusServerName
					DisplayString,
				vnsRadiusServerPort
					Integer32,
				vnsRadiusServerRetries
					Integer32,
				vnsRadiusServerTimeout
					Integer32,
				vnsRadiusServerSharedSecret
					DisplayString,
				vnsRadiusServerNASIdentifier
					DisplayString,
				vnsRadiusServerAuthType
					INTEGER,
				vnsRadiusServerRowStatus
					RowStatus,
				vnsRadiusServerNasAddress
					IpAddress
			 }

		-- 1.3.6.1.4.1.4329.15.3.3.1.5.1.1
		vnsRadiusServerName OBJECT-TYPE
			SYNTAX DisplayString (SIZE (0..64))
			MAX-ACCESS read-write
			STATUS current
			DESCRIPTION
				"Name of the RADIUS server."
			::= { vnsRadiusServerEntry 1 }

		
		-- 1.3.6.1.4.1.4329.15.3.3.1.5.1.2
		vnsRadiusServerPort OBJECT-TYPE
			SYNTAX Integer32
			MAX-ACCESS read-write
			STATUS current
			DESCRIPTION
				"Port number for the RADIUS server."
			::= { vnsRadiusServerEntry 2 }

		
		-- 1.3.6.1.4.1.4329.15.3.3.1.5.1.3
		vnsRadiusServerRetries OBJECT-TYPE
			SYNTAX Integer32
			MAX-ACCESS read-write
			STATUS current
			DESCRIPTION
				"Number of retries for a RADIUS authentication request."
			::= { vnsRadiusServerEntry 3 }

		
		-- 1.3.6.1.4.1.4329.15.3.3.1.5.1.4
		vnsRadiusServerTimeout OBJECT-TYPE
			SYNTAX Integer32
			MAX-ACCESS read-write
			STATUS current
			DESCRIPTION
				"Delay between requests."
			::= { vnsRadiusServerEntry 4 }

		
		-- 1.3.6.1.4.1.4329.15.3.3.1.5.1.5
		vnsRadiusServerSharedSecret OBJECT-TYPE
			SYNTAX DisplayString
			MAX-ACCESS read-write
			STATUS current
			DESCRIPTION
				"Shared secret to be used between the NAS and RADIUS server."
			::= { vnsRadiusServerEntry 5 }

		
		-- 1.3.6.1.4.1.4329.15.3.3.1.5.1.6
		vnsRadiusServerNASIdentifier OBJECT-TYPE
			SYNTAX DisplayString
			MAX-ACCESS read-write
			STATUS current
			DESCRIPTION
				"NAS identifier to be included in RADIUS request."
			::= { vnsRadiusServerEntry 6 }

		
		-- 1.3.6.1.4.1.4329.15.3.3.1.5.1.7
		vnsRadiusServerAuthType OBJECT-TYPE
			SYNTAX INTEGER
				{
				pap(0),
				chap(1),
				msChap(2),
				msChapV2(3),
				notApplicable(4)
				}
			MAX-ACCESS read-write
			STATUS current
			DESCRIPTION
				"Challenge mechanism for the request."
			::= { vnsRadiusServerEntry 7 }

		
		-- 1.3.6.1.4.1.4329.15.3.3.1.5.1.8
		vnsRadiusServerRowStatus OBJECT-TYPE
			SYNTAX RowStatus
			MAX-ACCESS read-write
			STATUS current
			DESCRIPTION
				"RowStatus value for manipulating vnsRADIUSServerTable."
			::= { vnsRadiusServerEntry 8 }

		
		-- 1.3.6.1.4.1.4329.15.3.3.1.5.1.9
		vnsRadiusServerNasAddress OBJECT-TYPE
			SYNTAX IpAddress
			MAX-ACCESS read-write
			STATUS current
			DESCRIPTION
				"NAS address to be included in RADIUS request."
			::= { vnsRadiusServerEntry 9 }

		
		-- 1.3.6.1.4.1.4329.15.3.3.1.6
		vnsFilterIDTable OBJECT-TYPE
			SYNTAX SEQUENCE OF VnsFilterIDEntry
			MAX-ACCESS not-accessible
			STATUS current
			DESCRIPTION
				"Table of names filters for a VNS."
			::= { vnsConfigObjects 6 }

		
		-- 1.3.6.1.4.1.4329.15.3.3.1.6.1
		vnsFilterIDEntry OBJECT-TYPE
			SYNTAX VnsFilterIDEntry
			MAX-ACCESS not-accessible
			STATUS current
			DESCRIPTION
				"Name of a specific filter in the VNS."
			INDEX { ifIndex, vnsFilterID }
			::= { vnsFilterIDTable 1 }

		
		VnsFilterIDEntry ::=
			SEQUENCE { 
				vnsFilterID
					DisplayString,
				vnsFilterIDStatus
					RowStatus
			 }

		-- 1.3.6.1.4.1.4329.15.3.3.1.6.1.1
		vnsFilterID OBJECT-TYPE
			SYNTAX DisplayString
			MAX-ACCESS read-write
			STATUS current
			DESCRIPTION
				"Filter names."
			::= { vnsFilterIDEntry 1 }

		
		-- 1.3.6.1.4.1.4329.15.3.3.1.6.1.2
		vnsFilterIDStatus OBJECT-TYPE
			SYNTAX RowStatus
			MAX-ACCESS read-write
			STATUS current
			DESCRIPTION
				"RowStatus for operating on vnsFilterIDTable."
			::= { vnsFilterIDEntry 2 }

		
		-- 1.3.6.1.4.1.4329.15.3.3.1.7
		vnsFilterRuleTable OBJECT-TYPE
			SYNTAX SEQUENCE OF VnsFilterRuleEntry
			MAX-ACCESS not-accessible
			STATUS current
			DESCRIPTION
				"Table containing specific filters for a named filter."
			::= { vnsConfigObjects 7 }

		
		-- 1.3.6.1.4.1.4329.15.3.3.1.7.1
		vnsFilterRuleEntry OBJECT-TYPE
			SYNTAX VnsFilterRuleEntry
			MAX-ACCESS not-accessible
			STATUS current
			DESCRIPTION
				"Filter elements for an individual VNS filter."
			INDEX { ifIndex, vnsFilterID, vnsFilterRuleOrder }
			::= { vnsFilterRuleTable 1 }

		
		VnsFilterRuleEntry ::=
			SEQUENCE { 
				vnsFilterRuleOrder
					Integer32,
				vnsFilterRuleDirection
					INTEGER,
				vnsFilterRuleAction
					INTEGER,
				vnsFilterRuleIPAddress
					IpAddress,
				vnsFilterRulePortLow
					Integer32,
				vnsFilterRulePortHigh
					Integer32,
				vnsFilterRuleProtocol
					INTEGER,
				vnsFilterRuleEtherType
					INTEGER,
				vnsFilterRuleStatus
					RowStatus
			 }

		-- 1.3.6.1.4.1.4329.15.3.3.1.7.1.1
		vnsFilterRuleOrder OBJECT-TYPE
			SYNTAX Integer32 (1..65532)
			MAX-ACCESS read-write
			STATUS current
			DESCRIPTION
				"Position of the filter in the filter list."
			::= { vnsFilterRuleEntry 1 }

		
		-- 1.3.6.1.4.1.4329.15.3.3.1.7.1.2
		vnsFilterRuleDirection OBJECT-TYPE
			SYNTAX INTEGER
				{
				in(1),
				out(2),
				both(3)
				}
			MAX-ACCESS read-write
			STATUS current
			DESCRIPTION
				"Traffic direction to apply the rule."
			::= { vnsFilterRuleEntry 2 }

		
		-- 1.3.6.1.4.1.4329.15.3.3.1.7.1.3
		vnsFilterRuleAction OBJECT-TYPE
			SYNTAX INTEGER
				{
				allow(1),
				disallow(2)
				}
			MAX-ACCESS read-write
			STATUS current
			DESCRIPTION
				"Allow or deny traffic for the filter."
			::= { vnsFilterRuleEntry 3 }

		
		-- 1.3.6.1.4.1.4329.15.3.3.1.7.1.4
		vnsFilterRuleIPAddress OBJECT-TYPE
			SYNTAX IpAddress
			MAX-ACCESS read-write
			STATUS current
			DESCRIPTION
				"IP address to apply the filter."
			::= { vnsFilterRuleEntry 4 }

		
		-- 1.3.6.1.4.1.4329.15.3.3.1.7.1.5
		vnsFilterRulePortLow OBJECT-TYPE
			SYNTAX Integer32
			MAX-ACCESS read-write
			STATUS current
			DESCRIPTION
				"Low port number for the filter."
			::= { vnsFilterRuleEntry 5 }

		
		-- 1.3.6.1.4.1.4329.15.3.3.1.7.1.6
		vnsFilterRulePortHigh OBJECT-TYPE
			SYNTAX Integer32
			MAX-ACCESS read-write
			STATUS current
			DESCRIPTION
				"High port number for the filter."
			::= { vnsFilterRuleEntry 6 }

		
		-- 1.3.6.1.4.1.4329.15.3.3.1.7.1.7
		vnsFilterRuleProtocol OBJECT-TYPE
			SYNTAX INTEGER
				{
				notApplicable(1),
				tcp(2),
				udp(3),
				icmp(4),
				ipsec-esp(5),
				ipsec-ah(6)
				}
			MAX-ACCESS read-write
			STATUS current
			DESCRIPTION
				"Specific protocol to filter."
			::= { vnsFilterRuleEntry 7 }

		
		-- 1.3.6.1.4.1.4329.15.3.3.1.7.1.8
		vnsFilterRuleEtherType OBJECT-TYPE
			SYNTAX INTEGER
				{
				ip(1),
				arp(2),
				rarp(3)
				}
			MAX-ACCESS read-write
			STATUS current
			DESCRIPTION
				"Specific ethertype to filter."
			::= { vnsFilterRuleEntry 8 }

		
		-- 1.3.6.1.4.1.4329.15.3.3.1.7.1.9
		vnsFilterRuleStatus OBJECT-TYPE
			SYNTAX RowStatus
			MAX-ACCESS read-write
			STATUS current
			DESCRIPTION
				"RowStatus value for the vnsFilterRuleTable."
			::= { vnsFilterRuleEntry 9 }

		
		-- 1.3.6.1.4.1.4329.15.3.3.1.8
		vnsPrivacyTable OBJECT-TYPE
			SYNTAX SEQUENCE OF VnsPrivacyEntry
			MAX-ACCESS not-accessible
			STATUS current
			DESCRIPTION
				"Table of privacy settings for the VNS."
			::= { vnsConfigObjects 8 }

		
		-- 1.3.6.1.4.1.4329.15.3.3.1.8.1
		vnsPrivacyEntry OBJECT-TYPE
			SYNTAX VnsPrivacyEntry
			MAX-ACCESS not-accessible
			STATUS current
			DESCRIPTION
				"Configuration values for a specific privacy setting."
			INDEX { ifIndex }
			::= { vnsPrivacyTable 1 }

		
		VnsPrivacyEntry ::=
			SEQUENCE { 
				vnsPrivWEPKeyType
					INTEGER,
				vnsPrivDynamicRekeyFrequency
					Integer32,
				vnsPrivWEPKeyLength
					Integer32,
				vnsPrivWPA1Enabled
					TruthValue,
				vnsPrivUseSharedKey
					TruthValue,
				vnsPrivWPASharedKey
					DisplayString,
				vnsPrivWPA2Enabled
					TruthValue
			 }

		-- 1.3.6.1.4.1.4329.15.3.3.1.8.1.1
		vnsPrivWEPKeyType OBJECT-TYPE
			SYNTAX INTEGER
				{
				none(1),
				wepstatic(2),
				wpapsk(3),
				dynamic(4),
				wpa(5)
				}
			MAX-ACCESS read-write
			STATUS current
			DESCRIPTION
				"Type of key in use. 
				none(1) = not cofigured, 
				wepstatic(2) = static WEP, 
				wpapsk(3) = WPA Pre-Shared Key,
				dynamic(4) = dynamically assigned,
				wpa(5) = WPA."
			::= { vnsPrivacyEntry 1 }

		
		-- 1.3.6.1.4.1.4329.15.3.3.1.8.1.2
		vnsPrivDynamicRekeyFrequency OBJECT-TYPE
			SYNTAX Integer32
			MAX-ACCESS read-write
			STATUS current
			DESCRIPTION
				"Dynamic WEP re-keying frequency, in seconds.  Setting this 
				value to 0 disables rekeying.
				
				This value is only meaningful if vnsPrivWEPKeyType = wpapsk(3).
				For any other values of vnsPrivWEPKeyType, reading or setting 
				this value will return an unsuccessful status and will return 
				a value of null or zero."
			::= { vnsPrivacyEntry 2 }

		
		-- 1.3.6.1.4.1.4329.15.3.3.1.8.1.3
		vnsPrivWEPKeyLength OBJECT-TYPE
			SYNTAX Integer32
			MAX-ACCESS read-write
			STATUS current
			DESCRIPTION
				"WEP key length,  64, 128, or 152 bits.  If vnsPrivWEPKeyType
				is none, reading or setting this value will return an 
				unsuccessful status and will return a value of null or zero."
			::= { vnsPrivacyEntry 3 }

		
		-- 1.3.6.1.4.1.4329.15.3.3.1.8.1.4
		vnsPrivWPA1Enabled OBJECT-TYPE
			SYNTAX TruthValue
			MAX-ACCESS read-write
			STATUS current
			DESCRIPTION
				"Enables WPA.1 (Wi-Fi Protected Access)."
			::= { vnsPrivacyEntry 4 }

		
		-- 1.3.6.1.4.1.4329.15.3.3.1.8.1.5
		vnsPrivUseSharedKey OBJECT-TYPE
			SYNTAX TruthValue
			MAX-ACCESS read-write
			STATUS current
			DESCRIPTION
				"Enables the use of WPA shared key for this VNS."
			::= { vnsPrivacyEntry 5 }

		
		-- 1.3.6.1.4.1.4329.15.3.3.1.8.1.6
		vnsPrivWPASharedKey OBJECT-TYPE
			SYNTAX DisplayString
			MAX-ACCESS read-write
			STATUS current
			DESCRIPTION
				"The value of the WPA shared key for this VNS.  
				This value is logically WRITE ONLY.  Attempts 
				to read this value shall return unsuccessful 
				status and values of null or zero."
			::= { vnsPrivacyEntry 6 }

		
		-- 1.3.6.1.4.1.4329.15.3.3.1.8.1.7
		vnsPrivWPA2Enabled OBJECT-TYPE
			SYNTAX TruthValue
			MAX-ACCESS read-write
			STATUS current
			DESCRIPTION
				"When true, WPA v.2 support is enabled."
			::= { vnsPrivacyEntry 7 }

		
		-- 1.3.6.1.4.1.4329.15.3.3.1.9
		vnsWEPKeyTable OBJECT-TYPE
			SYNTAX SEQUENCE OF VnsWEPKeyEntry
			MAX-ACCESS not-accessible
			STATUS current
			DESCRIPTION
				"Table of WEP key entries for a static WEP definition."
			::= { vnsConfigObjects 9 }

		
		-- 1.3.6.1.4.1.4329.15.3.3.1.9.1
		vnsWEPKeyEntry OBJECT-TYPE
			SYNTAX VnsWEPKeyEntry
			MAX-ACCESS not-accessible
			STATUS current
			DESCRIPTION
				"WEP key for a single entry in the table."
			INDEX { ifIndex, vnsWEPKeyIndex }
			::= { vnsWEPKeyTable 1 }

		
		VnsWEPKeyEntry ::=
			SEQUENCE { 
				vnsWEPKeyIndex
					Integer32,
				vnsWEPKeyValue
					WEPKeytype
			 }

		-- 1.3.6.1.4.1.4329.15.3.3.1.9.1.1
		vnsWEPKeyIndex OBJECT-TYPE
			SYNTAX Integer32 (1..4)
			MAX-ACCESS read-write
			STATUS current
			DESCRIPTION
				"Table index for the WEP key."
			::= { vnsWEPKeyEntry 1 }

		
		-- 1.3.6.1.4.1.4329.15.3.3.1.9.1.2
		vnsWEPKeyValue OBJECT-TYPE
			SYNTAX WEPKeytype
			MAX-ACCESS read-write
			STATUS current
			DESCRIPTION
				"Value of a WEP key for this VNS.
				
				This value is logically WRITE ONLY.  Attempts 
				to read this value shall return unsuccessful 
				status and values of null or zero."
			::= { vnsWEPKeyEntry 2 }

		
		-- 1.3.6.1.4.1.4329.15.3.3.1.10
		vns3rdPartyAPTable OBJECT-TYPE
			SYNTAX SEQUENCE OF Vns3rdPartyAPEntry
			MAX-ACCESS not-accessible
			STATUS current
			DESCRIPTION
				"Contains a list of 3rd Party access points for 
				the HWC."
			::= { vnsConfigObjects 10 }

		
		-- 1.3.6.1.4.1.4329.15.3.3.1.10.1
		vns3rdPartyAPEntry OBJECT-TYPE
			SYNTAX Vns3rdPartyAPEntry
			MAX-ACCESS not-accessible
			STATUS current
			DESCRIPTION
				"Configuration information for a 3rd party access point."
			INDEX { ifIndex, apMacAddress }
			::= { vns3rdPartyAPTable 1 }

		
		Vns3rdPartyAPEntry ::=
			SEQUENCE { 
				apMacAddress
					MacAddress,
				apIpAddress
					IpAddress
			 }

		-- 1.3.6.1.4.1.4329.15.3.3.1.10.1.1
		apMacAddress OBJECT-TYPE
			SYNTAX MacAddress
			MAX-ACCESS read-write
			STATUS current
			DESCRIPTION
				"Ethernet MAC address of the 3rd party access point."
			::= { vns3rdPartyAPEntry 1 }

		
		-- 1.3.6.1.4.1.4329.15.3.3.1.10.1.2
		apIpAddress OBJECT-TYPE
			SYNTAX IpAddress
			MAX-ACCESS read-write
			STATUS current
			DESCRIPTION
				"IP address of the 3rd party access point."
			::= { vns3rdPartyAPEntry 2 }

		
		-- 1.3.6.1.4.1.4329.15.3.3.1.11
		vnsQoSTable OBJECT-TYPE
			SYNTAX SEQUENCE OF VnsQoSEntry
			MAX-ACCESS not-accessible
			STATUS current
			DESCRIPTION
				"This table contains list of per-VNS QoS related configuration."
			::= { vnsConfigObjects 11 }

		
		-- 1.3.6.1.4.1.4329.15.3.3.1.11.1
		vnsQoSEntry OBJECT-TYPE
			SYNTAX VnsQoSEntry
			MAX-ACCESS not-accessible
			STATUS current
			DESCRIPTION
				"An entry related to QoS configuration for the VNS indexed by vnsIfIndex."
			INDEX { vnsIfIndex }
			::= { vnsQoSTable 1 }

		
		VnsQoSEntry ::=
			SEQUENCE { 
				vnsQoSWirelessLegacyFlag
					INTEGER,
				vnsQoSWirelessWMMFlag
					INTEGER,
				vnsQoSWireless80211eFlag
					INTEGER,
				vnsQoSWirelessTurboVoiceFlag
					INTEGER,
				vnsQoSPriorityOverrideFlag
					INTEGER,
				vnsQoSPriorityOverrideSC
					INTEGER,
				vnsQoSPriorityOverrideDSCP
					Integer32,
				vnsQoSClassificationServiceClass
					OCTET STRING,
				vnsQoSWirelessEnableUAPSD
					INTEGER,
				vnsQoSWirelessUseAdmControlVoice
					INTEGER,
				vnsQoSWirelessUseAdmControlVideo
					INTEGER,
				vnsQoSWirelessULPolicerAction
					INTEGER,
				vnsQoSWirelessDLPolicerAction
					INTEGER
			 }

		-- 1.3.6.1.4.1.4329.15.3.3.1.11.1.1
		vnsQoSWirelessLegacyFlag OBJECT-TYPE
			SYNTAX INTEGER
				{
				enabled(1),
				disabled(2)
				}
			MAX-ACCESS read-write
			STATUS current
			DESCRIPTION
				"This variable is used to enable/disable legacy QoS feature."
			::= { vnsQoSEntry 1 }

		
		-- 1.3.6.1.4.1.4329.15.3.3.1.11.1.2
		vnsQoSWirelessWMMFlag OBJECT-TYPE
			SYNTAX INTEGER
				{
				enabled(1),
				disabled(2)
				}
			MAX-ACCESS read-write
			STATUS current
			DESCRIPTION
				"This variable is used to enable/disable WMM feature."
			::= { vnsQoSEntry 2 }

		
		-- 1.3.6.1.4.1.4329.15.3.3.1.11.1.3
		vnsQoSWireless80211eFlag OBJECT-TYPE
			SYNTAX INTEGER
				{
				enabled(1),
				disabled(2)
				}
			MAX-ACCESS read-write
			STATUS current
			DESCRIPTION
				"This variable is used to enable/disable 802.11e feature."
			::= { vnsQoSEntry 3 }

		
		-- 1.3.6.1.4.1.4329.15.3.3.1.11.1.4
		vnsQoSWirelessTurboVoiceFlag OBJECT-TYPE
			SYNTAX INTEGER
				{
				enabled(1),
				disabled(2)
				}
			MAX-ACCESS read-write
			STATUS current
			DESCRIPTION
				"This variable is used to enable/disable turbo feature."
			::= { vnsQoSEntry 4 }

		
		-- 1.3.6.1.4.1.4329.15.3.3.1.11.1.5
		vnsQoSPriorityOverrideFlag OBJECT-TYPE
			SYNTAX INTEGER
				{
				enabled(1),
				disabled(2)
				}
			MAX-ACCESS read-write
			STATUS current
			DESCRIPTION
				"Enable/disable the use of DSCP to override Servic Class (SC) value."
			DEFVAL { disabled }
			::= { vnsQoSEntry 5 }

		
		-- 1.3.6.1.4.1.4329.15.3.3.1.11.1.6
		vnsQoSPriorityOverrideSC OBJECT-TYPE
			SYNTAX INTEGER
				{
				background(0),
				bestEffort(1),
				bronze(2),
				silver(3),
				gold(4),
				platinum(5),
				premiumVoice(6),
				networkControl(7)
				}
			MAX-ACCESS read-write
			STATUS current
			DESCRIPTION
				"Service class (SC) of the override value. This field has a meaning
				if vnsQoSPriorityOverrideFlag is enabled."
			DEFVAL { background }
			::= { vnsQoSEntry 6 }

		
		-- 1.3.6.1.4.1.4329.15.3.3.1.11.1.7
		vnsQoSPriorityOverrideDSCP OBJECT-TYPE
			SYNTAX Integer32 (0..63)
			MAX-ACCESS read-write
			STATUS current
			DESCRIPTION
				"DSCP override value to be used for the service class. This field has a meaning
				if vnsQoSPriorityOverrideFlag is enabled."
			DEFVAL { 0 }
			::= { vnsQoSEntry 7 }

		
		-- 1.3.6.1.4.1.4329.15.3.3.1.11.1.8
		vnsQoSClassificationServiceClass OBJECT-TYPE
			SYNTAX OCTET STRING (SIZE (0..64))
			MAX-ACCESS read-write
			STATUS current
			DESCRIPTION
				"Service Class value for the DSCP code. This field is 64-bytes long. Each
				byte represents mapping between DSCP and Service Class. Position of each
				byte in the array represents DSCP code and the content of each byte 
				represents the service class value for that DSCP code. For example, 
				second byte represents DSCP code 1 and its value represents SC value.
				Value for each byte is equivalent to either of:
				background = 0, 
				bestEffort = 1, 
				bronze = 2,
				silver = 3,
				gold = 4,
				platinum = 5,
				premiumVoice = 6,
				networkControl = 7
				"
			::= { vnsQoSEntry 8 }

		
		-- 1.3.6.1.4.1.4329.15.3.3.1.11.1.9
		vnsQoSWirelessEnableUAPSD OBJECT-TYPE
			SYNTAX INTEGER
				{
				enabled(1),
				disabled(2)
				}
			MAX-ACCESS read-write
			STATUS current
			DESCRIPTION
				"This variable is used to enable/disable U-APSD feature."
			::= { vnsQoSEntry 9 }

		
		-- 1.3.6.1.4.1.4329.15.3.3.1.11.1.10
		vnsQoSWirelessUseAdmControlVoice OBJECT-TYPE
			SYNTAX INTEGER
				{
				enabled(1),
				disabled(2)
				}
			MAX-ACCESS read-write
			STATUS current
			DESCRIPTION
				"If enabled, admission control for voice traffic is used."
			::= { vnsQoSEntry 10 }

		
		-- 1.3.6.1.4.1.4329.15.3.3.1.11.1.11
		vnsQoSWirelessUseAdmControlVideo OBJECT-TYPE
			SYNTAX INTEGER
				{
				enabled(1),
				disabled(2)
				}
			MAX-ACCESS read-write
			STATUS current
			DESCRIPTION
				"If enabled, admission control for vedio traffic is used.
				This field has a meaning if vnsQoSUseGlobalAdmVoice is enabled."
			::= { vnsQoSEntry 11 }

		
		-- 1.3.6.1.4.1.4329.15.3.3.1.11.1.12
		vnsQoSWirelessULPolicerAction OBJECT-TYPE
			SYNTAX INTEGER
				{
				doNothing(0),
				sendDELTStoClient(1)
				}
			MAX-ACCESS read-write
			STATUS current
			DESCRIPTION
				"If doNothing is selected, no action is taken. This is default value.
				If sendDELTStoClient is selected, AP will send DELTS if a client 
				is abusing in uplink. This field has a meaning only if admission
				control is enabled for VO or VI."
			DEFVAL { doNothing }
			::= { vnsQoSEntry 12 }

		
		-- 1.3.6.1.4.1.4329.15.3.3.1.11.1.13
		vnsQoSWirelessDLPolicerAction OBJECT-TYPE
			SYNTAX INTEGER
				{
				doNothing(0),
				downgrade(1),
				drop(2)
				}
			MAX-ACCESS read-write
			STATUS current
			DESCRIPTION
				"If doNothing is selected, no action is taken. This is default value.
				If downgrade is selected, AP will downgrade all traffic to the 
				   highest AC that does not require CAC in downlink.
				If drop is selected, AP will drop client if it observes a client 
				   that is illegally using an AC that has CAC mandatory in downlink.
				This field has a meaning only if admission control is enabled for 
				      VO or VI."
			DEFVAL { doNothing }
			::= { vnsQoSEntry 13 }

		
		-- 1.3.6.1.4.1.4329.15.3.3.1.12
		vnsWDSRFTable OBJECT-TYPE
			SYNTAX SEQUENCE OF VnsWDSRFEntry
			MAX-ACCESS not-accessible
			STATUS current
			DESCRIPTION
				"Contains definitions of the Wireless Distirbution System (WDS) VNS defined on this Controller."
			::= { vnsConfigObjects 12 }

		
		-- 1.3.6.1.4.1.4329.15.3.3.1.12.1
		vnsWDSRFEntry OBJECT-TYPE
			SYNTAX VnsWDSRFEntry
			MAX-ACCESS not-accessible
			STATUS current
			DESCRIPTION
				"Configuration elements for a specific WDS VNS."
			INDEX { vnsIfIndex, apIndex }
			::= { vnsWDSRFTable 1 }

		
		VnsWDSRFEntry ::=
			SEQUENCE { 
				vnsWDSRFAPName
					DisplayString,
				vnsWDSRFbgService
					INTEGER,
				vnsWDSRFaService
					INTEGER,
				vnsWDSRFPreferredParent
					DisplayString,
				vnsWDSRFBackupParent
					DisplayString,
				vnsWDSRFBridge
					INTEGER
			 }

		-- 1.3.6.1.4.1.4329.15.3.3.1.12.1.1
		vnsWDSRFAPName OBJECT-TYPE
			SYNTAX DisplayString
			MAX-ACCESS read-write
			STATUS current
			DESCRIPTION
				"AP name."
			::= { vnsWDSRFEntry 1 }

		
		-- 1.3.6.1.4.1.4329.15.3.3.1.12.1.2
		vnsWDSRFbgService OBJECT-TYPE
			SYNTAX INTEGER
				{
				notAvailable(0),
				none(1),
				child(2),
				parent(3),
				both(4)
				}
			MAX-ACCESS read-write
			STATUS current
			DESCRIPTION
				"Type of service offered by this radio."
			::= { vnsWDSRFEntry 2 }

		
		-- 1.3.6.1.4.1.4329.15.3.3.1.12.1.3
		vnsWDSRFaService OBJECT-TYPE
			SYNTAX INTEGER
				{
				notAvailable(0),
				none(1),
				child(2),
				parent(3),
				both(4)
				}
			MAX-ACCESS read-write
			STATUS current
			DESCRIPTION
				"Type of service offered by this radio."
			::= { vnsWDSRFEntry 3 }

		
		-- 1.3.6.1.4.1.4329.15.3.3.1.12.1.4
		vnsWDSRFPreferredParent OBJECT-TYPE
			SYNTAX DisplayString
			MAX-ACCESS read-write
			STATUS current
			DESCRIPTION
				"Desired preferred parent."
			::= { vnsWDSRFEntry 4 }

		
		-- 1.3.6.1.4.1.4329.15.3.3.1.12.1.5
		vnsWDSRFBackupParent OBJECT-TYPE
			SYNTAX DisplayString
			MAX-ACCESS read-write
			STATUS current
			DESCRIPTION
				"Desired backup parent."
			::= { vnsWDSRFEntry 5 }

		
		-- 1.3.6.1.4.1.4329.15.3.3.1.12.1.6
		vnsWDSRFBridge OBJECT-TYPE
			SYNTAX INTEGER
				{
				bridged(1),
				notBridged(2)
				}
			MAX-ACCESS read-write
			STATUS current
			DESCRIPTION
				"WDS bridge status."
			::= { vnsWDSRFEntry 6 }

		
		-- 1.3.6.1.4.1.4329.15.3.3.1.13
		vnsRateControlProfTable OBJECT-TYPE
			SYNTAX SEQUENCE OF VnsRateControlProfEntry
			MAX-ACCESS not-accessible
			STATUS current
			DESCRIPTION
				"Table of Rate Control Profiles."
			::= { vnsConfigObjects 13 }

		
		-- 1.3.6.1.4.1.4329.15.3.3.1.13.1
		vnsRateControlProfEntry OBJECT-TYPE
			SYNTAX VnsRateControlProfEntry
			MAX-ACCESS not-accessible
			STATUS current
			DESCRIPTION
				"Name of a specific Rate Control Profile."
			INDEX { vnsRateControlProfInd }
			::= { vnsRateControlProfTable 1 }

		
		VnsRateControlProfEntry ::=
			SEQUENCE { 
				vnsRateControlProfInd
					Unsigned32,
				vnsRateControlProfName
					DisplayString,
				vnsRateControlCIR
					Unsigned32,
				vnsRateControlCBS
					Unsigned32
			 }

		-- 1.3.6.1.4.1.4329.15.3.3.1.13.1.1
		vnsRateControlProfInd OBJECT-TYPE
			SYNTAX Unsigned32
			MAX-ACCESS read-write
			STATUS current
			DESCRIPTION
				"A monotonically increasing integer which acts as index of entries
				within the named Rate Control Profiles."
			::= { vnsRateControlProfEntry 1 }

		
		-- 1.3.6.1.4.1.4329.15.3.3.1.13.1.2
		vnsRateControlProfName OBJECT-TYPE
			SYNTAX DisplayString
			MAX-ACCESS read-write
			STATUS current
			DESCRIPTION
				"Rate Control Profile Name."
			::= { vnsRateControlProfEntry 2 }

		
		-- 1.3.6.1.4.1.4329.15.3.3.1.13.1.3
		vnsRateControlCIR OBJECT-TYPE
			SYNTAX Unsigned32
			MAX-ACCESS read-write
			STATUS current
			DESCRIPTION
				"Rate Control Average Rate (CIR) in kbps."
			::= { vnsRateControlProfEntry 3 }

		
		-- 1.3.6.1.4.1.4329.15.3.3.1.13.1.4
		vnsRateControlCBS OBJECT-TYPE
			SYNTAX Unsigned32
			MAX-ACCESS read-write
			STATUS current
			DESCRIPTION
				"Rate Control Burst Size (CBS) in bytes."
			::= { vnsRateControlProfEntry 4 }

		
		-- 1.3.6.1.4.1.4329.15.3.3.2
		vnsStatsObjects OBJECT IDENTIFIER ::= { virtualNetworks 2 }

		
		-- 1.3.6.1.4.1.4329.15.3.3.2.1
		activeVNSSessionCount OBJECT-TYPE
			SYNTAX Integer32
			MAX-ACCESS read-write
			STATUS current
			DESCRIPTION
				"Number of active VNSs."
			::= { vnsStatsObjects 1 }

		
		-- 1.3.6.1.4.1.4329.15.3.3.2.2
		vnsStatTable OBJECT-TYPE
			SYNTAX SEQUENCE OF VnsStatEntry
			MAX-ACCESS not-accessible
			STATUS current
			DESCRIPTION
				"The table contains per-VNS specific statistics."
			::= { vnsStatsObjects 2 }

		
		-- 1.3.6.1.4.1.4329.15.3.3.2.2.1
		vnsStatEntry OBJECT-TYPE
			SYNTAX VnsStatEntry
			MAX-ACCESS not-accessible
			STATUS current
			DESCRIPTION
				"An entry in vnsStatTable. Each entry is indexed by VNS ID"
			INDEX { vnsIfIndex }
			::= { vnsStatTable 1 }

		
		VnsStatEntry ::=
			SEQUENCE { 
				vnsStatName
					OCTET STRING,
				vnsStatTxPkts
					Counter64,
				vnsStatRxPkts
					Counter64,
				vnsStatTxOctects
					Counter64,
				vnsStatRxOctects
					Counter64,
				vnsStatMulticastTxPkts
					Counter64,
				vnsStatMulticastRxPkts
					Counter64,
				vnsStatBroadcastTxPkts
					Counter64,
				vnsStatBroadcastRxPkts
					Counter64,
				vnsStatRadiusTotRequests
					Counter64,
				vnsStatRadiusReqFailed
					Counter64,
				vnsStatRadiusReqRejected
					Counter64
			 }

		-- 1.3.6.1.4.1.4329.15.3.3.2.2.1.1
		vnsStatName OBJECT-TYPE
			SYNTAX OCTET STRING
			MAX-ACCESS read-write
			STATUS current
			DESCRIPTION
				"Name of the VNS."
			::= { vnsStatEntry 1 }

		
		-- 1.3.6.1.4.1.4329.15.3.3.2.2.1.2
		vnsStatTxPkts OBJECT-TYPE
			SYNTAX Counter64
			MAX-ACCESS read-only
			STATUS current
			DESCRIPTION
				"Trasmitted packets."
			::= { vnsStatEntry 2 }

		
		-- 1.3.6.1.4.1.4329.15.3.3.2.2.1.3
		vnsStatRxPkts OBJECT-TYPE
			SYNTAX Counter64
			MAX-ACCESS read-only
			STATUS current
			DESCRIPTION
				"Received packtes."
			::= { vnsStatEntry 3 }

		
		-- 1.3.6.1.4.1.4329.15.3.3.2.2.1.4
		vnsStatTxOctects OBJECT-TYPE
			SYNTAX Counter64
			MAX-ACCESS read-only
			STATUS current
			DESCRIPTION
				"Trasmitted octects."
			::= { vnsStatEntry 4 }

		
		-- 1.3.6.1.4.1.4329.15.3.3.2.2.1.5
		vnsStatRxOctects OBJECT-TYPE
			SYNTAX Counter64
			MAX-ACCESS read-only
			STATUS current
			DESCRIPTION
				"Received octets."
			::= { vnsStatEntry 5 }

		
		-- 1.3.6.1.4.1.4329.15.3.3.2.2.1.6
		vnsStatMulticastTxPkts OBJECT-TYPE
			SYNTAX Counter64
			MAX-ACCESS read-only
			STATUS current
			DESCRIPTION
				"Multicast trasmitted packets."
			::= { vnsStatEntry 6 }

		
		-- 1.3.6.1.4.1.4329.15.3.3.2.2.1.7
		vnsStatMulticastRxPkts OBJECT-TYPE
			SYNTAX Counter64
			MAX-ACCESS read-only
			STATUS current
			DESCRIPTION
				"Multicast received packets."
			::= { vnsStatEntry 7 }

		
		-- 1.3.6.1.4.1.4329.15.3.3.2.2.1.8
		vnsStatBroadcastTxPkts OBJECT-TYPE
			SYNTAX Counter64
			MAX-ACCESS read-only
			STATUS current
			DESCRIPTION
				"Broadcast trasmitted packets."
			::= { vnsStatEntry 8 }

		
		-- 1.3.6.1.4.1.4329.15.3.3.2.2.1.9
		vnsStatBroadcastRxPkts OBJECT-TYPE
			SYNTAX Counter64
			MAX-ACCESS read-only
			STATUS current
			DESCRIPTION
				"Broadcast received packets."
			::= { vnsStatEntry 9 }

		
		-- 1.3.6.1.4.1.4329.15.3.3.2.2.1.10
		vnsStatRadiusTotRequests OBJECT-TYPE
			SYNTAX Counter64
			MAX-ACCESS read-only
			STATUS current
			DESCRIPTION
				"Total requests sent to radius server."
			::= { vnsStatEntry 10 }

		
		-- 1.3.6.1.4.1.4329.15.3.3.2.2.1.11
		vnsStatRadiusReqFailed OBJECT-TYPE
			SYNTAX Counter64
			MAX-ACCESS read-only
			STATUS current
			DESCRIPTION
				"Requests that failed to be processed by radius server."
			::= { vnsStatEntry 11 }

		
		-- 1.3.6.1.4.1.4329.15.3.3.2.2.1.12
		vnsStatRadiusReqRejected OBJECT-TYPE
			SYNTAX Counter64
			MAX-ACCESS read-only
			STATUS current
			DESCRIPTION
				"Requests that have been rejected by radius server."
			::= { vnsStatEntry 12 }

		
		-- 1.3.6.1.4.1.4329.15.3.3.2.3
		vnsExceptionStatTable OBJECT-TYPE
			SYNTAX SEQUENCE OF VnsExceptionStatEntry
			MAX-ACCESS not-accessible
			STATUS current
			DESCRIPTION
				"The table contains list of per-VNS exception-filters specific statistics."
			::= { vnsStatsObjects 3 }

		
		-- 1.3.6.1.4.1.4329.15.3.3.2.3.1
		vnsExceptionStatEntry OBJECT-TYPE
			SYNTAX VnsExceptionStatEntry
			MAX-ACCESS not-accessible
			STATUS current
			DESCRIPTION
				"An entry in vnsExceptionStatTable."
			INDEX { vnsIfIndex, vnsExceptionFiterName }
			::= { vnsExceptionStatTable 1 }

		
		VnsExceptionStatEntry ::=
			SEQUENCE { 
				vnsExceptionFiterName
					OCTET STRING,
				vnsExceptionStatPktsDenied
					Counter64,
				vnsExceptionStatPktsAllowed
					Counter64
			 }

		-- 1.3.6.1.4.1.4329.15.3.3.2.3.1.1
		vnsExceptionFiterName OBJECT-TYPE
			SYNTAX OCTET STRING (SIZE (1..64))
			MAX-ACCESS read-write
			STATUS current
			DESCRIPTION
				"Filter name."
			::= { vnsExceptionStatEntry 1 }

		
		-- 1.3.6.1.4.1.4329.15.3.3.2.3.1.2
		vnsExceptionStatPktsDenied OBJECT-TYPE
			SYNTAX Counter64
			MAX-ACCESS read-only
			STATUS current
			DESCRIPTION
				"Total packets that are denied by defined filters."
			::= { vnsExceptionStatEntry 2 }

		
		-- 1.3.6.1.4.1.4329.15.3.3.2.3.1.3
		vnsExceptionStatPktsAllowed OBJECT-TYPE
			SYNTAX Counter64
			MAX-ACCESS read-only
			STATUS current
			DESCRIPTION
				"Total packets that are allowed by defined filters."
			::= { vnsExceptionStatEntry 3 }

		
		-- 1.3.6.1.4.1.4329.15.3.3.2.4
		vnsWDSStatTable OBJECT-TYPE
			SYNTAX SEQUENCE OF VnsWDSStatEntry
			MAX-ACCESS not-accessible
			STATUS current
			DESCRIPTION
				"Contains statistics of the Wireless Distirbution System (WDS) VNSes defined on this Controller."
			::= { vnsStatsObjects 4 }

		
		-- 1.3.6.1.4.1.4329.15.3.3.2.4.1
		vnsWDSStatEntry OBJECT-TYPE
			SYNTAX VnsWDSStatEntry
			MAX-ACCESS not-accessible
			STATUS current
			DESCRIPTION
				"Statistics elements for a specific WDS VNS."
			INDEX { vnsIfIndex, apIndex }
			::= { vnsWDSStatTable 1 }

		
		VnsWDSStatEntry ::=
			SEQUENCE { 
				vnsWDSStatAPName
					DisplayString,
				vnsWDSStatAPRole
					INTEGER,
				vnsWDSStatAPRadio
					DisplayString,
				vnsWDSStatAPParent
					DisplayString,
				vnsWDSStatSSID
					DisplayString,
				vnsWDSStatRxFrame
					Counter64,
				vnsWDSStatTxFrame
					Counter64,
				vnsWDSStatRxError
					Counter64,
				vnsWDSStatTxError
					Counter64,
				vnsWDSStatRxRSSI
					Integer32,
				vnsWDSStatRxRate
					Counter64,
				vnsWDSStatTxRate
					Counter64
			 }

		-- 1.3.6.1.4.1.4329.15.3.3.2.4.1.1
		vnsWDSStatAPName OBJECT-TYPE
			SYNTAX DisplayString
			MAX-ACCESS read-write
			STATUS current
			DESCRIPTION
				"AP name serving WDS VNS."
			::= { vnsWDSStatEntry 1 }

		
		-- 1.3.6.1.4.1.4329.15.3.3.2.4.1.2
		vnsWDSStatAPRole OBJECT-TYPE
			SYNTAX INTEGER
				{
				unknown(-1),
				none(0),
				satellite(1),
				root(2),
				repeater(3)
				}
			MAX-ACCESS read-write
			STATUS current
			DESCRIPTION
				"Role of the AP in WDS tree. All the statistics and configuration information 
				in this table has no meaning if the role is unknown(-1)."
			::= { vnsWDSStatEntry 2 }

		
		-- 1.3.6.1.4.1.4329.15.3.3.2.4.1.3
		vnsWDSStatAPRadio OBJECT-TYPE
			SYNTAX DisplayString (SIZE (0..15))
			MAX-ACCESS read-write
			STATUS current
			DESCRIPTION
				"Radio and freq on which uplink WDS is established, N/A if connected
				over etherent (value are 'a:<freq>', 'b/g:<freq>', or 'N/A') "
			::= { vnsWDSStatEntry 3 }

		
		-- 1.3.6.1.4.1.4329.15.3.3.2.4.1.4
		vnsWDSStatAPParent OBJECT-TYPE
			SYNTAX DisplayString
			MAX-ACCESS read-write
			STATUS current
			DESCRIPTION
				"AP Name of the parent AP."
			::= { vnsWDSStatEntry 4 }

		
		-- 1.3.6.1.4.1.4329.15.3.3.2.4.1.5
		vnsWDSStatSSID OBJECT-TYPE
			SYNTAX DisplayString (SIZE (0..32))
			MAX-ACCESS read-write
			STATUS current
			DESCRIPTION
				"SSID of the WDS VNS where parent WDS link is established."
			::= { vnsWDSStatEntry 5 }

		
		-- 1.3.6.1.4.1.4329.15.3.3.2.4.1.6
		vnsWDSStatRxFrame OBJECT-TYPE
			SYNTAX Counter64
			MAX-ACCESS read-write
			STATUS current
			DESCRIPTION
				"Received frames from the parent AP."
			::= { vnsWDSStatEntry 6 }

		
		-- 1.3.6.1.4.1.4329.15.3.3.2.4.1.7
		vnsWDSStatTxFrame OBJECT-TYPE
			SYNTAX Counter64
			MAX-ACCESS read-write
			STATUS current
			DESCRIPTION
				"Transmitted frames to the parent AP."
			::= { vnsWDSStatEntry 7 }

		
		-- 1.3.6.1.4.1.4329.15.3.3.2.4.1.8
		vnsWDSStatRxError OBJECT-TYPE
			SYNTAX Counter64
			MAX-ACCESS read-write
			STATUS current
			DESCRIPTION
				"Received frames in error from the parent AP."
			::= { vnsWDSStatEntry 8 }

		
		-- 1.3.6.1.4.1.4329.15.3.3.2.4.1.9
		vnsWDSStatTxError OBJECT-TYPE
			SYNTAX Counter64
			MAX-ACCESS read-write
			STATUS current
			DESCRIPTION
				"Transmitted frames in error to the parent AP."
			::= { vnsWDSStatEntry 9 }

		
		-- 1.3.6.1.4.1.4329.15.3.3.2.4.1.10
		vnsWDSStatRxRSSI OBJECT-TYPE
			SYNTAX Integer32 (0..64)
			MAX-ACCESS read-write
			STATUS current
			DESCRIPTION
				"Average Received Signal Strength Indicator (RSSI)."
			::= { vnsWDSStatEntry 10 }

		
		-- 1.3.6.1.4.1.4329.15.3.3.2.4.1.11
		vnsWDSStatRxRate OBJECT-TYPE
			SYNTAX Counter64
			MAX-ACCESS read-write
			STATUS current
			DESCRIPTION
				"Average receive rate."
			::= { vnsWDSStatEntry 11 }

		
		-- 1.3.6.1.4.1.4329.15.3.3.2.4.1.12
		vnsWDSStatTxRate OBJECT-TYPE
			SYNTAX Counter64
			MAX-ACCESS read-write
			STATUS current
			DESCRIPTION
				"Average transmission rate."
			::= { vnsWDSStatEntry 12 }

		
		-- 1.3.6.1.4.1.4329.15.3.3.3
		vnsGlobalSetting OBJECT IDENTIFIER ::= { virtualNetworks 3 }

		
		-- 1.3.6.1.4.1.4329.15.3.3.3.1
		wirelessQoS OBJECT IDENTIFIER ::= { vnsGlobalSetting 1 }

		
		-- 1.3.6.1.4.1.4329.15.3.3.3.1.1
		maxVoiceBWforReassociation OBJECT-TYPE
			SYNTAX Integer32 (0..100)
			MAX-ACCESS read-write
			STATUS current
			DESCRIPTION
				"Maximum voice bandwidth to be used for re-association."
			DEFVAL { 80 }
			::= { wirelessQoS 1 }

		
		-- 1.3.6.1.4.1.4329.15.3.3.3.1.2
		maxVoiceBWforAssociation OBJECT-TYPE
			SYNTAX Integer32 (0..100)
			MAX-ACCESS read-write
			STATUS current
			DESCRIPTION
				"Maximum voice bandwidth to be used for association."
			DEFVAL { 60 }
			::= { wirelessQoS 2 }

		
		-- 1.3.6.1.4.1.4329.15.3.3.3.1.3
		maxVideoBWforReassociation OBJECT-TYPE
			SYNTAX Integer32 (0..100)
			MAX-ACCESS read-write
			STATUS current
			DESCRIPTION
				"Maximum video bandwidth to be used for re-association."
			DEFVAL { 60 }
			::= { wirelessQoS 3 }

		
		-- 1.3.6.1.4.1.4329.15.3.3.3.1.4
		maxVideoBWforAssociation OBJECT-TYPE
			SYNTAX Integer32 (0..100)
			MAX-ACCESS read-write
			STATUS current
			DESCRIPTION
				"Maximum video bandwidth to be used for association."
			DEFVAL { 40 }
			::= { wirelessQoS 4 }

		
		-- 1.3.6.1.4.1.4329.15.3.3.3.2
		radiusInfo OBJECT IDENTIFIER ::= { vnsGlobalSetting 2 }

		
		-- 1.3.6.1.4.1.4329.15.3.3.3.2.2
		externalRadiusServerTable OBJECT-TYPE
			SYNTAX SEQUENCE OF ExternalRadiusServerEntry
			MAX-ACCESS not-accessible
			STATUS current
			DESCRIPTION
				"Table of external RADIUS servers available for authentication services."
			::= { radiusInfo 2 }

		
		-- 1.3.6.1.4.1.4329.15.3.3.3.2.2.1
		externalRadiusServerEntry OBJECT-TYPE
			SYNTAX ExternalRadiusServerEntry
			MAX-ACCESS not-accessible
			STATUS current
			DESCRIPTION
				"Configuration information about the RADIUS server entry."
			INDEX { externalRadiusServerName }
			::= { externalRadiusServerTable 1 }

		
		ExternalRadiusServerEntry ::=
			SEQUENCE { 
				externalRadiusServerName
					DisplayString,
				externalRadiusServerAddress
					DisplayString,
				externalRadiusServerSharedSecret
					OCTET STRING,
				externalRadiusServerRowStatus
					RowStatus
			 }

		-- 1.3.6.1.4.1.4329.15.3.3.3.2.2.1.1
		externalRadiusServerName OBJECT-TYPE
			SYNTAX DisplayString
			MAX-ACCESS read-write
			STATUS current
			DESCRIPTION
				"RADIUS server name."
			::= { externalRadiusServerEntry 1 }

		
		-- 1.3.6.1.4.1.4329.15.3.3.3.2.2.1.2
		externalRadiusServerAddress OBJECT-TYPE
			SYNTAX DisplayString
			MAX-ACCESS read-write
			STATUS current
			DESCRIPTION
				"RADIUS server address, it can be either string or IP address."
			::= { externalRadiusServerEntry 2 }

		
		-- 1.3.6.1.4.1.4329.15.3.3.3.2.2.1.3
		externalRadiusServerSharedSecret OBJECT-TYPE
			SYNTAX OCTET STRING (SIZE (0..64))
			MAX-ACCESS read-write
			STATUS current
			DESCRIPTION
				"Shared secret between Radius and the client."
			::= { externalRadiusServerEntry 3 }

		
		-- 1.3.6.1.4.1.4329.15.3.3.3.2.2.1.4
		externalRadiusServerRowStatus OBJECT-TYPE
			SYNTAX RowStatus
			MAX-ACCESS read-write
			STATUS current
			DESCRIPTION
				"Row Status for the entry."
			::= { externalRadiusServerEntry 4 }

		
		-- 1.3.6.1.4.1.4329.15.3.3.3.3
		dasInfo OBJECT IDENTIFIER ::= { vnsGlobalSetting 3 }

		
		-- 1.3.6.1.4.1.4329.15.3.3.3.3.1
		dasPort OBJECT-TYPE
			SYNTAX Integer32 (1024..65535)
			MAX-ACCESS read-write
			STATUS current
			DESCRIPTION
				"Dynamic Authorization Server (DAS) port. "
			DEFVAL { 3799 }
			::= { dasInfo 1 }

		
		-- 1.3.6.1.4.1.4329.15.3.3.3.3.2
		dasReplayInterval OBJECT-TYPE
			SYNTAX Integer32 (0..1000)
			UNITS "seconds"
			MAX-ACCESS read-write
			STATUS current
			DESCRIPTION
				"The time window for message timeliness and replay protection
				for DAS packets. Packets should be dropped that their time
				generation is outside of this specified interval.
				Value zero indicates that the timeliness checking will be performed."
			DEFVAL { 300 }
			::= { dasInfo 2 }

		
		-- 1.3.6.1.4.1.4329.15.3.5
		accessPoints OBJECT IDENTIFIER ::= { hiPathWirelessMgmt 5 }

		
		-- 1.3.6.1.4.1.4329.15.3.5.1
		apConfigObjects OBJECT IDENTIFIER ::= { accessPoints 1 }

		
		-- 1.3.6.1.4.1.4329.15.3.5.1.1
		apCount OBJECT-TYPE
			SYNTAX Integer32
			MAX-ACCESS read-only
			STATUS current
			DESCRIPTION
				"The count of currently configured AccessPoints associated with this WirelessController."
			::= { apConfigObjects 1 }

		
		-- 1.3.6.1.4.1.4329.15.3.5.1.2
		apTable OBJECT-TYPE
			SYNTAX SEQUENCE OF ApEntry
			MAX-ACCESS not-accessible
			STATUS current
			DESCRIPTION
				"Contains a list of all configured APs associated with the WirelessController."
			::= { apConfigObjects 2 }

		
		-- 1.3.6.1.4.1.4329.15.3.5.1.2.1
		apEntry OBJECT-TYPE
			SYNTAX ApEntry
			MAX-ACCESS not-accessible
			STATUS current
			DESCRIPTION
				"Configuration information for an access point."
			INDEX { apIndex }
			::= { apTable 1 }

		
		ApEntry ::=
			SEQUENCE { 
				apIndex
					Integer32,
				apName
					DisplayString,
				apDesc
					DisplayString,
				apSerialNumber
					OCTET STRING,
				apPortifIndex
					InterfaceIndex,
				apWiredIfIndex
					InterfaceIndex,
				apSoftwareVersion
					OCTET STRING,
				apSpecific
					OBJECT IDENTIFIER,
				apBroadcastDisassociate
					TruthValue,
				apRowStatus
					RowStatus,
				apVlanID
					Integer32,
				apIpAssignmentType
					INTEGER,
				apIfMAC
					MacAddress,
				apIPAddress
					IpAddress,
				apCredentialType
					INTEGER,
				apCertificateExpiry
					TimeTicks,
				apHwVersion
					DisplayString,
				apSwVersion
					DisplayString,
				apEnvironment
					INTEGER,
				apHome
					INTEGER,
				apRole
					INTEGER,
				apState
					INTEGER,
				apStatus
					INTEGER,
				apPollTimeout
					Gauge32,
				apPollInterval
					Gauge32,
				apTelnetAccess
					INTEGER,
				apMaintainClientSession
					TruthValue,
				apRestartServiceContAbsent
					TruthValue,
				apHostname
					DisplayString
			 }

		-- 1.3.6.1.4.1.4329.15.3.5.1.2.1.1
		apIndex OBJECT-TYPE
			SYNTAX Integer32 (1..2147483647)
			MAX-ACCESS read-write
			STATUS current
			DESCRIPTION
				"Table index for the access point."
			::= { apEntry 1 }

		
		-- 1.3.6.1.4.1.4329.15.3.5.1.2.1.2
		apName OBJECT-TYPE
			SYNTAX DisplayString
			MAX-ACCESS read-write
			STATUS current
			DESCRIPTION
				"Access Point's name."
			::= { apEntry 2 }

		
		-- 1.3.6.1.4.1.4329.15.3.5.1.2.1.3
		apDesc OBJECT-TYPE
			SYNTAX DisplayString
			MAX-ACCESS read-write
			STATUS current
			DESCRIPTION
				"Text description of the AP."
			::= { apEntry 3 }

		
		-- 1.3.6.1.4.1.4329.15.3.5.1.2.1.4
		apSerialNumber OBJECT-TYPE
			SYNTAX OCTET STRING (SIZE (16))
			MAX-ACCESS read-only
			STATUS current
			DESCRIPTION
				"16-character serial number of the AccessPoint."
			::= { apEntry 4 }

		
		-- 1.3.6.1.4.1.4329.15.3.5.1.2.1.5
		apPortifIndex OBJECT-TYPE
			SYNTAX InterfaceIndex
			MAX-ACCESS read-write
			STATUS current
			DESCRIPTION
				"ifIndex of the physical port to which this AP is assigned."
			::= { apEntry 5 }

		
		-- 1.3.6.1.4.1.4329.15.3.5.1.2.1.6
		apWiredIfIndex OBJECT-TYPE
			SYNTAX InterfaceIndex
			MAX-ACCESS read-write
			STATUS current
			DESCRIPTION
				"ifIndex of the wired interface on the AP."
			::= { apEntry 6 }

		
		-- 1.3.6.1.4.1.4329.15.3.5.1.2.1.7
		apSoftwareVersion OBJECT-TYPE
			SYNTAX OCTET STRING
			MAX-ACCESS read-only
			STATUS current
			DESCRIPTION
				"Software version currently installed on the AP."
			::= { apEntry 7 }

		
		-- 1.3.6.1.4.1.4329.15.3.5.1.2.1.8
		apSpecific OBJECT-TYPE
			SYNTAX OBJECT IDENTIFIER
			MAX-ACCESS read-only
			STATUS current
			DESCRIPTION
				"A link back to the OID under the hiPathWirelessProducts
				branch that identifies the specific version of this AP."
			::= { apEntry 8 }

		
		-- 1.3.6.1.4.1.4329.15.3.5.1.2.1.9
		apBroadcastDisassociate OBJECT-TYPE
			SYNTAX TruthValue
			MAX-ACCESS read-write
			STATUS current
			DESCRIPTION
				"True indicates that the AP should broadcast
				disassociation requests, False indicates unicast."
			::= { apEntry 9 }

		
		-- 1.3.6.1.4.1.4329.15.3.5.1.2.1.10
		apRowStatus OBJECT-TYPE
			SYNTAX RowStatus
			MAX-ACCESS read-write
			STATUS current
			DESCRIPTION
				"RowStatus for the apTable."
			::= { apEntry 10 }

		
		-- 1.3.6.1.4.1.4329.15.3.5.1.2.1.11
		apVlanID OBJECT-TYPE
			SYNTAX Integer32
			MAX-ACCESS read-write
			STATUS current
			DESCRIPTION
				"VLAN tag for the packets trasmitted to/from Access Point.
				Value ranges: (-1) it is not tagged, zero(0) means reserved, 1-4094 tag value."
			DEFVAL { -1 }
			::= { apEntry 11 }

		
		-- 1.3.6.1.4.1.4329.15.3.5.1.2.1.12
		apIpAssignmentType OBJECT-TYPE
			SYNTAX INTEGER
				{
				dhcp(1),
				static(2)
				}
			MAX-ACCESS read-write
			STATUS current
			DESCRIPTION
				"IP address assignment type, dhcp(1) = uses DHCP to obtain IP address, 
				static(2) = static IP address is assigned to the access point."
			::= { apEntry 12 }

		
		-- 1.3.6.1.4.1.4329.15.3.5.1.2.1.13
		apIfMAC OBJECT-TYPE
			SYNTAX MacAddress
			MAX-ACCESS read-only
			STATUS current
			DESCRIPTION
				"Acess Point's wired interface MAC address."
			::= { apEntry 13 }

		
		-- 1.3.6.1.4.1.4329.15.3.5.1.2.1.14
		apIPAddress OBJECT-TYPE
			SYNTAX IpAddress
			MAX-ACCESS read-write
			STATUS current
			DESCRIPTION
				"Access Point's wired interface IP address."
			::= { apEntry 14 }

		
		-- 1.3.6.1.4.1.4329.15.3.5.1.2.1.15
		apCredentialType OBJECT-TYPE
			SYNTAX INTEGER
				{
				none(0),
				tls(1),
				peap(2),
				all(3)
				}
			MAX-ACCESS read-write
			STATUS current
			DESCRIPTION
				"Supported certificate type used by AP for commnuication.
				none(0) = not supported,
				TLS(1) = Trasport Layer Security (TLS),
				PEAP(2) = Protected Extensible Authentication Protocol,
				all(2) = supports all supported EAP."
			::= { apEntry 15 }

		
		-- 1.3.6.1.4.1.4329.15.3.5.1.2.1.16
		apCertificateExpiry OBJECT-TYPE
			SYNTAX TimeTicks
			MAX-ACCESS read-write
			STATUS current
			DESCRIPTION
				"The number of timeticks from January, 1st, 1970 to the date when 
				the certificate expires (issued certificate no longer is valid)."
			::= { apEntry 16 }

		
		-- 1.3.6.1.4.1.4329.15.3.5.1.2.1.17
		apHwVersion OBJECT-TYPE
			SYNTAX DisplayString
			MAX-ACCESS read-write
			STATUS current
			DESCRIPTION
				"Text description of Access Point's hardware version."
			::= { apEntry 17 }

		
		-- 1.3.6.1.4.1.4329.15.3.5.1.2.1.18
		apSwVersion OBJECT-TYPE
			SYNTAX DisplayString
			MAX-ACCESS read-write
			STATUS current
			DESCRIPTION
				"Text description of Access Point's software version."
			::= { apEntry 18 }

		
		-- 1.3.6.1.4.1.4329.15.3.5.1.2.1.19
		apEnvironment OBJECT-TYPE
			SYNTAX INTEGER
				{
				indoor(1),
				outdoor(2)
				}
			MAX-ACCESS read-write
			STATUS current
			DESCRIPTION
				"Access Point's environment."
			::= { apEntry 19 }

		
		-- 1.3.6.1.4.1.4329.15.3.5.1.2.1.20
		apHome OBJECT-TYPE
			SYNTAX INTEGER
				{
				local(1),
				foreign(2)
				}
			MAX-ACCESS read-write
			STATUS current
			DESCRIPTION
				"Indicates whether Access Point is local or foreign."
			::= { apEntry 20 }

		
		-- 1.3.6.1.4.1.4329.15.3.5.1.2.1.21
		apRole OBJECT-TYPE
			SYNTAX INTEGER
				{
				accessPoint(1),
				sensor(2)
				}
			MAX-ACCESS read-write
			STATUS current
			DESCRIPTION
				"Indicates whether Access Point is a sensor or not. Some of the fields of this table
				may not have meaning if the role is sensor(2)."
			::= { apEntry 21 }

		
		-- 1.3.6.1.4.1.4329.15.3.5.1.2.1.22
		apState OBJECT-TYPE
			SYNTAX INTEGER
				{
				active(1),
				inactive(2)
				}
			MAX-ACCESS read-write
			STATUS current
			DESCRIPTION
				"State of Access Point."
			::= { apEntry 22 }

		
		-- 1.3.6.1.4.1.4329.15.3.5.1.2.1.23
		apStatus OBJECT-TYPE
			SYNTAX INTEGER
				{
				approved(1),
				pending(2)
				}
			MAX-ACCESS read-write
			STATUS current
			DESCRIPTION
				"Status of Access Point."
			::= { apEntry 23 }

		
		-- 1.3.6.1.4.1.4329.15.3.5.1.2.1.24
		apPollTimeout OBJECT-TYPE
			SYNTAX Gauge32
			MAX-ACCESS read-write
			STATUS current
			DESCRIPTION
				"The amount of time for poll timeout."
			::= { apEntry 24 }

		
		-- 1.3.6.1.4.1.4329.15.3.5.1.2.1.25
		apPollInterval OBJECT-TYPE
			SYNTAX Gauge32
			MAX-ACCESS read-write
			STATUS current
			DESCRIPTION
				"Interval between each poll sent to the controller."
			::= { apEntry 25 }

		
		-- 1.3.6.1.4.1.4329.15.3.5.1.2.1.26
		apTelnetAccess OBJECT-TYPE
			SYNTAX INTEGER
				{
				enabled(1),
				disabled(2)
				}
			MAX-ACCESS read-write
			STATUS current
			DESCRIPTION
				"Indicates whether telnet access is enabled/disabled."
			::= { apEntry 26 }

		
		-- 1.3.6.1.4.1.4329.15.3.5.1.2.1.27
		apMaintainClientSession OBJECT-TYPE
			SYNTAX TruthValue
			MAX-ACCESS read-write
			STATUS current
			DESCRIPTION
				"If true, Access Point maintains client's session in the event of poll failure."
			::= { apEntry 27 }

		
		-- 1.3.6.1.4.1.4329.15.3.5.1.2.1.28
		apRestartServiceContAbsent OBJECT-TYPE
			SYNTAX TruthValue
			MAX-ACCESS read-write
			STATUS current
			DESCRIPTION
				"If true, Access Point restarts the service in the absence of controller."
			::= { apEntry 28 }

		
		-- 1.3.6.1.4.1.4329.15.3.5.1.2.1.29
		apHostname OBJECT-TYPE
			SYNTAX DisplayString
			MAX-ACCESS read-only
			STATUS current
			DESCRIPTION
				"Hostname assigned to Access Point."
			::= { apEntry 29 }

		
		-- 1.3.6.1.4.1.4329.15.3.5.1.3
		apRadioTable OBJECT-TYPE
			SYNTAX SEQUENCE OF ApRadioEntry
			MAX-ACCESS not-accessible
			STATUS current
			DESCRIPTION
				"Table access point radio configuration information."
			::= { apConfigObjects 3 }

		
		-- 1.3.6.1.4.1.4329.15.3.5.1.3.1
		apRadioEntry OBJECT-TYPE
			SYNTAX ApRadioEntry
			MAX-ACCESS not-accessible
			STATUS current
			DESCRIPTION
				"Configuration information for a radio on the access point."
			INDEX { apIndex, ifIndex }
			::= { apRadioTable 1 }

		
		ApRadioEntry ::=
			SEQUENCE { 
				apRadioFrequency
					INTEGER
			 }

		-- 1.3.6.1.4.1.4329.15.3.5.1.3.1.1
		apRadioFrequency OBJECT-TYPE
			SYNTAX INTEGER
				{
				freq50GHz(1),
				freq24GHz(2)
				}
			MAX-ACCESS read-only
			STATUS current
			DESCRIPTION
				"Indicates the frequency of each radio."
			::= { apRadioEntry 1 }

		
		-- 1.3.6.1.4.1.4329.15.3.5.1.4
		radioVNSTable OBJECT-TYPE
			SYNTAX SEQUENCE OF RadioVNSEntry
			MAX-ACCESS not-accessible
			STATUS current
			DESCRIPTION
				"Table of VNSs the radio is participating in."
			::= { apConfigObjects 4 }

		
		-- 1.3.6.1.4.1.4329.15.3.5.1.4.1
		radioVNSEntry OBJECT-TYPE
			SYNTAX RadioVNSEntry
			MAX-ACCESS not-accessible
			STATUS current
			DESCRIPTION
				"Information for a single VNS entry."
			INDEX { radioIfIndex, vnsIfIndex }
			::= { radioVNSTable 1 }

		
		RadioVNSEntry ::=
			SEQUENCE { 
				radioIfIndex
					InterfaceIndex,
				vnsIfIndex
					InterfaceIndex,
				radioVNSRowStatus
					RowStatus
			 }

		-- 1.3.6.1.4.1.4329.15.3.5.1.4.1.1
		radioIfIndex OBJECT-TYPE
			SYNTAX InterfaceIndex
			MAX-ACCESS read-write
			STATUS current
			DESCRIPTION
				"Radio participating in the VNS."
			::= { radioVNSEntry 1 }

		
		-- 1.3.6.1.4.1.4329.15.3.5.1.4.1.2
		vnsIfIndex OBJECT-TYPE
			SYNTAX InterfaceIndex
			MAX-ACCESS read-write
			STATUS current
			DESCRIPTION
				"ifIndex for the VNS the radio is participating."
			::= { radioVNSEntry 2 }

		
		-- 1.3.6.1.4.1.4329.15.3.5.1.4.1.3
		radioVNSRowStatus OBJECT-TYPE
			SYNTAX RowStatus
			MAX-ACCESS read-write
			STATUS current
			DESCRIPTION
				"RowStatus for the radioVNSTable."
			::= { radioVNSEntry 3 }

		
		-- 1.3.6.1.4.1.4329.15.3.5.1.5
		apFastFailoverEnable OBJECT-TYPE
			SYNTAX TruthValue
			MAX-ACCESS read-write
			STATUS current
			DESCRIPTION
				"True indicates that Fast Failover feature is enabled at AP"
			::= { apConfigObjects 5 }

		
		-- 1.3.6.1.4.1.4329.15.3.5.1.6
		apLinkTimeout OBJECT-TYPE
			SYNTAX Integer32
			MAX-ACCESS read-write
			STATUS current
			DESCRIPTION
				"Time to deteck link failure. The value is in 1-30 seconds"
			::= { apConfigObjects 6 }

		
		-- 1.3.6.1.4.1.4329.15.3.5.2
		apStatsObjects OBJECT IDENTIFIER ::= { accessPoints 2 }

		
		-- 1.3.6.1.4.1.4329.15.3.5.2.1
		apActiveCount OBJECT-TYPE
			SYNTAX Integer32
			MAX-ACCESS read-only
			STATUS current
			DESCRIPTION
				"The count of active AccessPoints associated with this WirelessController."
			::= { apStatsObjects 1 }

		
		-- 1.3.6.1.4.1.4329.15.3.5.2.2
		apStatsTable OBJECT-TYPE
			SYNTAX SEQUENCE OF ApStatsEntry
			MAX-ACCESS not-accessible
			STATUS current
			DESCRIPTION
				"Table of statistics for the access points."
			::= { apStatsObjects 2 }

		
		-- 1.3.6.1.4.1.4329.15.3.5.2.2.1
		apStatsEntry OBJECT-TYPE
			SYNTAX ApStatsEntry
			MAX-ACCESS not-accessible
			STATUS current
			DESCRIPTION
				"Statistics for an access point."
			INDEX { apIndex }
			::= { apStatsTable 1 }

		
		ApStatsEntry ::=
			SEQUENCE { 
				apInUcastPkts
					Counter64,
				apInNUcastPkts
					Counter64,
				apInOctets
					Counter64,
				apInErrors
					Counter64,
				apInDiscards
					Counter64,
				apOutUcastPkts
					Counter64,
				apOutNUcastPkts
					Counter64,
				apOutOctets
					Counter64,
				apOutErrors
					Counter64,
				apOutDiscards
					Counter64,
				apUpTime
					TimeTicks
			 }

		-- 1.3.6.1.4.1.4329.15.3.5.2.2.1.1
		apInUcastPkts OBJECT-TYPE
			SYNTAX Counter64
			MAX-ACCESS read-only
			STATUS current
			DESCRIPTION
				"Number of unicast packets from wireless-to-wired network."
			::= { apStatsEntry 1 }

		
		-- 1.3.6.1.4.1.4329.15.3.5.2.2.1.2
		apInNUcastPkts OBJECT-TYPE
			SYNTAX Counter64
			MAX-ACCESS read-only
			STATUS current
			DESCRIPTION
				"Number of non-unicast packets from wireless-to-wired network."
			::= { apStatsEntry 2 }

		
		-- 1.3.6.1.4.1.4329.15.3.5.2.2.1.3
		apInOctets OBJECT-TYPE
			SYNTAX Counter64
			MAX-ACCESS read-only
			STATUS current
			DESCRIPTION
				"Number of octets from wireless-to-wired network."
			::= { apStatsEntry 3 }

		
		-- 1.3.6.1.4.1.4329.15.3.5.2.2.1.4
		apInErrors OBJECT-TYPE
			SYNTAX Counter64
			MAX-ACCESS read-only
			STATUS current
			DESCRIPTION
				"Number of error packets from wireless-to-wired network."
			::= { apStatsEntry 4 }

		
		-- 1.3.6.1.4.1.4329.15.3.5.2.2.1.5
		apInDiscards OBJECT-TYPE
			SYNTAX Counter64
			MAX-ACCESS read-only
			STATUS current
			DESCRIPTION
				"Number of discarded packets from wireless-to-wired network."
			::= { apStatsEntry 5 }

		
		-- 1.3.6.1.4.1.4329.15.3.5.2.2.1.6
		apOutUcastPkts OBJECT-TYPE
			SYNTAX Counter64
			MAX-ACCESS read-only
			STATUS current
			DESCRIPTION
				"Number of unicast packets from wired-to-wireless network."
			::= { apStatsEntry 6 }

		
		-- 1.3.6.1.4.1.4329.15.3.5.2.2.1.7
		apOutNUcastPkts OBJECT-TYPE
			SYNTAX Counter64
			MAX-ACCESS read-only
			STATUS current
			DESCRIPTION
				"Number of non-unicast packets from wired-to-wireless network."
			::= { apStatsEntry 7 }

		
		-- 1.3.6.1.4.1.4329.15.3.5.2.2.1.8
		apOutOctets OBJECT-TYPE
			SYNTAX Counter64
			MAX-ACCESS read-only
			STATUS current
			DESCRIPTION
				"Number of octets from wired-to-wireless network."
			::= { apStatsEntry 8 }

		
		-- 1.3.6.1.4.1.4329.15.3.5.2.2.1.9
		apOutErrors OBJECT-TYPE
			SYNTAX Counter64
			MAX-ACCESS read-only
			STATUS current
			DESCRIPTION
				"Number of error packets from wired-to-wireless network."
			::= { apStatsEntry 9 }

		
		-- 1.3.6.1.4.1.4329.15.3.5.2.2.1.10
		apOutDiscards OBJECT-TYPE
			SYNTAX Counter64
			MAX-ACCESS read-only
			STATUS current
			DESCRIPTION
				"Number of discarded packets from wired-to-wireless network."
			::= { apStatsEntry 10 }

		
		-- 1.3.6.1.4.1.4329.15.3.5.2.2.1.11
		apUpTime OBJECT-TYPE
			SYNTAX TimeTicks
			MAX-ACCESS read-only
			STATUS current
			DESCRIPTION
				"The time (in hundredths of a second) since the
				management portion of the access point was last
				re-initialized."
			::= { apStatsEntry 11 }

		
		-- 1.3.6.1.4.1.4329.15.3.6
		mobileUnits OBJECT IDENTIFIER ::= { hiPathWirelessMgmt 6 }

		
		-- 1.3.6.1.4.1.4329.15.3.6.1
		mobileUnitCount OBJECT-TYPE
			SYNTAX Integer32
			MAX-ACCESS read-write
			STATUS current
			DESCRIPTION
				"Number of clients associated with the access point."
			::= { mobileUnits 1 }

		
		-- 1.3.6.1.4.1.4329.15.3.6.2
		muTable OBJECT-TYPE
			SYNTAX SEQUENCE OF MuEntry
			MAX-ACCESS not-accessible
			STATUS current
			DESCRIPTION
				"Table of information for clients associated with the HWC."
			::= { mobileUnits 2 }

		
		-- 1.3.6.1.4.1.4329.15.3.6.2.1
		muEntry OBJECT-TYPE
			SYNTAX MuEntry
			MAX-ACCESS not-accessible
			STATUS current
			DESCRIPTION
				"Information for a client associated with the HWC."
			INDEX { muMACAddress }
			::= { muTable 1 }

		
		MuEntry ::=
			SEQUENCE { 
				muMACAddress
					MacAddress,
				muIPAddress
					IpAddress,
				muUser
					OCTET STRING,
				muState
					TruthValue,
				muAPSerialNo
					OCTET STRING,
				muVnsSSID
					OCTET STRING,
				muTxPackets
					Counter64,
				muRxPackets
					Counter64,
				muTxOctets
					Counter64,
				muRxOctets
					Counter64,
				muDuration
					Counter64,
				muAPName
					DisplayString
			 }

		-- 1.3.6.1.4.1.4329.15.3.6.2.1.1
		muMACAddress OBJECT-TYPE
			SYNTAX MacAddress
			MAX-ACCESS read-only
			STATUS current
			DESCRIPTION
				"Client MAC address."
			::= { muEntry 1 }

		
		-- 1.3.6.1.4.1.4329.15.3.6.2.1.2
		muIPAddress OBJECT-TYPE
			SYNTAX IpAddress
			MAX-ACCESS read-only
			STATUS current
			DESCRIPTION
				"Client IP Address."
			::= { muEntry 2 }

		
		-- 1.3.6.1.4.1.4329.15.3.6.2.1.3
		muUser OBJECT-TYPE
			SYNTAX OCTET STRING
			MAX-ACCESS read-only
			STATUS current
			DESCRIPTION
				"Client login name."
			::= { muEntry 3 }

		
		-- 1.3.6.1.4.1.4329.15.3.6.2.1.4
		muState OBJECT-TYPE
			SYNTAX TruthValue
			MAX-ACCESS read-only
			STATUS current
			DESCRIPTION
				"True if the client is authenticated."
			::= { muEntry 4 }

		
		-- 1.3.6.1.4.1.4329.15.3.6.2.1.5
		muAPSerialNo OBJECT-TYPE
			SYNTAX OCTET STRING
			MAX-ACCESS read-only
			STATUS current
			DESCRIPTION
				"Serial Number of the Access Point the client is associated with."
			::= { muEntry 5 }

		
		-- 1.3.6.1.4.1.4329.15.3.6.2.1.6
		muVnsSSID OBJECT-TYPE
			SYNTAX OCTET STRING
			MAX-ACCESS read-only
			STATUS current
			DESCRIPTION
				"SSID of the VNS the client is associated with."
			::= { muEntry 6 }

		
		-- 1.3.6.1.4.1.4329.15.3.6.2.1.7
		muTxPackets OBJECT-TYPE
			SYNTAX Counter64
			MAX-ACCESS read-only
			STATUS current
			DESCRIPTION
				"Number of packets trasmitted to the client."
			::= { muEntry 7 }

		
		-- 1.3.6.1.4.1.4329.15.3.6.2.1.8
		muRxPackets OBJECT-TYPE
			SYNTAX Counter64
			MAX-ACCESS read-only
			STATUS current
			DESCRIPTION
				"Number of packets received from the client."
			::= { muEntry 8 }

		
		-- 1.3.6.1.4.1.4329.15.3.6.2.1.9
		muTxOctets OBJECT-TYPE
			SYNTAX Counter64
			MAX-ACCESS read-only
			STATUS current
			DESCRIPTION
				"Number of octets transmitted to the client."
			::= { muEntry 9 }

		
		-- 1.3.6.1.4.1.4329.15.3.6.2.1.10
		muRxOctets OBJECT-TYPE
			SYNTAX Counter64
			MAX-ACCESS read-only
			STATUS current
			DESCRIPTION
				"Number of octets received from the client."
			::= { muEntry 10 }

		
		-- 1.3.6.1.4.1.4329.15.3.6.2.1.11
		muDuration OBJECT-TYPE
			SYNTAX Counter64
			MAX-ACCESS read-only
			STATUS current
			DESCRIPTION
				"Time client has been associated with the HWC."
			::= { muEntry 11 }

		
		-- 1.3.6.1.4.1.4329.15.3.6.2.1.12
		muAPName OBJECT-TYPE
			SYNTAX DisplayString
			MAX-ACCESS read-only
			STATUS current
			DESCRIPTION
				"Name of the Access Point the client is associated with."
			::= { muEntry 12 }

		
		-- 1.3.6.1.4.1.4329.15.3.6.3
		muTSPECTable OBJECT-TYPE
			SYNTAX SEQUENCE OF MuTSPECEntry
			MAX-ACCESS not-accessible
			STATUS current
			DESCRIPTION
				"Table of information for Admission Control Statistics by active client."
			::= { mobileUnits 3 }

		
		-- 1.3.6.1.4.1.4329.15.3.6.3.1
		muTSPECEntry OBJECT-TYPE
			SYNTAX MuTSPECEntry
			MAX-ACCESS not-accessible
			STATUS current
			DESCRIPTION
				"Information for Admission Control Statistics by active client."
			INDEX { apIndex, muMACAddress, tspecAC, tspecDirection }
			::= { muTSPECTable 1 }

		
		MuTSPECEntry ::=
			SEQUENCE { 
				tspecMuMACAddress
					MacAddress,
				tspecAC
					INTEGER,
				tspecDirection
					INTEGER,
				tspecApSerialNumber
					OCTET STRING,
				tspecMuIPAddress
					IpAddress,
				tspecBssMac
					MacAddress,
				tspecSsid
					DisplayString,
				tspecMDR
					INTEGER,
				tspecNMS
					INTEGER,
				tspecSBA
					INTEGER,
				tspecDlRate
					DisplayString,
				tspecUlRate
					DisplayString,
				tspecDlViolations
					DisplayString,
				tspecUlViolations
					DisplayString,
				tspecProtocol
					INTEGER
			 }

		-- 1.3.6.1.4.1.4329.15.3.6.3.1.1
		tspecMuMACAddress OBJECT-TYPE
			SYNTAX MacAddress
			MAX-ACCESS read-only
			STATUS current
			DESCRIPTION
				"Client MAC address."
			::= { muTSPECEntry 1 }

		
		-- 1.3.6.1.4.1.4329.15.3.6.3.1.2
		tspecAC OBJECT-TYPE
			SYNTAX INTEGER
				{
				be(0),
				bk(1),
				vi(2),
				vo(3),
				tvo(4),
				nwme(5)
				}
			MAX-ACCESS read-only
			STATUS current
			DESCRIPTION
				"Access Category, such as Best Effort, Background, Voice, Video, 
				and Reserved."
			::= { muTSPECEntry 2 }

		
		-- 1.3.6.1.4.1.4329.15.3.6.3.1.3
		tspecDirection OBJECT-TYPE
			SYNTAX INTEGER
				{
				uplink(0),
				dnlink(1),
				reserved(2),
				bidir(3)
				}
			MAX-ACCESS read-only
			STATUS current
			DESCRIPTION
				"Traffic direction, such as uplink direction, downlink direction."
			::= { muTSPECEntry 3 }

		
		-- 1.3.6.1.4.1.4329.15.3.6.3.1.4
		tspecApSerialNumber OBJECT-TYPE
			SYNTAX OCTET STRING
			MAX-ACCESS read-only
			STATUS current
			DESCRIPTION
				"16-character serial number of the AccessPoint."
			::= { muTSPECEntry 4 }

		
		-- 1.3.6.1.4.1.4329.15.3.6.3.1.5
		tspecMuIPAddress OBJECT-TYPE
			SYNTAX IpAddress
			MAX-ACCESS read-only
			STATUS current
			DESCRIPTION
				"Client IP Address."
			::= { muTSPECEntry 5 }

		
		-- 1.3.6.1.4.1.4329.15.3.6.3.1.6
		tspecBssMac OBJECT-TYPE
			SYNTAX MacAddress
			MAX-ACCESS read-only
			STATUS current
			DESCRIPTION
				"Access Point BSSID."
			::= { muTSPECEntry 6 }

		
		-- 1.3.6.1.4.1.4329.15.3.6.3.1.7
		tspecSsid OBJECT-TYPE
			SYNTAX DisplayString
			MAX-ACCESS read-only
			STATUS current
			DESCRIPTION
				"VNS SSID."
			::= { muTSPECEntry 7 }

		
		-- 1.3.6.1.4.1.4329.15.3.6.3.1.8
		tspecMDR OBJECT-TYPE
			SYNTAX INTEGER
			MAX-ACCESS read-only
			STATUS current
			DESCRIPTION
				"Mean Data Rate (bytes per second)."
			::= { muTSPECEntry 8 }

		
		-- 1.3.6.1.4.1.4329.15.3.6.3.1.9
		tspecNMS OBJECT-TYPE
			SYNTAX INTEGER
			MAX-ACCESS read-only
			STATUS current
			DESCRIPTION
				"Nominal MSDU size (bytes)."
			::= { muTSPECEntry 9 }

		
		-- 1.3.6.1.4.1.4329.15.3.6.3.1.10
		tspecSBA OBJECT-TYPE
			SYNTAX INTEGER
			MAX-ACCESS read-only
			STATUS current
			DESCRIPTION
				"Surplus Bandwidth Allowance."
			::= { muTSPECEntry 10 }

		
		-- 1.3.6.1.4.1.4329.15.3.6.3.1.11
		tspecDlRate OBJECT-TYPE
			SYNTAX DisplayString
			MAX-ACCESS read-only
			STATUS current
			DESCRIPTION
				"Downlink Rate (bytes per second)."
			::= { muTSPECEntry 11 }

		
		-- 1.3.6.1.4.1.4329.15.3.6.3.1.12
		tspecUlRate OBJECT-TYPE
			SYNTAX DisplayString
			MAX-ACCESS read-only
			STATUS current
			DESCRIPTION
				"Uplink Rate (bytes per second)."
			::= { muTSPECEntry 12 }

		
		-- 1.3.6.1.4.1.4329.15.3.6.3.1.13
		tspecDlViolations OBJECT-TYPE
			SYNTAX DisplayString
			MAX-ACCESS read-only
			STATUS current
			DESCRIPTION
				"Downlink Violations (bytes per second)."
			::= { muTSPECEntry 13 }

		
		-- 1.3.6.1.4.1.4329.15.3.6.3.1.14
		tspecUlViolations OBJECT-TYPE
			SYNTAX DisplayString
			MAX-ACCESS read-only
			STATUS current
			DESCRIPTION
				"Uplink Violations (bytes per second)."
			::= { muTSPECEntry 14 }

		
		-- 1.3.6.1.4.1.4329.15.3.6.3.1.15
		tspecProtocol OBJECT-TYPE
			SYNTAX INTEGER
				{
				proto80211a(1),
				proto80211g(2),
				proto80211b(3),
				proto80211an(4),
				proto80211bgn(5)
				}
			MAX-ACCESS read-only
			STATUS current
			DESCRIPTION
				"802.11 radio protocol."
			::= { muTSPECEntry 15 }

		
		-- 1.3.6.1.4.1.4329.15.3.7
		associations OBJECT IDENTIFIER ::= { hiPathWirelessMgmt 7 }

		
		-- 1.3.6.1.4.1.4329.15.3.7.1
		assocCount OBJECT-TYPE
			SYNTAX Integer32
			MAX-ACCESS read-write
			STATUS current
			DESCRIPTION
				"Total number of current client associations to the access point."
			::= { associations 1 }

		
		-- 1.3.6.1.4.1.4329.15.3.7.2
		assocTable OBJECT-TYPE
			SYNTAX SEQUENCE OF AssocEntry
			MAX-ACCESS not-accessible
			STATUS current
			DESCRIPTION
				"Table of information about clients associated with the access point."
			::= { associations 2 }

		
		-- 1.3.6.1.4.1.4329.15.3.7.2.1
		assocEntry OBJECT-TYPE
			SYNTAX AssocEntry
			MAX-ACCESS not-accessible
			STATUS current
			DESCRIPTION
				"Information for a single client in the association table."
			INDEX { assocMUMacAddress, apIndex, assocStartSysUpTime }
			::= { assocTable 1 }

		
		AssocEntry ::=
			SEQUENCE { 
				assocMUMacAddress
					MacAddress,
				assocStartSysUpTime
					TimeTicks,
				assocTxPackets
					Counter64,
				assocRxPackets
					Counter64,
				assocTxOctets
					Counter64,
				assocRxOctets
					Counter64,
				assocDuration
					Integer32,
				assocVnsIfIndex
					InterfaceIndex
			 }

		-- 1.3.6.1.4.1.4329.15.3.7.2.1.1
		assocMUMacAddress OBJECT-TYPE
			SYNTAX MacAddress
			MAX-ACCESS read-only
			STATUS current
			DESCRIPTION
				"MAC address of the client."
			::= { assocEntry 1 }

		
		-- 1.3.6.1.4.1.4329.15.3.7.2.1.2
		assocStartSysUpTime OBJECT-TYPE
			SYNTAX TimeTicks
			MAX-ACCESS read-only
			STATUS current
			DESCRIPTION
				"The system uptime that client became associated with the access point."
			::= { assocEntry 2 }

		
		-- 1.3.6.1.4.1.4329.15.3.7.2.1.3
		assocTxPackets OBJECT-TYPE
			SYNTAX Counter64
			MAX-ACCESS read-only
			STATUS current
			DESCRIPTION
				"Nubmer of tx packets to the client."
			::= { assocEntry 3 }

		
		-- 1.3.6.1.4.1.4329.15.3.7.2.1.4
		assocRxPackets OBJECT-TYPE
			SYNTAX Counter64
			MAX-ACCESS read-only
			STATUS current
			DESCRIPTION
				"Number of received packets from the client."
			::= { assocEntry 4 }

		
		-- 1.3.6.1.4.1.4329.15.3.7.2.1.5
		assocTxOctets OBJECT-TYPE
			SYNTAX Counter64
			MAX-ACCESS read-only
			STATUS current
			DESCRIPTION
				"Number of octets sent to the client."
			::= { assocEntry 5 }

		
		-- 1.3.6.1.4.1.4329.15.3.7.2.1.6
		assocRxOctets OBJECT-TYPE
			SYNTAX Counter64
			MAX-ACCESS read-only
			STATUS current
			DESCRIPTION
				"Number of octets received from the client."
			::= { assocEntry 6 }

		
		-- 1.3.6.1.4.1.4329.15.3.7.2.1.7
		assocDuration OBJECT-TYPE
			SYNTAX Integer32
			MAX-ACCESS read-write
			STATUS current
			DESCRIPTION
				"Length of time since last association."
			::= { assocEntry 7 }

		
		-- 1.3.6.1.4.1.4329.15.3.7.2.1.8
		assocVnsIfIndex OBJECT-TYPE
			SYNTAX InterfaceIndex
			MAX-ACCESS read-only
			STATUS current
			DESCRIPTION
				"Index of VNS to which the MU is associated with."
			::= { assocEntry 8 }

		
		-- 1.3.6.1.4.1.4329.15.3.8
		protocols OBJECT IDENTIFIER ::= { hiPathWirelessMgmt 8 }

		
		-- 1.3.6.1.4.1.4329.15.3.8.1
		wassp OBJECT IDENTIFIER ::= { protocols 1 }

		
		-- 1.3.6.1.4.1.4329.15.3.9
		logNotifications OBJECT IDENTIFIER ::= { hiPathWirelessMgmt 9 }

		
		-- 1.3.6.1.4.1.4329.15.3.9.1
		logEventSeverityThreshold OBJECT-TYPE
			SYNTAX LogEventSeverity
			MAX-ACCESS read-write
			STATUS current
			DESCRIPTION
				"Specifies the minimum level at which the SNMP agent will 
				send notifications for log events.  I.e., setting this
				value to 'major' will send notifcations for critical and
				major log events.  Setting the threshold to minor will 
				trap critical, major, and minor events.
				"
			::= { logNotifications 1 }

		
		-- 1.3.6.1.4.1.4329.15.3.9.3
		logEventSeverity OBJECT-TYPE
			SYNTAX LogEventSeverity
			MAX-ACCESS read-only
			STATUS current
			DESCRIPTION
				"Contains the severity of the most recently trapped hiPathWirelessLogAlarm notification."
			::= { logNotifications 3 }

		
		-- 1.3.6.1.4.1.4329.15.3.9.4
		logEventComponent OBJECT-TYPE
			SYNTAX OCTET STRING
			MAX-ACCESS read-only
			STATUS current
			DESCRIPTION
				"Contains the component which sent the most
				recently trapped hiPathWirelessLogAlarm notification."
			::= { logNotifications 4 }

		
		-- 1.3.6.1.4.1.4329.15.3.9.5
		logEventDescription OBJECT-TYPE
			SYNTAX OCTET STRING
			MAX-ACCESS read-only
			STATUS current
			DESCRIPTION
				"Contains the description of the most recently trapped 
				hiPathWirelessLogAlarm."
			::= { logNotifications 5 }

		
		-- 1.3.6.1.4.1.4329.15.3.9.6
		hiPathWirelessLogAlarm NOTIFICATION-TYPE
			OBJECTS { logEventSeverity, logEventComponent, logEventDescription }
			STATUS current
			DESCRIPTION 
				"Components of an alarm."
			::= { logNotifications 6 }

		
		-- 1.3.6.1.4.1.4329.15.3.19
		apNotifications OBJECT IDENTIFIER ::= { hiPathWirelessMgmt 19 }

		
		-- 1.3.6.1.4.1.4329.15.3.19.1
		apEventId OBJECT-TYPE
			SYNTAX INTEGER { apPollTimeout(1) }
			MAX-ACCESS read-write
			STATUS current
			DESCRIPTION
				"Identifies event associated with AP or AP tunnel:
				
				apPollTimeout - an event triggered when AP disconnects from HWC"
			::= { apNotifications 1 }

		
		-- 1.3.6.1.4.1.4329.15.3.19.2
		apEventDescription OBJECT-TYPE
			SYNTAX OCTET STRING
			MAX-ACCESS read-only
			STATUS current
			DESCRIPTION
				"Contains the description of the most recently triggered event."
			::= { apNotifications 2 }

		
		-- 1.3.6.1.4.1.4329.15.3.19.3
		apEventAPSerialNumber OBJECT-TYPE
			SYNTAX OCTET STRING (SIZE (16))
			MAX-ACCESS read-only
			STATUS current
			DESCRIPTION
				"16-character serial number of the AP."
			::= { apNotifications 3 }

		
		-- 1.3.6.1.4.1.4329.15.3.19.4
		apTunnelAlarm NOTIFICATION-TYPE
			OBJECTS { apEventId, apEventDescription, apEventAPSerialNumber }
			STATUS current
			DESCRIPTION 
				"alarm associated with AP and AP interface."
			::= { apNotifications 4 }

		
		-- 1.3.6.1.4.1.4329.15.3.30
		hiPathWirelessHWCConformance OBJECT IDENTIFIER ::= { hiPathWirelessMgmt 30 }

		
--  this module
		-- 1.3.6.1.4.1.4329.15.3.30.1
		hiPathWirelessHWCModule MODULE-COMPLIANCE
			STATUS current
			DESCRIPTION 
				"Conformance definition for the HWC MIB."
			MODULE -- this module
				MANDATORY-GROUPS { hiPathWirelessHWCGroup }
			::= { hiPathWirelessHWCConformance 1 }

		
		-- 1.3.6.1.4.1.4329.15.3.30.2
		hiPathWirelessHWCGroup OBJECT-GROUP
			OBJECTS { sysSoftwareVersion, sysLogLevel, logEventSeverityThreshold, logEventSeverity, logEventComponent, 
				logEventDescription, apEventId, apEventDescription, apEventAPSerialNumber, assocTxPackets, 
				assocRxPackets, assocTxOctets, assocRxOctets, assocDuration, assocCount, 
				assocMUMacAddress, assocStartSysUpTime, muTxPackets, muRxPackets, muTxOctets, 
				muRxOctets, muDuration, mobileUnitCount, muMACAddress, vnsIfIndex, 
				radioVNSRowStatus, apSpecific, apRowStatus, radioIfIndex, apDesc, 
				apSerialNumber, apPortifIndex, vnsFilterRulePortLow, vnsFilterRulePortHigh, apInUcastPkts, 
				apInNUcastPkts, apInOctets, apInErrors, apInDiscards, apOutUcastPkts, 
				apOutNUcastPkts, apOutOctets, apOutErrors, apOutDiscards, cpPasswordLabel, 
				cpLoginLabel, cpURL, vnsDHCPRangeIndex, vns3rdPartyAP, vnsUseDHCPRelay, 
				vnsMgmtTrafficEnable, vnsAuthModel, physicalPortCount, apSoftwareVersion, mgmtPortIfIndex, 
				mgmtPortHostname, mgmtPortDomain, portMgmtTrafficEnable, portDuplexMode, portFunction, 
				vnRole, vnIfIndex, vnHeartbeatInterval, ntpEnabled, ntpTimezone, 
				ntpTimeServer1, ntpTimeServer2, ntpTimeServer3, tunnelCount, vnsCount, 
				vnsDescription, vnsAssignmentMode, vnsMUSessionTimeout, vnsAllowMulticast, vnsSSID, 
				vnsDomain, vnsDNSServers, vnsWINSServers, vnsParentIfIndex, vnsStatus, 
				vnsDHCPRangeStart, vnsDHCPRangeEnd, vnsDHCPRangeType, vnsDHCPRangeStatus, vnsRadiusServerPort, 
				vnsRadiusServerRetries, vnsRadiusServerTimeout, vnsRadiusServerSharedSecret, vnsRadiusServerNASIdentifier, vnsRadiusServerAuthType, 
				vnsRadiusServerRowStatus, vnsFilterID, vnsFilterIDStatus, vnsFilterRuleOrder, vnsFilterRuleDirection, 
				vnsFilterRuleAction, vnsFilterRuleIPAddress, vnsFilterRuleProtocol, vnsFilterRuleEtherType, vnsFilterRuleStatus, 
				vnsPrivWEPKeyType, vnsPrivDynamicRekeyFrequency, vnsPrivWEPKeyLength, vnsPrivWPA1Enabled, vnsPrivUseSharedKey, 
				vnsPrivWPASharedKey, vnsWEPKeyIndex, vnsWEPKeyValue, activeVNSSessionCount, apCount, 
				apIndex, cpHeaderURL, cpFooterURL, cpMessage, cpReplaceGatewayWithFQDN, 
				cpDefaultRedirectionURL, cpConnectionIP, cpConnectionPort, cpSharedSecret, cpLogOff, 
				cpStatusCheck, cpType, apMacAddress, serviceLogFacility, sysLogServerIP, 
				sysLogServerPort, sysLogServerRowStatus, sysLogServerIndex, apActiveCount, apWiredIfIndex, 
				sysLogServerEnabled, apUpTime, assocVnsIfIndex, muIPAddress, muUser, 
				muState, muAPSerialNo, muVnsSSID, apRadioFrequency, includeAllServiceMessages, 
				tunnelStartIP, tunnelStartHWC, tunnelEndIP, tunnelEndHWC, apBroadcastDisassociate, 
				apName, sysSerialNo, vnsPrivWPA2Enabled, tunnelStatus, hiPathWirelessAppLogFacility, 
				vnsStatTxOctects, vnsStatRxOctects, vnsStatMulticastTxPkts, vnsStatMulticastRxPkts, vnsStatBroadcastTxPkts, 
				vnsStatBroadcastRxPkts, vnsStatName, vnsStatRadiusTotRequests, vnsStatRadiusReqFailed, vnsStatRadiusReqRejected, 
				vnsExceptionStatPktsAllowed, vnsExceptionStatPktsDenied, vnsExceptionFiterName, vnsVlanID, vnsMgmIpAddress, 
				vnsStatRxPkts, maxVoiceBWforReassociation, maxVoiceBWforAssociation, maxVideoBWforReassociation, maxVideoBWforAssociation, 
				portEnabled, vnsStatTxPkts, portName, portIpAddress, portMask, 
				portMacAddress, portVlanID, physicalPortsInternalVlanID, vnsMode, vnsQoSPriorityOverrideFlag, 
				vnsQoSPriorityOverrideSC, vnsQoSPriorityOverrideDSCP, apIpAssignmentType, apVlanID, vnsQoSClassificationServiceClass, 
				vnsQoSWirelessLegacyFlag, vnsQoSWirelessWMMFlag, vnsQoSWireless80211eFlag, vnsQoSWirelessTurboVoiceFlag, vnsQoSWirelessEnableUAPSD, 
				vnsQoSWirelessUseAdmControlVoice, vnsSuppressSSID, vnsEnable11hSupport, vnsApplyPowerBackOff, vnsProcessClientIEReq, 
				vnsWDSRFAPName, vnsWDSRFbgService, vnsWDSRFaService, vnsWDSRFPreferredParent, vnsWDSRFBridge, 
				vnsWDSStatAPName, vnsWDSStatAPRole, vnsWDSStatAPRadio, vnsWDSStatAPParent, vnsWDSStatSSID, 
				vnsWDSStatRxFrame, vnsWDSStatTxFrame, vnsWDSStatRxError, vnsWDSStatTxError, vnsWDSStatRxRSSI, 
				vnsWDSStatRxRate, vnsWDSStatTxRate, apCredentialType, apCertificateExpiry, apIfMAC, 
				vnsQoSWirelessUseAdmControlVideo, vnsInterfaceName, vnsWDSRFBackupParent, vnsQoSWirelessULPolicerAction, vnsQoSWirelessDLPolicerAction, 
				apFastFailoverEnable, tspecMuMACAddress, tspecAC, tspecDirection, tspecApSerialNumber, 
				tspecMuIPAddress, tspecBssMac, tspecSsid, tspecMDR, tspecNMS, 
				tspecSBA, tspecDlRate, tspecUlRate, tspecDlViolations, tspecUlViolations, 
				tspecProtocol, portDHCPEnable, portDHCPGateway, portDHCPDomain, portDHCPDefaultLease, 
				apLinkTimeout, portDHCPMaxLease, portDHCPDnsServers, portDHCPWins, phyDHCPRangeIndex, 
				phyDHCPRangeStart, phyDHCPRangeEnd, phyDHCPRangeType, phyDHCPRangeStatus, vnsDLSSupportEnable, 
				vnsDLSAddress, vnsDLSPort, vnsRateControlProfile, vnsSessionAvailabilityEnable, vnsRateControlProfInd, 
				vnsRateControlProfName, vnsRateControlCIR, vnsRateControlCBS, ntpServerEnabled, apSwVersion, 
				apRole, apEnvironment, apPollTimeout, apPollInterval, apTelnetAccess, 
				apHome, apState, primaryDNS, secondaryDNS, tertiaryDNS, 
				apRestartServiceContAbsent, apMaintainClientSession, apStatus, apHwVersion, externalRadiusServerRowStatus, 
				externalRadiusServerSharedSecret, externalRadiusServerAddress, externalRadiusServerName, physicalFlash, vnsRadiusServerName, 
				vnsRadiusServerNasAddress, muAPName, apIpAddress, dasReplayInterval, dasPort, 
				apIPAddress, apHostname }
			STATUS current
			DESCRIPTION 
				"Conformance groups."
			::= { hiPathWirelessHWCConformance 2 }

		
		-- 1.3.6.1.4.1.4329.15.3.30.3
		hiPathWirelessHWCAlarms NOTIFICATION-GROUP
			NOTIFICATIONS { hiPathWirelessLogAlarm, apTunnelAlarm }
			STATUS current
			DESCRIPTION 
				"Conformance information for the alarm groups."
			::= { hiPathWirelessHWCConformance 3 }

		
	
	END
