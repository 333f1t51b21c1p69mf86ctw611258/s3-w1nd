RDN-CHASSIS-MIB DEFINITIONS ::= BEGIN

        IMPORTS
            MODULE-IDENTITY, OBJECT-TYPE, TimeTicks, Integer32
                FROM SNMPv2-SMI
			riverdelta
				FROM RDN-MIB
            DisplayString
			    FROM RFC1213-MIB;


		-- chassis module definitions

        rdnChassis MODULE-IDENTITY
            LAST-UPDATED "200206250000Z" -- 25th June 2002
            ORGANIZATION "Motorola"
            CONTACT-INFO "Motorola
                          3 Highwood Drive
                          Tewksbury, MA 01867
                          Tel: +1 978 858 2000
                          Fax: +1 978 858 2399
                          E-mail:  BSRSNMP@maillist2001.mot.com

                          Tom Keske 
                          Motorola BCS
                          20 Cabot Blvd. MA07 M2-330
                          Mansfield, MA 02048
                          Tel: 1-508-851-8325
                          Fax: 1-508-851-8510
                          E-mail: Tom.Keske@motorola.com"
            DESCRIPTION
                    "MIB module for Motorola
                     Chassis."
            REVISION     "0004040000Z"
            DESCRIPTION
                    "Initial creation."
            REVISION     "0005230000Z"
            DESCRIPTION
                    "Moved 'riverdelta' definition into a separate
                     file; this allows an external module to
                     not include the entire riverdelta chassis mib
                     when needing only the 'riverdelta' definition."
            REVISION     "0101150000Z"
            DESCRIPTION
                    "Added option 'unknown' to variable chassisPartner."
            REVISION     "0105080000Z"
            DESCRIPTION
                    "Changed rdnCardSerial to DisplayString;
                     removed rdnCardSlots, rdnConfigReg, rdnConfigRegNext,
                     and rdnChassisPartner; added options bsr1000 and
                     bsr2000 to rdnChassisType; plus other syntax changes."
            ::= { riverdelta 1 }


          --
          -- chassis group should be present in all products.
          --

               rdnChassisType OBJECT-TYPE
                   SYNTAX  INTEGER {
                        unknown(1),
                        bsr64000(2),
                        bsr1000(3),
                        osr2000(4)
                        }
                   MAX-ACCESS  read-only
                   STATUS  current
                   DESCRIPTION
                           "Chassis type."
                   ::= { rdnChassis 1 }

               rdnChassisVersion OBJECT-TYPE
                   SYNTAX  DisplayString
                   MAX-ACCESS  read-only
                   STATUS  current
                   DESCRIPTION
                           "Chassis hardware revision level, or an empty
                           string if unavailable."
                   ::= { rdnChassis 2 }

               rdnChassisId OBJECT-TYPE
                   SYNTAX  DisplayString
                   MAX-ACCESS  read-write
                   STATUS  current
                   DESCRIPTION
                           "Unique ID string. Defaults to chassis serial
                           number if available, otherwise empty. Can
                           also be set with 'snmp-server chassis-id'."
                   ::= { rdnChassis 3 }

               rdnProcessorRam OBJECT-TYPE
                   SYNTAX  Integer32
                   MAX-ACCESS  read-only
                   STATUS  current
                   DESCRIPTION
                           "Bytes of RAM available to CPU."
                   ::= { rdnChassis 4 }

               rdnNvRAMSize OBJECT-TYPE
                   SYNTAX  Integer32
                   MAX-ACCESS  read-only
                   STATUS  current
                   DESCRIPTION
                           "Bytes of non-volatile configuration memory."
                   ::= { rdnChassis 5 }

               rdnNvRAMUsed OBJECT-TYPE
                   SYNTAX  Integer32
                   MAX-ACCESS  read-only
                   STATUS  current
                   DESCRIPTION
                           "Bytes of non-volatile configuration memory
                           in use."
                   ::= { rdnChassis 6 }

               rdnFlashSize OBJECT-TYPE
                   SYNTAX  Integer32
                   MAX-ACCESS  read-only
                   STATUS  current
                   DESCRIPTION
                           "Bytes flash memory."
                   ::= { rdnChassis 7 }

               rdnCardTable OBJECT-TYPE
                   SYNTAX  SEQUENCE OF RdnCardEntry
                   MAX-ACCESS  not-accessible
                   STATUS  current
                   DESCRIPTION
                            "Chassis card table."
                   ::= { rdnChassis 8 }

               rdnCardEntry OBJECT-TYPE
                   SYNTAX RdnCardEntry
                   MAX-ACCESS  not-accessible
                   STATUS  current
                   DESCRIPTION
                            "Chassis card table."
                   INDEX { rdnCardIndex }
               ::= { rdnCardTable 1 }

               RdnCardEntry ::=
                   SEQUENCE {
                       rdnCardIndex
                           Integer32,
                       rdnCardType
                           INTEGER,
                       rdnCardDescr
                           DisplayString,
                       rdnCardSerial
                           DisplayString,
                       rdnCardHwVersion
                           DisplayString,
                       rdnCardSwVersion
                           DisplayString,
                       rdnCardSlotNumber
                           Integer32,
                       rdnCardContainedByIndex
                           Integer32,
                       rdnCardOperStatus
                           INTEGER
                   }

               --
               -- start of card table
               --

               rdnCardIndex OBJECT-TYPE
                   SYNTAX  Integer32
                   MAX-ACCESS  read-only
                   STATUS  current
                   DESCRIPTION
                           "Index into cardTable (not physical chassis
                           slot number)."
                   ::= { rdnCardEntry 1 }

               rdnCardType OBJECT-TYPE
                   SYNTAX  INTEGER {
                        unknown(1),
                        srm(2),
                        io(3)
                        }
                   MAX-ACCESS  read-only
                   STATUS  current
                   DESCRIPTION
                           "Functional type of this card."
                   ::= { rdnCardEntry 2 }

               rdnCardDescr OBJECT-TYPE
                   SYNTAX  DisplayString
                   MAX-ACCESS  read-only
                   STATUS  current
                   DESCRIPTION
                           "Text description of this card."
                   ::= { rdnCardEntry 3 }

               rdnCardSerial OBJECT-TYPE
                   SYNTAX  DisplayString
                   MAX-ACCESS  read-only
                   STATUS  current
                   DESCRIPTION
                           "The serial number of this card, or zero if
                           unavailable."
                   ::= { rdnCardEntry 4 }

               rdnCardHwVersion OBJECT-TYPE
                   SYNTAX  DisplayString
                   MAX-ACCESS  read-only
                   STATUS  current
                   DESCRIPTION
                           "Hardware revision level of this card, or an
                           empty string if unavailable."
                   ::= { rdnCardEntry 5 }

               rdnCardSwVersion OBJECT-TYPE
                   SYNTAX  DisplayString
                   MAX-ACCESS  read-only
                   STATUS  current
                   DESCRIPTION
                           "Version of the firmware or microcode
                           installed on this card, or an empty string if
                           unavailable."
                   ::= { rdnCardEntry 6 }

               rdnCardSlotNumber OBJECT-TYPE
                   SYNTAX  Integer32
                   MAX-ACCESS  read-only
                   STATUS  current
                   DESCRIPTION
                           "Slot number relative to the containing card or 
                           chassis, or -1 if neither applicable nor 
                           determinable."
                   ::= { rdnCardEntry 7 }

               rdnCardContainedByIndex OBJECT-TYPE
                   SYNTAX  Integer32
                   MAX-ACCESS  read-only
                   STATUS  current
                   DESCRIPTION
                           "cardIndex of the parent card which
                           directly contains this card, or 0 if
                           contained by the chassis, or -1 if not
                           applicable nor determinable."
                   ::= { rdnCardEntry 8 }

               rdnCardOperStatus OBJECT-TYPE
                   SYNTAX  INTEGER {
                          not-specified(1), 
                          up(2),
                          down(3),
                          standby(4)
                          }
                   MAX-ACCESS  read-only
                   STATUS  current
                   DESCRIPTION
                           "The operational status of the card.
                           cardOperStatus is up when a card is
                           recognized by the device and is enabled for
                           operation. cardOperStatus is down if the
                           card is not recognized by the device, or if
                           it is not enabled for operation.
                           cardOperStatus is standby if the card is
                           enabled and acting as a standby slave"
                   ::= { rdnCardEntry 9 }


               -- end of card table


               rdnChassisSlots OBJECT-TYPE
                   SYNTAX  Integer32
                   MAX-ACCESS  read-only
                   STATUS  current
                   DESCRIPTION
                           "Number of slots in this chassis, or -1 if
                           neither applicable nor determinable."
                   ::= { rdnChassis 9 }

               rdnSlotTable OBJECT-TYPE
                   SYNTAX  SEQUENCE OF RdnSlotEntry
                   MAX-ACCESS  not-accessible
                   STATUS  current
                   DESCRIPTION
                            "Chassis slot table."
                   ::= { rdnChassis 10 }

               --
               -- start of slot table
               --

               rdnSlotEntry OBJECT-TYPE
                   SYNTAX RdnSlotEntry
                   MAX-ACCESS  not-accessible
                   STATUS  current
                   DESCRIPTION
                            "Chassis slot table."
                   INDEX { rdnSlotIndex }
               ::= { rdnSlotTable 1 }

               RdnSlotEntry ::=
                   SEQUENCE {
                       rdnSlotIndex               Integer32,
                       rdnSlotType                INTEGER,
                       rdnSlotNumber              Integer32,
                       rdnSlotOperStatus          INTEGER,
                       rdnOfflineModemCount       Integer32,
                       rdnOnlineModemCount        Integer32,
                       rdnActiveModemCount        Integer32,
                       rdnRegisteredModemCount    Integer32,
                       rdnProvisionedModemCount   Integer32,
                       rdnUnregisteredModemCount  Integer32,
                       rdnResetSlotStats          INTEGER
                   }

               rdnSlotIndex OBJECT-TYPE
                   SYNTAX  Integer32 (0..2147483647)
                   MAX-ACCESS  read-only
                   STATUS  current
                   DESCRIPTION
                           "Index into slotTable (not physical slot number)."
                   ::= { rdnSlotEntry 1 }

               rdnSlotType OBJECT-TYPE
                   SYNTAX  INTEGER {
                        unknown(1),
                        srm(2),
                        io(3)
                        }
                   MAX-ACCESS  read-only
                   STATUS  current
                   DESCRIPTION
                           "Functional type of this slot."
                   ::= { rdnSlotEntry 2 }

               rdnSlotNumber OBJECT-TYPE
                   SYNTAX  Integer32 (0..2147483647)
                   MAX-ACCESS  read-only
                   STATUS  current
                   DESCRIPTION
                           "Slot number relative to the containing card or 
                           chassis, or -1 if neither applicable nor 
                           determinable."
                   ::= { rdnSlotEntry 3 }

               rdnSlotOperStatus OBJECT-TYPE
                   SYNTAX  INTEGER {
                          not-specified(1), 
                          up(2),
                          down(3),
                          standby(4)
                          }
                   MAX-ACCESS  read-only
                   STATUS  current
                   DESCRIPTION
                           "The operational status of the card.
                           cardOperStatus is up when a card is
                           recognized by the device and is enabled for
                           operation. cardOperStatus is down if the
                           card is not recognized by the device, or if
                           it is not enabled for operation.
                           cardOperStatus is standby if the card is
                           enabled and acting as a standby slave"
                   ::= { rdnSlotEntry 4 }

               rdnOfflineModemCount OBJECT-TYPE
                   SYNTAX      Integer32 (0..2147483647)
                   MAX-ACCESS  read-only
                   STATUS      current
                   DESCRIPTION "Number of offline modems for this slot"
                   ::= { rdnSlotEntry 5 }

               rdnOnlineModemCount OBJECT-TYPE
                   SYNTAX      Integer32 (0..2147483647)
                   MAX-ACCESS  read-only
                   STATUS      current
                   DESCRIPTION "Number of online modems for this slot"
                   ::= { rdnSlotEntry 6 }

               rdnActiveModemCount OBJECT-TYPE
                   SYNTAX      Integer32 (0..2147483647)
                   MAX-ACCESS  read-only
                   STATUS      current
                   DESCRIPTION "Number of active modems for this slot"
                   ::= { rdnSlotEntry 7 }

               rdnRegisteredModemCount OBJECT-TYPE
                   SYNTAX      Integer32 (0..2147483647)
                   MAX-ACCESS  read-only
                   STATUS      current
                   DESCRIPTION "Number of registered modems for this slot"
                   ::= { rdnSlotEntry 8 }

               rdnProvisionedModemCount OBJECT-TYPE
                   SYNTAX      Integer32 (0..2147483647)
                   MAX-ACCESS  read-only
                   STATUS      current
                   DESCRIPTION "Number of provisioned modems for this slot"
                   ::= { rdnSlotEntry 9 }

               rdnUnregisteredModemCount OBJECT-TYPE
                   SYNTAX      Integer32 (0..2147483647)
                   MAX-ACCESS  read-only
                   STATUS      current
                   DESCRIPTION "Number of registered modems for this slot"
                   ::= { rdnSlotEntry 10 }

               rdnResetSlotStats OBJECT-TYPE
                   SYNTAX      INTEGER { clear(1) }
                   MAX-ACCESS  read-write
                   STATUS      current
                   DESCRIPTION "The byte and packet counters for all the cable
                                modems for the given slot is reset by a 'set'
                                to this object. Only the value of 'clear(1)'
                                is allowed. On a get operation, it returns '0'"
                   ::= { rdnSlotEntry 11 }



 
               -- end of slot table


               rdnCardIfIndexTable OBJECT-TYPE
                   SYNTAX  SEQUENCE OF RdnCardIfIndexEntry
                   MAX-ACCESS  not-accessible
                   STATUS  current
                   DESCRIPTION
                            "Chassis card table."
                   ::= { rdnChassis 11 }

               --
               -- start of card if table
               --

               rdnCardIfIndexEntry OBJECT-TYPE
                   SYNTAX      RdnCardIfIndexEntry
                   MAX-ACCESS  not-accessible
                   STATUS      current
                   DESCRIPTION
                            "Chassis card table."
                   INDEX { rdnCardIfIndex }
               ::= { rdnCardIfIndexTable 1 }

               RdnCardIfIndexEntry ::=
                   SEQUENCE {
                       rdnCardIfIndex                 Integer32,
                       rdnCardIfSlotNumber            Integer32,
                       rdnCardIfPortNumber            Integer32,
                       rdnCardIfCardIndex             Integer32,
                       rdnCardIfConnectorTypeEnabled  INTEGER
                   }

               rdnCardIfIndex OBJECT-TYPE
                   SYNTAX      Integer32
                   MAX-ACCESS  read-only
                   STATUS      current
                   DESCRIPTION
                           "matches RFC1213 ifTable IfIndex"
                   ::= { rdnCardIfIndexEntry 1 }

               rdnCardIfSlotNumber OBJECT-TYPE
                   SYNTAX      Integer32
                   MAX-ACCESS  read-only
                   STATUS      current
                   DESCRIPTION
                           "Chassis slot number, or -1 if neither
                           applicable nor determinable."
                   ::= { rdnCardIfIndexEntry 2 }

               rdnCardIfPortNumber OBJECT-TYPE
                   SYNTAX      Integer32
                   MAX-ACCESS  read-only
                   STATUS      current
                   DESCRIPTION
                           "Chassis port number, unique per port on a 
                            given card if available."
                   ::= { rdnCardIfIndexEntry 3 }

               rdnCardIfCardIndex OBJECT-TYPE
                   SYNTAX      Integer32
                   MAX-ACCESS  read-only
                   STATUS      current
                   DESCRIPTION
                           "cardIndex of the card in the Chassis cardTable
                            which contains this interface."
                   ::= { rdnCardIfIndexEntry 4 }

               rdnCardIfConnectorTypeEnabled OBJECT-TYPE
                   SYNTAX      INTEGER {
                                   not-specified(1), 
                                   none (2),
                                   rj-45 (3),
                                   db-40 (4),
                                   db-15 (5)
                               }
                   MAX-ACCESS  read-only
                   STATUS      current
                   DESCRIPTION "Interface connector type currently enabled.
                                Value will be 1 if not known or not used,
                                or 2 if none of this ports' interface
                                connectors are enabled."
                   ::= { rdnCardIfIndexEntry 5 }

               -- end of card if table


               rdnSysUpTimeAtLastChassisChange OBJECT-TYPE
                   SYNTAX  TimeTicks
                   MAX-ACCESS  read-only
                   STATUS  current
                   DESCRIPTION
                           "Time in seconds/100 from the last cold
                           start to the last change in the chassis'
                           configuration. This value will be updated
                           whenever the chassis experiences a change
                           in the count, type, or slot position of
                           a card in cardTable."
                   ::= { rdnChassis 12 }

               rdnSysUpTimeAtLastConfigChange OBJECT-TYPE
                   SYNTAX  TimeTicks
                   MAX-ACCESS  read-only
                   STATUS  current
                   DESCRIPTION
                           "Time in seconds/100 from the last
						   configuration change in the system. This
						   value will be updated whenever the system
						   experiences a change in the configuration."
                   ::= { rdnChassis 13 }


        -- traps


        -- conformance information


        -- compliance statements


        -- units of conformance

    END
