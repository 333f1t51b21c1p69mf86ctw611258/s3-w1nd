-- Retix Remote Bridge/Router family MIB
-- Copyright Retix 1991. 
-- Retix. 2401 Colorado Ave, Santa Monica. CA 90404.

-- Retix: The OpenNetworking Company.

-- Version No 1.3 : Replaces last version on the Internet

-- Changes : 	Some changes to help ensure MIB compilers can 
-- 	 	compile this mib.

        RETIX-MIB --{ iso org(3) dod(6) internet(1) mgmt(2) 1 }

    	DEFINITIONS ::= BEGIN

	IMPORTS
	NetworkAddress, IpAddress, Counter, Gauge, TimeTicks,
	enterprises
		FROM RFC1155-SMI
	OBJECT-TYPE
		FROM RFC-1212;

	retix      OBJECT IDENTIFIER ::= { enterprises 72 }

	station    OBJECT IDENTIFIER ::= { retix 1 } -- Station Group
	lapb       OBJECT IDENTIFIER ::= { retix 2 } -- LAPB Group
	ieee8023   OBJECT IDENTIFIER ::= { retix 3 } -- IEEE 802.3 Group
	phySerIf   OBJECT IDENTIFIER ::= { retix 4 } -- Physical Serial Group
	mlink      OBJECT IDENTIFIER ::= { retix 5 } -- Multilink Group
	lan        OBJECT IDENTIFIER ::= { retix 6 } -- LAN Group
	bridge     OBJECT IDENTIFIER ::= { retix 7 } -- Bridge Group
	product    OBJECT IDENTIFIER ::= { retix 8 } -- Product Group
	router     OBJECT IDENTIFIER ::= { retix 10 } -- Router Group
	boot       OBJECT IDENTIFIER ::= { retix 11 } -- Bootp Group
	boothelper OBJECT IDENTIFIER ::= { retix 12 } -- Boothelper Group
	remote     OBJECT IDENTIFIER ::= { retix 13 } -- Remote Group

	ipx        OBJECT IDENTIFIER ::= { remote 1 } -- IPX group
	decnet     OBJECT IDENTIFIER ::= { remote 2 } -- Decnet group
	rmtLapb    OBJECT IDENTIFIER ::= { remote 3 } -- Remote Lapb group
	x25        OBJECT IDENTIFIER ::= { remote 4 } -- x25 group

-- object types

    -- Station Group

	stationTime OBJECT-TYPE
		SYNTAX  OCTET STRING (SIZE(13))
		ACCESS  read-write
		STATUS  mandatory
		DESCRIPTION ""
		::=  { station 1 }

	stationResetCounter OBJECT-TYPE
		SYNTAX  Counter
		ACCESS  read-only
		STATUS  mandatory
		DESCRIPTION ""
		::=  { station 2 }

	freeBufferCount OBJECT-TYPE
		SYNTAX  INTEGER
		ACCESS  read-only
		STATUS  mandatory
		DESCRIPTION ""
		::=  { station 3 }

	freeHeaderCount OBJECT-TYPE
		SYNTAX  INTEGER
		ACCESS  read-only
		STATUS  mandatory
		DESCRIPTION ""
		::=  { station 4 }

	physBlkSize OBJECT-TYPE
		SYNTAX  INTEGER (300..1600)
		ACCESS  read-only
		STATUS  mandatory
		DESCRIPTION ""
		::=  { station 5 }

	newPhysBlkSize OBJECT-TYPE
		SYNTAX  INTEGER (300..1600)
		ACCESS  read-write
		STATUS  mandatory
		DESCRIPTION ""
		::=  { station 6 }

	resetStation OBJECT-TYPE
		SYNTAX  INTEGER
		ACCESS  read-write
		STATUS  mandatory
		DESCRIPTION ""
		::=  { station 7 }

	initStation OBJECT-TYPE
		SYNTAX  INTEGER
		ACCESS  read-write
		STATUS  mandatory
		DESCRIPTION ""
		::=  { station 8 }

	resetStats OBJECT-TYPE
		SYNTAX  INTEGER
		ACCESS  read-write
		STATUS  mandatory
		DESCRIPTION ""
		::=  { station 9 }

	processorLoading OBJECT-TYPE
		SYNTAX  INTEGER
		ACCESS  read-only
		STATUS  mandatory
		DESCRIPTION ""
		::=  { station 10 }

	trapDestinationTable OBJECT IDENTIFIER ::= { station 11 }

	trapDestTable OBJECT-TYPE
		SYNTAX  SEQUENCE OF TrapDestEntry
		ACCESS  not-accessible
		STATUS  mandatory
		DESCRIPTION ""
		::=  { trapDestinationTable 1 }

	trapDestEntry OBJECT-TYPE
		SYNTAX  TrapDestEntry
		ACCESS  not-accessible 
		STATUS  mandatory
		DESCRIPTION ""
		INDEX	{ trapDestEntryIpAddr }
	::=  { trapDestTable 1 }

	TrapDestEntry ::= SEQUENCE {
		trapDestEntryIpAddr
			IpAddress,
		trapDestEntryCommunityName
			OCTET STRING,
		trapDestEntryType
			INTEGER
		}

	trapDestEntryIpAddr OBJECT-TYPE
		SYNTAX  IpAddress
		ACCESS  read-write
		STATUS  mandatory
		DESCRIPTION ""
		::=  { trapDestEntry 1 }

	trapDestEntryCommunityName OBJECT-TYPE
		SYNTAX  OCTET STRING (SIZE(0..10))
		ACCESS  read-write
		STATUS  mandatory
		DESCRIPTION ""
		::=  { trapDestEntry 2 }

	trapDestEntryType OBJECT-TYPE
		SYNTAX  INTEGER
		ACCESS  read-write
		STATUS  mandatory
		DESCRIPTION ""
		::=  { trapDestEntry 3 }

	trapDestAction OBJECT-TYPE
		SYNTAX  INTEGER
		ACCESS  read-write
		STATUS  mandatory
		DESCRIPTION ""
		::=  { trapDestinationTable 2 }

	trapDestPage OBJECT-TYPE
		SYNTAX  OCTET STRING (SIZE(240))
		ACCESS  read-only
		STATUS  mandatory
		DESCRIPTION ""
		::=  { trapDestinationTable 3 }

	passWord OBJECT-TYPE
		SYNTAX  OCTET STRING (SIZE(0..10))
		ACCESS  read-write
		STATUS  mandatory
		DESCRIPTION ""
		::=  { station 12 }

	snmpAccessPolicyObject OBJECT IDENTIFIER ::= { station 13 }

	snmpAccessPolicyTable OBJECT-TYPE
		SYNTAX  SEQUENCE OF SnmpAccessPolicyEntry
		ACCESS  not-accessible 
		STATUS  mandatory
		DESCRIPTION ""
		::=  { snmpAccessPolicyObject 1 }

	snmpAccessPolicyEntry OBJECT-TYPE
		SYNTAX  SnmpAccessPolicyEntry
		ACCESS  not-accessible 
		STATUS  mandatory
		DESCRIPTION ""
		INDEX	{ accessPolicyIndex }
		::=  { snmpAccessPolicyTable 1 }

	 SnmpAccessPolicyEntry ::= SEQUENCE {
		accessPolicyIndex
			INTEGER,
		communityName
			OCTET STRING,
		accessMode
			INTEGER,
		snmpAccessPolicyType
			INTEGER
		}

	accessPolicyIndex OBJECT-TYPE
		SYNTAX  INTEGER
		ACCESS  read-write
		STATUS  mandatory
		DESCRIPTION ""
		::=  { snmpAccessPolicyEntry 1 }

	communityName OBJECT-TYPE
		SYNTAX  OCTET STRING ( SIZE (0..10))
		ACCESS  read-write
		STATUS  mandatory
		DESCRIPTION ""
		::=  { snmpAccessPolicyEntry 2 }

	accessMode OBJECT-TYPE
		SYNTAX  INTEGER
		ACCESS  read-write
		STATUS  mandatory
		DESCRIPTION ""
		::=  { snmpAccessPolicyEntry 3 }

	snmpAccessPolicyType OBJECT-TYPE
		SYNTAX  INTEGER
		ACCESS  read-write
		STATUS  mandatory
		DESCRIPTION ""
		::=  { snmpAccessPolicyEntry 4 }

	snmpAccessPolicyAction OBJECT-TYPE
		SYNTAX  INTEGER
		ACCESS  read-write
		STATUS  mandatory
		DESCRIPTION ""
		::=  { snmpAccessPolicyObject 2 }

	snmpAccessPolicyPage OBJECT-TYPE
		SYNTAX  OCTET STRING (SIZE(256))
		ACCESS  read-only
		STATUS  mandatory
		DESCRIPTION ""
		::=  { snmpAccessPolicyObject 3 }

	authenticationTrapStatus OBJECT-TYPE
		SYNTAX  INTEGER (0..1)
		ACCESS  read-write
		STATUS  mandatory
		DESCRIPTION ""
		::=  { station 14 }

	serialTxQueueSize OBJECT-TYPE
		SYNTAX  INTEGER (1..127)
		ACCESS  read-write
		STATUS  mandatory
		DESCRIPTION ""
		::=  { station 15 }

	internalQueueCurrentLength OBJECT-TYPE
		SYNTAX  INTEGER
		ACCESS  read-only
		STATUS  mandatory
		DESCRIPTION ""
		::=  { station 16 }

	queueUpperLimit OBJECT-TYPE
		SYNTAX  INTEGER
		ACCESS  read-write
		STATUS  mandatory
		DESCRIPTION ""
		::=  { station 17 }

	lanQueueSize OBJECT-TYPE
		SYNTAX  INTEGER
		ACCESS  read-only
		STATUS  mandatory
		DESCRIPTION ""
		::=  { station 18 }


	--  LAPB Group

	lapbNumber OBJECT-TYPE
		SYNTAX  INTEGER
		ACCESS  read-only
		STATUS  mandatory
		DESCRIPTION ""
		::=  { lapb 1 }

	lapbTable OBJECT-TYPE
		SYNTAX  SEQUENCE OF LapbEntry
		ACCESS  not-accessible 
		STATUS  mandatory
		DESCRIPTION ""
		::=  { lapb 2 }

	lapbEntry OBJECT-TYPE
		SYNTAX  LapbEntry
		ACCESS  not-accessible 
		STATUS  mandatory
		DESCRIPTION ""
		INDEX	{ lapbIndex }
		::=  { lapbTable 1 }

	LapbEntry ::= SEQUENCE {
		lapbIndex
			INTEGER,
		lapbModeT1
			INTEGER,
		lapbAutoT1value
			INTEGER,
		lapbManualT1value
			INTEGER,
		lapbWindow
			INTEGER,
		lapbPolarity
			INTEGER,
		lapbResetCount
			Counter,
		lapbSendFrameCount
			Counter,
		lapbRcvFrameCount
			Counter,
		lapbSendOctetCount
			Counter,
		lapbRcvOctetCount
			Counter,
		lapbAbortCount
			Counter,
		lapbCrcErrorCount
			Counter,
		lapbState
			INTEGER,
		lapbLastResetTime
			OCTET STRING,
		lapbLastResetReason
			INTEGER,
		lapbLinkReset
			INTEGER
		}

	lapbIndex OBJECT-TYPE
		SYNTAX  INTEGER
		ACCESS  read-only
		STATUS  mandatory
		DESCRIPTION ""
		::=  { lapbEntry 1 }

	lapbModeT1 OBJECT-TYPE
		SYNTAX  INTEGER (0..1)
		ACCESS  read-write
		STATUS  mandatory
		DESCRIPTION ""
		::=  { lapbEntry 2 }

	lapbAutoT1value OBJECT-TYPE
		SYNTAX  INTEGER
		ACCESS  read-only
		STATUS  mandatory
		DESCRIPTION ""
		::=  { lapbEntry 3 }

	lapbManualT1value OBJECT-TYPE
		SYNTAX  INTEGER (10..5000)
		ACCESS  read-write
		STATUS  mandatory
		DESCRIPTION ""
		::=  { lapbEntry 4 }

	lapbWindow OBJECT-TYPE
		SYNTAX  INTEGER (7..127)
		ACCESS  read-only
		STATUS  mandatory
		DESCRIPTION ""
		::=  { lapbEntry 5 }

	lapbPolarity OBJECT-TYPE
		SYNTAX  INTEGER (0..1)
		ACCESS  read-only
		STATUS  mandatory
		DESCRIPTION ""
		::=  { lapbEntry 6 }

	lapbResetCount OBJECT-TYPE
		SYNTAX  Counter
		ACCESS  read-only
		STATUS  mandatory
		DESCRIPTION ""
		::=  { lapbEntry 7 }

	lapbSendFrameCount OBJECT-TYPE
		SYNTAX  Counter
		ACCESS  read-only
		STATUS  mandatory
		DESCRIPTION ""
		::=  { lapbEntry 8 }

	lapbRcvFrameCount OBJECT-TYPE
		SYNTAX  Counter
		ACCESS  read-only
		STATUS  mandatory
		DESCRIPTION ""
		::=  { lapbEntry 9 }

	lapbSendOctetCount OBJECT-TYPE
		SYNTAX  Counter
		ACCESS  read-only
		STATUS  mandatory
		DESCRIPTION ""
		::=  { lapbEntry 10 }

	lapbRcvOctetCount OBJECT-TYPE
		SYNTAX  Counter
		ACCESS  read-only
		STATUS  mandatory
		DESCRIPTION ""
		::=  { lapbEntry 11 }

	lapbAbortCount OBJECT-TYPE
		SYNTAX  Counter
		ACCESS  read-only
		STATUS  mandatory
		DESCRIPTION ""
		::=  { lapbEntry 12 }

	lapbCrcErrorCount OBJECT-TYPE
		SYNTAX  Counter
		ACCESS  read-only
		STATUS  mandatory
		DESCRIPTION ""
		::=  { lapbEntry 13 }

	lapbState OBJECT-TYPE
		SYNTAX  INTEGER (0..3)
		ACCESS  read-only
		STATUS  mandatory
		DESCRIPTION ""
		::=  { lapbEntry 14 }

	lapbLastResetTime OBJECT-TYPE
		SYNTAX  OCTET STRING (SIZE (13))
		ACCESS  read-only
		STATUS  mandatory
		DESCRIPTION ""
		::=  { lapbEntry 15 }

	lapbLastResetReason OBJECT-TYPE
		SYNTAX  INTEGER (0..8)
		ACCESS  read-only
		STATUS  mandatory
		DESCRIPTION ""
		::=  { lapbEntry 16 }

	lapbLinkReset OBJECT-TYPE
		SYNTAX  INTEGER 
		ACCESS  read-write
		STATUS  mandatory
		DESCRIPTION ""
		::=  { lapbEntry 17 }

	lapbRetryCount OBJECT-TYPE
		SYNTAX  INTEGER
		ACCESS  read-write
		STATUS  mandatory
		DESCRIPTION ""
		::=  { lapb 3 }

	--  IEEE8023 Group

	ieee8023Number   OBJECT-TYPE
		SYNTAX  INTEGER
		ACCESS  read-only
		STATUS  mandatory
		DESCRIPTION ""
		::= { ieee8023 1 }

	ieee8023Table OBJECT-TYPE
		SYNTAX  SEQUENCE OF Ieee8023Entry
		ACCESS  not-accessible 
		STATUS  mandatory
		DESCRIPTION ""
		::= { ieee8023 2 }

	ieee8023Entry OBJECT-TYPE
		SYNTAX  Ieee8023Entry
		ACCESS  not-accessible  
		STATUS  mandatory
		DESCRIPTION ""
		INDEX	{ ieee8023Index }
		::= { ieee8023Table 1 }

	Ieee8023Entry ::= SEQUENCE {
		ieee8023Index
			INTEGER,
		ieee8023FramesTransmittedOks
			Counter,
		ieee8023SingleCollisionFrames
			Counter,
		ieee8023MultipleCollisionFrames
			Counter,
		ieee8023OctetsTransmittedOks
			Counter,
		ieee8023DeferredTransmissions
			Counter,
		ieee8023MulticastFramesTransmittedOks
			Counter,
		ieee8023BroadcastFramesTransmittedOks
			Counter,
		ieee8023LateCollisions
			Counter,
		ieee8023ExcessiveCollisions
			Counter,
		ieee8023InternalMACTransmitErrors
			Counter,
		ieee8023CarrierSenseErrors
			Counter,
		ieee8023ExcessiveDeferrals
			Counter,
		ieee8023FramesReceivedOks
			Counter,
		ieee8023OctetsReceivedOks
			Counter,
		ieee8023MulticastFramesReceivedOks
			Counter,
		ieee8023BroadcastFramesReceivedOks
			Counter,
		ieee8023FrameTooLongs
			Counter,
		ieee8023AlignmentErrors
			Counter,
		ieee8023FCSErrors
			Counter,
		ieee8023inRangeLengthErrors
			Counter,
		ieee8023outOfRangeLengthFields
			Counter,
		ieee8023InternalMACReceiveErrors
			Counter,
		ieee8023InitializeMAC
			INTEGER,
		ieee8023PromiscuousReceiveStatus
			INTEGER,
		ieee8023MACSubLayerStatus
			INTEGER,
		ieee8023TransmitStatus
			INTEGER,
		ieee8023MulticastReceiveStatus
			INTEGER,
		ieee8023MACAddress
			OCTET STRING,
		ieee8023SQETestErrors
			Counter
		}

	ieee8023Index   OBJECT-TYPE
		SYNTAX  INTEGER
		ACCESS  read-only
		STATUS  mandatory
		DESCRIPTION ""
		::= { ieee8023Entry 1 }
	
	ieee8023FramesTransmittedOks OBJECT-TYPE
		SYNTAX  Counter
		ACCESS  read-only
		STATUS  mandatory
		DESCRIPTION ""
		::= { ieee8023Entry 2 }
	
	ieee8023SingleCollisionFrames OBJECT-TYPE
		SYNTAX  Counter
		ACCESS  read-only
		STATUS  mandatory
		DESCRIPTION ""
		::= { ieee8023Entry 3 }
	
	ieee8023MultipleCollisionFrames OBJECT-TYPE
		SYNTAX  Counter
		ACCESS  read-only
		STATUS  mandatory
		DESCRIPTION ""
		::= { ieee8023Entry 4 }
	
	ieee8023OctetsTransmittedOks OBJECT-TYPE
		SYNTAX  Counter
		ACCESS  read-only
		STATUS  mandatory
		DESCRIPTION ""
		::= { ieee8023Entry 5 }
	
	ieee8023DeferredTransmissions OBJECT-TYPE
		SYNTAX  Counter
		ACCESS  read-only
		STATUS  mandatory
		DESCRIPTION ""
		::= { ieee8023Entry 6 }
	
	ieee8023MulticastFramesTransmittedOks OBJECT-TYPE
		SYNTAX  Counter
		ACCESS  read-only
		STATUS  mandatory
		DESCRIPTION ""
		::= { ieee8023Entry 7 }
	
	ieee8023BroadcastFramesTransmittedOks OBJECT-TYPE
		SYNTAX  Counter
		ACCESS  read-only
		STATUS  mandatory
		DESCRIPTION ""
		::= { ieee8023Entry 8 }
	
	ieee8023LateCollisions OBJECT-TYPE
		SYNTAX  Counter
		ACCESS  read-only
		STATUS  mandatory
		DESCRIPTION ""
		::= { ieee8023Entry 9 }
	
	ieee8023ExcessiveCollisions OBJECT-TYPE
		SYNTAX  Counter
		ACCESS  read-only
		STATUS  mandatory
		DESCRIPTION ""
		::= { ieee8023Entry 10 }
	
	ieee8023InternalMACTransmitErrors OBJECT-TYPE
		SYNTAX  Counter
		ACCESS  read-only
		STATUS  mandatory
		DESCRIPTION ""
		::= { ieee8023Entry 11 }
	
	ieee8023CarrierSenseErrors OBJECT-TYPE
		SYNTAX  Counter
		ACCESS  read-only
		STATUS  mandatory
		DESCRIPTION ""
		::= { ieee8023Entry 12 }
	
	ieee8023ExcessiveDeferrals OBJECT-TYPE
		SYNTAX  Counter
		ACCESS  read-only
		STATUS  mandatory
		DESCRIPTION ""
		::= { ieee8023Entry 13 }
	
	ieee8023FramesReceivedOks OBJECT-TYPE
		SYNTAX  Counter
		ACCESS  read-only
		STATUS  mandatory
		DESCRIPTION ""
		::= { ieee8023Entry 14 }
	
	ieee8023OctetsReceivedOks OBJECT-TYPE
		SYNTAX  Counter
		ACCESS  read-only
		STATUS  mandatory
		DESCRIPTION ""
		::= { ieee8023Entry 15 }
	
	ieee8023MulticastFramesReceivedOks OBJECT-TYPE
		SYNTAX  Counter
		ACCESS  read-only
		STATUS  mandatory
		DESCRIPTION ""
		::= { ieee8023Entry 16 }
	
	ieee8023BroadcastFramesReceivedOks OBJECT-TYPE
		SYNTAX  Counter
		ACCESS  read-only
		STATUS  mandatory
		DESCRIPTION ""
		::= { ieee8023Entry 17 }
	
	ieee8023FrameTooLongs OBJECT-TYPE
		SYNTAX  Counter
		ACCESS  read-only
		STATUS  mandatory
		DESCRIPTION ""
		::= { ieee8023Entry 18 }
	
	ieee8023AlignmentErrors OBJECT-TYPE
		SYNTAX  Counter
		ACCESS  read-only
		STATUS  mandatory
		DESCRIPTION ""
		::= { ieee8023Entry 19 }
	
	ieee8023FCSErrors OBJECT-TYPE
		SYNTAX  Counter
		ACCESS  read-only
		STATUS  mandatory
		DESCRIPTION ""
		::= { ieee8023Entry 20 }
	
	ieee8023inRangeLengthErrors OBJECT-TYPE
		SYNTAX  Counter
		ACCESS  read-only
		STATUS  mandatory
		DESCRIPTION ""
		::= { ieee8023Entry 21 }
	
	ieee8023outOfRangeLengthFields OBJECT-TYPE
		SYNTAX  Counter
		ACCESS  read-only
		STATUS  mandatory
		DESCRIPTION ""
		::= { ieee8023Entry 22 }
	
	ieee8023InternalMACReceiveErrors OBJECT-TYPE
		SYNTAX  Counter
		ACCESS  read-only
		STATUS  mandatory
		DESCRIPTION ""
		::= { ieee8023Entry 23 }
	
	ieee8023InitializeMAC OBJECT-TYPE
		SYNTAX  INTEGER {
			initialize (1)
			}
		ACCESS  read-write
		STATUS  mandatory
		DESCRIPTION ""
		::= { ieee8023Entry 24 }
	
	ieee8023PromiscuousReceiveStatus OBJECT-TYPE
		SYNTAX  INTEGER {
			enabled (1)
			}
		ACCESS  read-write
		STATUS  mandatory
		DESCRIPTION ""
		::= { ieee8023Entry 25 }
	
	ieee8023MACSubLayerStatus OBJECT-TYPE
		SYNTAX  INTEGER {
			enabled (1)
			}
		ACCESS  read-write
		STATUS  mandatory
		DESCRIPTION ""
		::= { ieee8023Entry 26 }
	
	ieee8023TransmitStatus OBJECT-TYPE
		SYNTAX  INTEGER {
			enabled (1),
			disabled (2)
			}
		ACCESS  read-write
		STATUS  mandatory
		DESCRIPTION ""
		::= { ieee8023Entry 27 }
	
	ieee8023MulticastReceiveStatus OBJECT-TYPE
		SYNTAX  INTEGER {
			enabled (1)
			}
		ACCESS  read-write
		STATUS  mandatory
		DESCRIPTION ""
		::= { ieee8023Entry 28 }
	
	ieee8023MACAddress OBJECT-TYPE
		SYNTAX  OCTET STRING (SIZE (6))
		ACCESS  read-only
		STATUS  mandatory
		DESCRIPTION ""
		::= { ieee8023Entry 29 }
	
	ieee8023SQETestErrors OBJECT-TYPE
		SYNTAX  Counter
		ACCESS  read-only
		STATUS  mandatory
		DESCRIPTION ""
		::= { ieee8023Entry 30 }
	
	ieee8023NewMACAddress OBJECT-TYPE
		SYNTAX  SEQUENCE OF Ieee8023NewMACAddressEntry
		ACCESS  not-accessible 
		STATUS  mandatory
		DESCRIPTION ""
		::= { ieee8023 3 }
	
	ieee8023NewMACAddressEntry OBJECT-TYPE
		SYNTAX  Ieee8023NewMACAddressEntry
		ACCESS  not-accessible 
		STATUS  mandatory
		DESCRIPTION ""
		INDEX	{ ieee8023NewMACAddressIndex }
		::= { ieee8023NewMACAddress 1 }

	Ieee8023NewMACAddressEntry ::= SEQUENCE {
		ieee8023NewMACAddressIndex
			INTEGER,
		ieee8023NewMACAddressValue
			OCTET STRING
		}

	ieee8023NewMACAddressIndex OBJECT-TYPE
		SYNTAX  INTEGER
		ACCESS  read-only
		STATUS  mandatory
		DESCRIPTION ""
		::= { ieee8023NewMACAddressEntry 1 }

	ieee8023NewMACAddressValue OBJECT-TYPE
		SYNTAX  OCTET STRING (SIZE (6))
		ACCESS  read-write
		STATUS  mandatory
		DESCRIPTION ""
		::= { ieee8023NewMACAddressEntry 2 }

	--  Physical Serial Group

	phySerIfNumber OBJECT-TYPE
		SYNTAX  INTEGER
		ACCESS  read-only
		STATUS  mandatory
		DESCRIPTION ""
		::=  { phySerIf 1 }

	phySerIfTable OBJECT-TYPE
		SYNTAX  SEQUENCE OF PhySerIfEntry
		ACCESS  not-accessible 
		STATUS  mandatory
		DESCRIPTION ""
		::=  { phySerIf 2 }

	phySerIfEntry OBJECT-TYPE
		SYNTAX  PhySerIfEntry
		ACCESS  not-accessible 
		STATUS  mandatory
		DESCRIPTION ""
		INDEX	{ phySerIfIndex }
		::=  { phySerIfTable 1 }

	PhySerIfEntry ::= SEQUENCE {
		phySerIfIndex
			INTEGER,
		phySerIfInterfaceType
			INTEGER,
		phySerIfMeasuredSpeed
			INTEGER,
		phySerIfIsSpeedsettable
			INTEGER,
		phySerIfPortSpeed
			INTEGER,
		phySerIfTransitDelay
			INTEGER,
		phySerIfT1clockSource
	  		INTEGER,
		phySerIfT1SlotLvalue
			 INTEGER,
		phySerIfT1SlotHvalue
			 INTEGER,
		phySerIfT1dRatePerChan
			 INTEGER,
		phySerIfT1frameAndCode
			 INTEGER,
		phySerIfMeasuredSpeed
			INTEGER,
		phySerIfPartnerAddress
			OCTET STRING
		}


	phySerIfIndex OBJECT-TYPE
		SYNTAX  INTEGER
		ACCESS  read-only
		STATUS  mandatory
		DESCRIPTION ""
		::=  { phySerIfEntry 1 }

	phySerIfInterfaceType OBJECT-TYPE
		SYNTAX  INTEGER {
			x21dte(1),
			x21dce(2),
			rs449(3),
			g703(4),
			v35(5),
			v35btb(6),
			rs232(7),
			t1(8)
			}
		ACCESS  read-write
		STATUS  mandatory
		DESCRIPTION ""
		::=  { phySerIfEntry 2 }

	phySerIfMeasuredSpeed OBJECT-TYPE
		SYNTAX  INTEGER
		ACCESS  read-only
		STATUS  mandatory
		DESCRIPTION ""
		::=  { phySerIfEntry 3 }

	phySerIfIsSpeedsettable OBJECT-TYPE
		SYNTAX  INTEGER (0..1)
		ACCESS  read-only
		STATUS  mandatory
		DESCRIPTION ""
		::=  { phySerIfEntry 4 }

	phySerIfPortSpeed OBJECT-TYPE
		SYNTAX  INTEGER {
			b1200(1200),
			b2400(2400),
			b4800(4800),
			b9600(9600),
			b19200(19200),
			b24000(24000),
			b32000(32000),
			b48000(48000),
			b64000(64000),
			b256000(256000),
			b512000(512000),
			b1024000(1024000),
			b2048000(2048000)
			}
		ACCESS  read-write
		STATUS  mandatory
		DESCRIPTION ""
		::=  { phySerIfEntry 5 }

	phySerIfTransitDelay OBJECT-TYPE
		SYNTAX  INTEGER
		ACCESS  read-only
		STATUS  mandatory
		DESCRIPTION ""
		::=  { phySerIfEntry 6 }

	phySerIfT1clockSource OBJECT-TYPE
		SYNTAX  INTEGER(0..2)
		ACCESS  read-write
		STATUS  mandatory
		DESCRIPTION ""
		::=  { phySerIfEntry 7 }

	phySerIfT1SlotLvalue OBJECT-TYPE
		SYNTAX  INTEGER (1..24)
		ACCESS  read-write
		STATUS  mandatory
		DESCRIPTION ""
		::=  { phySerIfEntry 8 }

	phySerIfT1SlotHvalue OBJECT-TYPE
		SYNTAX  INTEGER (1..24)
		ACCESS  read-write
		STATUS  mandatory
		DESCRIPTION ""
		::=  { phySerIfEntry 9 }

	phySerIfT1dRatePerChan OBJECT-TYPE
		SYNTAX  INTEGER (0..1)
		ACCESS  read-write
		STATUS  mandatory
		DESCRIPTION ""
		::=  { phySerIfEntry 10 }

	phySerIfT1frameAndCode OBJECT-TYPE
		SYNTAX  INTEGER (0..3) 
		ACCESS  read-write
		STATUS  mandatory
		DESCRIPTION ""
		::=  { phySerIfEntry 11 }

	phySerIfPartnerAddress OBJECT-TYPE
		SYNTAX  OCTET STRING (SIZE (0..6))
		ACCESS  read-only
		STATUS  mandatory
		DESCRIPTION ""
		::=  { phySerIfEntry 12 }

	--  Multilink Group

	mlinkNumber OBJECT-TYPE
		SYNTAX  INTEGER
		ACCESS  read-only
		STATUS  mandatory
		DESCRIPTION ""
		::=  { mlink 1 }

	mlinkTable OBJECT-TYPE
		SYNTAX  SEQUENCE OF MlinkEntry
		ACCESS  not-accessible 
		STATUS  mandatory
		DESCRIPTION ""
		::=  { mlink 2 }

	mlinkEntry OBJECT-TYPE
		SYNTAX  MlinkEntry
		ACCESS  not-accessible 
		STATUS  mandatory
		DESCRIPTION ""
		INDEX	{ mlinkIndex }
		::=  { mlinkTable 1 }

	MlinkEntry ::= SEQUENCE {
		mlinkIndex
			INTEGER,
		mlinkState
			INTEGER,
		mlinkSendSeq
			 INTEGER,
		mlinkRcvSeq
			INTEGER,
		mlinkSendUpperEdge
			INTEGER,
		mlinkRcvUpperEdge
			INTEGER,
		mlinkFramesLost
			Counter,
		deletedMlinkFrames
			Counter,
		expressQueueCurrentLength
			INTEGER,
		expressQueueUpperLimit
			INTEGER,
		hiPriQueueCurrentLength
			INTEGER,
		hiPriQueueUpperLimit
			INTEGER,
		loPriQueueCurrentLength
			INTEGER,
		loPriQueueUpperLimit
			INTEGER
		}

	mlinkIndex OBJECT-TYPE
		SYNTAX  INTEGER
		ACCESS  read-only
		STATUS  mandatory
		DESCRIPTION ""
		::=  { mlinkEntry 1 }

	mlinkState OBJECT-TYPE
		SYNTAX  INTEGER (0..3)
		ACCESS  read-only
		STATUS  mandatory
		DESCRIPTION ""
		::=  { mlinkEntry 2 }

	mlinkSendSeq OBJECT-TYPE
		SYNTAX  INTEGER
		ACCESS  read-only
		STATUS  mandatory
		DESCRIPTION ""
		::=  { mlinkEntry 3 }

	mlinkRcvSeq OBJECT-TYPE
		SYNTAX  INTEGER
		ACCESS  read-only
		STATUS  mandatory
		DESCRIPTION ""
		::=  { mlinkEntry 4 }

	mlinkSendUpperEdge OBJECT-TYPE
		SYNTAX  INTEGER
		ACCESS  read-only
		STATUS  mandatory
		DESCRIPTION ""
		::=  { mlinkEntry 5 }

	mlinkRcvUpperEdge OBJECT-TYPE
		SYNTAX  INTEGER
		ACCESS  read-only
		STATUS  mandatory
		DESCRIPTION ""
		::=  { mlinkEntry 6 }

	mlinkFramesLost OBJECT-TYPE
		SYNTAX  Counter
		ACCESS  read-only
		STATUS  mandatory
		DESCRIPTION ""
		::=  { mlinkEntry 7 }

	deletedMlinkFrames OBJECT-TYPE
		SYNTAX  Counter
		ACCESS  read-only
		STATUS  mandatory
		DESCRIPTION ""
		::=  { mlinkEntry 8 }

	expressQueueCurrentLength OBJECT-TYPE
		SYNTAX  INTEGER
		ACCESS  read-only
		STATUS  mandatory
		DESCRIPTION ""
		::=  { mlinkEntry 9 }

	expressQueueUpperLimit OBJECT-TYPE
		SYNTAX  INTEGER
		ACCESS  read-only
		STATUS  mandatory
		DESCRIPTION ""
		::=  { mlinkEntry 10 }

	hiPriQueueCurrentLength OBJECT-TYPE
		SYNTAX  INTEGER
		ACCESS  read-only
		STATUS  mandatory
		DESCRIPTION ""
		::=  { mlinkEntry 11 }

	hiPriQueueUpperLimit OBJECT-TYPE
		SYNTAX  INTEGER
		ACCESS  read-only
		STATUS  mandatory
		DESCRIPTION ""
		::=  { mlinkEntry 12 }

	loPriQueueCurrentLength OBJECT-TYPE
		SYNTAX  INTEGER
		ACCESS  read-only
		STATUS  mandatory
		DESCRIPTION ""
		::=  { mlinkEntry 13 }

	loPriQueueUpperLimit OBJECT-TYPE
		SYNTAX  INTEGER
		ACCESS  read-only
		STATUS  mandatory
		DESCRIPTION ""
		::=  { mlinkEntry 14 }

	mlinkWindow OBJECT-TYPE
		SYNTAX  INTEGER
		ACCESS  read-write
		STATUS  mandatory
		DESCRIPTION ""
		::=  { mlink 3 }

	mlinkRxTimeout OBJECT-TYPE
		SYNTAX  INTEGER
		ACCESS  read-write
		STATUS  mandatory
		DESCRIPTION ""
		::=  { mlink 4 }



	--  LAN Group

	lanInterfaceType OBJECT-TYPE
		SYNTAX  INTEGER (1..3)
		ACCESS  read-only
		STATUS  mandatory
		DESCRIPTION ""
		::=  { lan 1 }


	--  Bridge Group

	portNumber OBJECT-TYPE
		SYNTAX  INTEGER
		ACCESS  read-only
		STATUS  mandatory
		DESCRIPTION ""
		::=  { bridge 1 }

	bridgeStatsTable OBJECT-TYPE
		SYNTAX  SEQUENCE OF BridgeStatsEntry
		ACCESS  not-accessible 
		STATUS  mandatory
		DESCRIPTION ""
		::=  { bridge 2 }

	bridgeStatsEntry OBJECT-TYPE
		SYNTAX  BridgeStatsEntry
		ACCESS  not-accessible 
		STATUS  mandatory
		DESCRIPTION ""
		INDEX	{ bridgeStatsIndex }
		::=  { bridgeStatsTable 1 }

	BridgeStatsEntry ::= SEQUENCE {
		bridgeStatsIndex
			INTEGER,
		averageForwarded
			Counter,
		maxForwarded
			Counter,
		averageRejected
			Counter,
		maxRejected
			Counter,
		lanAccepts
			Counter,
		lanRejects
			Counter,
		deletedLanFrames
			Counter
		}

	bridgeStatsIndex OBJECT-TYPE
		SYNTAX  INTEGER
		ACCESS  read-only
		STATUS  mandatory
		DESCRIPTION ""
		::=  { bridgeStatsEntry 1 }

	averageForwarded OBJECT-TYPE
		SYNTAX  Counter
		ACCESS  read-only
		STATUS  mandatory
		DESCRIPTION ""
		::=  { bridgeStatsEntry 2 }

	maxForwarded OBJECT-TYPE
		SYNTAX Counter
		ACCESS  read-only
		STATUS  mandatory
		DESCRIPTION ""
		::=  { bridgeStatsEntry 3 }

	averageRejected OBJECT-TYPE
		SYNTAX  Counter
		ACCESS  read-only
		STATUS  mandatory
		DESCRIPTION ""
		::=  { bridgeStatsEntry 4 }

	maxRejected OBJECT-TYPE
		SYNTAX Counter
		ACCESS  read-only
		STATUS  mandatory
		DESCRIPTION ""
		::=  { bridgeStatsEntry 5 }

	lanAccepts OBJECT-TYPE
		SYNTAX Counter
		ACCESS  read-only
		STATUS  mandatory
		DESCRIPTION ""
		::=  { bridgeStatsEntry 6 }

	lanRejects OBJECT-TYPE
		SYNTAX Counter
		ACCESS  read-only
		STATUS  mandatory
		DESCRIPTION ""
		::=  { bridgeStatsEntry 7 }

	deletedLanFrames OBJECT-TYPE
		SYNTAX Counter
		ACCESS  read-only
		STATUS  mandatory
		DESCRIPTION ""
		::=  { bridgeStatsEntry 8 }

	stpTable OBJECT-TYPE
		SYNTAX  SEQUENCE OF StpEntry
		ACCESS  not-accessible 
		STATUS  mandatory
		DESCRIPTION ""
		::=  { bridge 3 }

	stpEntry OBJECT-TYPE
		SYNTAX  StpEntry
		ACCESS  not-accessible 
		STATUS  mandatory
		DESCRIPTION ""
		INDEX	{ stpIndex }
		::=  { stpTable 1 }

	StpEntry ::= SEQUENCE {
		stpIndex
			INTEGER,
		portSpatState
			INTEGER,
		pathCostMode
			INTEGER,
		pathCostAutoValue
			INTEGER,
		pathCostManualValue
			INTEGER,
		portPriorityMode
			INTEGER,
		portPriorityAutoValue
			INTEGER,
		portPriorityManualValue
			INTEGER
		}


	stpIndex OBJECT-TYPE
		SYNTAX  INTEGER
		ACCESS  read-only
		STATUS  mandatory
		DESCRIPTION ""
		::=  { stpEntry 1 }

	pathCostMode OBJECT-TYPE
		SYNTAX INTEGER(0..1)
		ACCESS  read-write
		STATUS  mandatory
		DESCRIPTION ""
		::=  { stpEntry 2 }

	pathCostAutoValue OBJECT-TYPE
		SYNTAX INTEGER
		ACCESS  read-only
		STATUS  mandatory
		DESCRIPTION ""
		::=  { stpEntry 3 }

	pathCostManualValue OBJECT-TYPE
		SYNTAX INTEGER(0..65535)
		ACCESS  read-write
		STATUS  mandatory
		DESCRIPTION ""
		::=  { stpEntry 4 }

	portSpatState OBJECT-TYPE
		SYNTAX INTEGER
		ACCESS  read-only
		STATUS  mandatory
		DESCRIPTION ""
		::=  { stpEntry 5 }

	portPriorityMode OBJECT-TYPE
		SYNTAX INTEGER(0..1)
		ACCESS  read-write
		STATUS  mandatory
		DESCRIPTION ""
		::=  { stpEntry 6 }

	portPriorityAutoValue OBJECT-TYPE
		SYNTAX INTEGER
		ACCESS  read-only
		STATUS  mandatory
		DESCRIPTION ""
		::=  { stpEntry 7 }

	portPriorityManualValue OBJECT-TYPE
		SYNTAX INTEGER(0..255)
		ACCESS  read-write
		STATUS  mandatory
		DESCRIPTION ""
		::=  { stpEntry 8 }

	spanningTree OBJECT-TYPE
		SYNTAX INTEGER (0..1)
		ACCESS read-write
		STATUS mandatory
		DESCRIPTION ""
		::=  { bridge 4 }

	spatPriority OBJECT-TYPE
		SYNTAX INTEGER (1..65535)
		ACCESS read-write
		STATUS mandatory
		DESCRIPTION ""
		::=  { bridge 5 }

	spatHelloTimer OBJECT-TYPE
		SYNTAX INTEGER (1..10)
		ACCESS read-write
		STATUS mandatory
		DESCRIPTION ""
		::=  { bridge 6 }

	spatResetTimer OBJECT-TYPE
		SYNTAX INTEGER (1..1800)
		ACCESS read-write
		STATUS mandatory
		DESCRIPTION ""
		::=  { bridge 7 }

	spatVersion OBJECT-TYPE
		SYNTAX INTEGER {
				  revisionC(3),
				  revision8(8)
				  }
		ACCESS read-write
		STATUS mandatory
		DESCRIPTION ""
		::=  { bridge 8 }

	spanningMcastAddr OBJECT-TYPE
		SYNTAX OCTET STRING ( SIZE (6))
		ACCESS read-write
		STATUS mandatory
		DESCRIPTION ""
		::=  { bridge 9 }

	operatingMode OBJECT-TYPE
		SYNTAX  INTEGER (0..1)
		ACCESS  read-write
		STATUS  mandatory
		DESCRIPTION ""
		::=  { bridge 10 }

	preconfSourceFilter OBJECT-TYPE
		SYNTAX  INTEGER (0..1)
		ACCESS  read-write
		STATUS  mandatory
		DESCRIPTION ""
		::=  { bridge 11 }

	typeFilter OBJECT-TYPE
		SYNTAX  INTEGER (0..1)
		ACCESS  read-write
		STATUS  mandatory
		DESCRIPTION ""
		::=  { bridge 12 }

	typePrioritisation OBJECT-TYPE
		SYNTAX  INTEGER (0..1)
		ACCESS  read-write
		STATUS  mandatory
		DESCRIPTION ""
		::=  { bridge 13 }

	dynamicLearningInLM OBJECT-TYPE
		SYNTAX  INTEGER (0..1)
		ACCESS  read-write
		STATUS  mandatory
		DESCRIPTION ""
		::=  { bridge 14 }

	forgetAddressTimer OBJECT-TYPE
		SYNTAX  INTEGER (24..1000)
		ACCESS  read-write
		STATUS  mandatory
		DESCRIPTION ""
		::=  { bridge 15 }

	deleteAddressTimer OBJECT-TYPE
		SYNTAX  INTEGER (1..20000)
		ACCESS  read-write
		STATUS  mandatory
		DESCRIPTION ""
		::=  { bridge 16 }

	multicastDisposition OBJECT-TYPE
		SYNTAX  INTEGER (0..1)
		ACCESS  read-write
		STATUS  mandatory
		DESCRIPTION ""
		::=  { bridge 17 }

	filterMatches OBJECT-TYPE
		SYNTAX  INTEGER (0..1)
		ACCESS  read-write
		STATUS  mandatory
		DESCRIPTION ""
		::=  { bridge 18 }

	ieeeFormatFilter OBJECT-TYPE
		SYNTAX  INTEGER (0..1)
		ACCESS  read-write
		STATUS  mandatory
		DESCRIPTION ""
		::=  { bridge 19 }

	priorityMatches OBJECT-TYPE
		SYNTAX  INTEGER (0..1)
		ACCESS  read-write
		STATUS  mandatory
		DESCRIPTION ""
		::=  { bridge 20 }

	ieeeFormatPriority OBJECT-TYPE
		SYNTAX  INTEGER (0..1)
		ACCESS  read-write
		STATUS  mandatory
		DESCRIPTION ""
		::=  { bridge 21 }

	averagePeriod OBJECT-TYPE
		SYNTAX  INTEGER
		ACCESS  read-only
		STATUS  mandatory
		DESCRIPTION ""
		::=  { bridge 22 }

	triangulation OBJECT-TYPE
		SYNTAX  INTEGER(0..1)
		ACCESS  read-write
		STATUS  mandatory
		DESCRIPTION ""
		::=  { bridge 23 }

	adaptiveRouting OBJECT-TYPE
		SYNTAX  INTEGER (0..1)
		ACCESS  read-write
		STATUS  mandatory
		DESCRIPTION ""
		::=  { bridge 24 }

	adaptiveMcastAddr OBJECT-TYPE
		SYNTAX  OCTET STRING ( SIZE (6))
		ACCESS  read-write
		STATUS  mandatory
		DESCRIPTION ""
		::=  { bridge 25 }

	arAddressInfo OBJECT IDENTIFIER ::= { bridge 26 }

	standbyRemote OBJECT-TYPE
		SYNTAX INTEGER
		ACCESS read-only
		STATUS mandatory
		DESCRIPTION ""
		::=  { arAddressInfo 1 }

	standbyLocal OBJECT-TYPE
		SYNTAX INTEGER
		ACCESS read-only
		STATUS mandatory
		DESCRIPTION ""
		::=  { arAddressInfo 2 }

	activeRemote OBJECT-TYPE
		SYNTAX INTEGER
		ACCESS read-only
		STATUS mandatory
		DESCRIPTION ""
		::=  { arAddressInfo 3 }

	activeLocal OBJECT-TYPE
		SYNTAX INTEGER
		ACCESS read-only
		STATUS mandatory
		DESCRIPTION ""
		::=  { arAddressInfo 4 }

	maxSerialLoading OBJECT-TYPE
		SYNTAX INTEGER
		ACCESS read-write
		STATUS mandatory
		DESCRIPTION ""
		::=	{ bridge 27 }
			
	serialLoadPeriod OBJECT-TYPE
		SYNTAX INTEGER
		ACCESS read-write
		STATUS mandatory
		DESCRIPTION ""
		::=	{ bridge 28 }

	serialLoading OBJECT-TYPE
		SYNTAX  INTEGER
		ACCESS  read-only
		STATUS  mandatory
		DESCRIPTION ""
		::=  { bridge 29 }

	filteringDataBaseTable OBJECT IDENTIFIER ::= { bridge 30 }

	filteringDbTable OBJECT-TYPE
		SYNTAX SEQUENCE OF FilteringDbEntry
		ACCESS not-accessible 
		STATUS mandatory
		DESCRIPTION ""
		::=  { filteringDataBaseTable 1 }

	filteringDbEntry OBJECT-TYPE
		SYNTAX FilteringDbEntry
		ACCESS not-accessible 
		STATUS mandatory
		DESCRIPTION ""
		INDEX	{ filteringDbMacAddress }
		::=  { filteringDbTable 1 }

	FilteringDbEntry ::= SEQUENCE {
		filteringDbMacAddress
			OCTET STRING,
		filteringDbDisposition
			INTEGER,
		filteringDbStatus
			INTEGER,
		filteringDbType
			INTEGER
		}

	filteringDbMacAddress OBJECT-TYPE
		SYNTAX OCTET STRING (SIZE(6))
		ACCESS read-write
		STATUS mandatory
		DESCRIPTION ""
		::=  { filteringDbEntry 1 }

	filteringDbDisposition OBJECT-TYPE
		SYNTAX INTEGER
		ACCESS read-write
		STATUS mandatory
		DESCRIPTION ""
		::=  { filteringDbEntry 2 }

	filteringDbStatus OBJECT-TYPE
		SYNTAX INTEGER
		ACCESS read-write
		STATUS mandatory
		DESCRIPTION ""
		::=  { filteringDbEntry 3 }

	filteringDbType OBJECT-TYPE
		SYNTAX INTEGER
		ACCESS read-write
		STATUS mandatory
		DESCRIPTION ""
		::=  { filteringDbEntry 4 }

	filteringDbAction OBJECT-TYPE
		SYNTAX INTEGER
		ACCESS read-write
		STATUS mandatory
		DESCRIPTION ""
		::=  {filteringDataBaseTable 2 }


	priorityTable    OBJECT IDENTIFIER ::= { bridge 31 }

	prioritySubTable OBJECT-TYPE
		SYNTAX SEQUENCE OF PriorityTableEntry
		ACCESS not-accessible 
		STATUS mandatory
		DESCRIPTION ""
		::=  { priorityTable 1 }

	priorityTableEntry OBJECT-TYPE
		SYNTAX PriorityTableEntry
		ACCESS not-accessible 
		STATUS mandatory
		DESCRIPTION ""
		INDEX { priorityTableEntryValue }
		::=  { prioritySubTable 1 }

	PriorityTableEntry ::= SEQUENCE {
		priorityTableEntryValue
			INTEGER,
		priorityTableEntryType
			INTEGER
		}

	priorityTableEntryValue OBJECT-TYPE
		SYNTAX INTEGER
		ACCESS read-write
		STATUS mandatory
		DESCRIPTION ""
		::=  { priorityTableEntry 1 }

	priorityTableEntryType OBJECT-TYPE
		SYNTAX INTEGER
		ACCESS read-write
		STATUS mandatory
		DESCRIPTION ""
		::=  { priorityTableEntry 2 }

	priorityTableAction OBJECT-TYPE
		SYNTAX INTEGER
		ACCESS read-write
		STATUS mandatory
		DESCRIPTION ""
		::=  { priorityTable 2 }

	priorityPage OBJECT-TYPE
		SYNTAX OCTET STRING (SIZE(8))
		ACCESS read-write
		STATUS mandatory
		DESCRIPTION ""
		::=  { priorityTable 3 }

	filterTable      OBJECT IDENTIFIER ::= { bridge 32 }

	filterSubTable OBJECT-TYPE
		SYNTAX SEQUENCE OF FilterTableEntry
		ACCESS not-accessible 
		STATUS mandatory
		DESCRIPTION ""
		::=  { filterTable 1 }

	filterTableEntry OBJECT-TYPE
		SYNTAX FilterTableEntry
		ACCESS not-accessible 
		STATUS mandatory
		DESCRIPTION ""
		INDEX { filterTableEntryValue }
		::=  { filterSubTable 1 }

	FilterTableEntry ::= SEQUENCE {
		filterTableEntryValue
			INTEGER,
		filterTableEntryType
			INTEGER
		}

	filterTableEntryValue OBJECT-TYPE
		SYNTAX INTEGER
		ACCESS read-write
		STATUS mandatory
		DESCRIPTION ""
		::=  { filterTableEntry 1 }

	filterTableEntryType OBJECT-TYPE
		SYNTAX INTEGER
		ACCESS read-write
		STATUS mandatory
		DESCRIPTION ""
		::=  { filterTableEntry 2 }

	filterTableAction OBJECT-TYPE
		SYNTAX INTEGER
		ACCESS read-write
		STATUS mandatory
		DESCRIPTION ""
		::=  { filterTable 2 }

	filterPage OBJECT-TYPE
		SYNTAX OCTET STRING (SIZE(8))
		ACCESS read-write
		STATUS mandatory
		DESCRIPTION ""
		::=  { filterTable 3 }


	--  Router group

	ipRSTable OBJECT-TYPE
		SYNTAX  SEQUENCE OF IpRSEntry
		ACCESS  not-accessible 
		STATUS  mandatory
		DESCRIPTION ""
		::=  { router 1 }

	ipRSEntry OBJECT-TYPE
		SYNTAX  IpRSEntry
		ACCESS  not-accessible 
		STATUS  mandatory
		DESCRIPTION ""
		INDEX 	{ ipRSIndex	}
		::=  { ipRSTable 1 }


	IpRSEntry ::= SEQUENCE {
		ipRSIndex
			INTEGER,
		gwProtocol
			INTEGER,
		ifStatus
			INTEGER,
		receivedTotal
			Counter,
		transmittedTotal
			Counter,
		outDiscardsTotal
			Counter,
		noRouteTotal
			Counter
		}


	ipRSIndex OBJECT-TYPE
		SYNTAX  INTEGER
		ACCESS  read-only
		STATUS  mandatory
		DESCRIPTION ""
		::=  { ipRSEntry 1 }

	gwProtocol OBJECT-TYPE
		SYNTAX  INTEGER
		ACCESS  read-write
		STATUS  mandatory
		DESCRIPTION ""
		::=  { ipRSEntry 2 }

	ifStatus OBJECT-TYPE
		SYNTAX  INTEGER
		ACCESS  read-only
		STATUS  mandatory
		DESCRIPTION ""
		::=  { ipRSEntry 3 }

	receivedTotal OBJECT-TYPE
		SYNTAX  Counter
		ACCESS  read-only
		STATUS  mandatory
		DESCRIPTION ""
		::=  { ipRSEntry 4 }

	transmittedTotal OBJECT-TYPE
		SYNTAX  Counter
		ACCESS  read-only
		STATUS  mandatory
		DESCRIPTION ""
		::=  { ipRSEntry 5 }

	outDiscardsTotal OBJECT-TYPE
		SYNTAX  Counter
		ACCESS  read-only
		STATUS  mandatory
		DESCRIPTION ""
		::=  { ipRSEntry 6 }

	noRouteTotal OBJECT-TYPE
		SYNTAX  Counter
		ACCESS  read-only
		STATUS  mandatory
		DESCRIPTION ""
		::=  { ipRSEntry 7 }


	icmpRSTable OBJECT IDENTIFIER ::= { router 2 }

	destUnreachLastRx OBJECT-TYPE
		SYNTAX  OCTET STRING (SIZE(13))
		ACCESS  read-only
		STATUS  mandatory
		DESCRIPTION ""
		::=  { icmpRSTable 1 }

	destUnreachLastTx OBJECT-TYPE
		SYNTAX  OCTET STRING (SIZE(13))
		ACCESS  read-only
		STATUS  mandatory
		DESCRIPTION ""
		::=  { icmpRSTable 2 }

	sourceQuenchLastRx OBJECT-TYPE
		SYNTAX  OCTET STRING (SIZE(13))
		ACCESS  read-only
		STATUS  mandatory
		DESCRIPTION ""
		::=  { icmpRSTable 3 }

	sourceQuenchLastTx OBJECT-TYPE
		SYNTAX  OCTET STRING (SIZE(13))
		ACCESS  read-only
		STATUS  mandatory
		DESCRIPTION ""
		::=  { icmpRSTable 4 }

	redirectsLastRx OBJECT-TYPE
		SYNTAX  OCTET STRING (SIZE(13))
		ACCESS  read-only
		STATUS  mandatory
		DESCRIPTION ""
		::=  { icmpRSTable 5 }

	redirectsLastTx OBJECT-TYPE
		SYNTAX  OCTET STRING (SIZE(13))
		ACCESS  read-only
		STATUS  mandatory
		DESCRIPTION ""
		::=  { icmpRSTable 6 }

	echoRequestsLastRx OBJECT-TYPE
		SYNTAX  OCTET STRING (SIZE(13))
		ACCESS  read-only
		STATUS  mandatory
		DESCRIPTION ""
		::=  { icmpRSTable 7 }

	echoRequestsLastTx OBJECT-TYPE
		SYNTAX  OCTET STRING (SIZE(13))
		ACCESS  read-only
		STATUS  mandatory
		DESCRIPTION ""
		::=  { icmpRSTable 8 }

	timeExceededLastRx OBJECT-TYPE
		SYNTAX  OCTET STRING (SIZE(13))
		ACCESS  read-only
		STATUS  mandatory
		DESCRIPTION ""
		::=  { icmpRSTable 9 }

	timeExceededLastTx OBJECT-TYPE
		SYNTAX  OCTET STRING (SIZE(13))
		ACCESS  read-only
		STATUS  mandatory
		DESCRIPTION ""
		::=  { icmpRSTable 10 }

	paramProbLastRx OBJECT-TYPE
		SYNTAX  OCTET STRING (SIZE(13))
		ACCESS  read-only
		STATUS  mandatory
		DESCRIPTION ""
		::=  { icmpRSTable 11 }

	paramProbLastTx OBJECT-TYPE
		SYNTAX  OCTET STRING (SIZE(13))
		ACCESS  read-only
		STATUS  mandatory
		DESCRIPTION ""
		::=  { icmpRSTable 12 }

	ipRouting OBJECT-TYPE
		SYNTAX  INTEGER
		ACCESS  read-write
		STATUS  mandatory
		DESCRIPTION ""
		::=  { router 3 }

	--	Boot group

	bootpRetryCount  OBJECT-TYPE
		SYNTAX  INTEGER (0..65535)
		ACCESS  read-write
		STATUS  mandatory
		DESCRIPTION ""
		::= { boot 1 }

	downloadRetryCount  OBJECT-TYPE
		SYNTAX  INTEGER (0..65535)
		ACCESS  read-write
		STATUS  mandatory
		DESCRIPTION ""
		::= { boot 2 }

	downloadFilename  OBJECT-TYPE
		SYNTAX  OCTET STRING (SIZE( 0..128))
		ACCESS  read-write
		STATUS  mandatory
		DESCRIPTION ""
		::= { boot 3 }

	bootserverIpAddress  OBJECT-TYPE
		SYNTAX  IpAddress
		ACCESS  read-write
		STATUS  mandatory
		DESCRIPTION ""
		::= { boot 4 }

	loadserverIpAddress  OBJECT-TYPE
		SYNTAX  IpAddress
		ACCESS  read-write
		STATUS  mandatory
		DESCRIPTION ""
		::= { boot 5 }

	uniqueBroadcastAddress  OBJECT-TYPE
		SYNTAX  IpAddress
		ACCESS  read-write
		STATUS  mandatory
		DESCRIPTION ""
		::= { boot 6 }

	tftpRetryCount  OBJECT-TYPE
		SYNTAX  INTEGER (0..65535)
		ACCESS  read-write
		STATUS  mandatory
		DESCRIPTION ""
		::= { boot 7 }

	tftpRetryPeriod  OBJECT-TYPE
		SYNTAX  INTEGER (0..65535)
		ACCESS  read-write
		STATUS  mandatory
		DESCRIPTION ""
		::= { boot 8 }

	initiateBootpDll  OBJECT-TYPE
		SYNTAX  INTEGER
		ACCESS  read-write
		STATUS  mandatory
		DESCRIPTION ""
		::= { boot 9 }


	--	Boothelper group

	boothelperEnabled  OBJECT-TYPE
		SYNTAX  INTEGER
		ACCESS  read-write
		STATUS  mandatory
		DESCRIPTION ""
		::= { boothelper 1 }

	boothelperHopsLimit  OBJECT-TYPE
		SYNTAX  INTEGER (0..255)
		ACCESS  read-write
		STATUS  mandatory
		DESCRIPTION ""
		::= { boothelper 2 }

	boothelperForwardingAddress  OBJECT-TYPE
		SYNTAX  IpAddress
		ACCESS  read-write
		STATUS  mandatory
		DESCRIPTION ""
		::= { boothelper 3 }


--	IPX Group

	ipxRouting OBJECT-TYPE
		SYNTAX  INTEGER (0..1)
		ACCESS  read-write
		STATUS  mandatory
		DESCRIPTION ""
		::= { ipx 1 }

	ipxIfNumber OBJECT-TYPE
		SYNTAX  INTEGER
		ACCESS  read-only
		STATUS  mandatory
		DESCRIPTION ""
		::= { ipx 2 }

	ipxIfTable OBJECT-TYPE
		SYNTAX  SEQUENCE OF IpxIfEntry
		ACCESS  not-accessible
		STATUS  mandatory
		DESCRIPTION ""
		::= { ipx 3 }

	ipxIfEntry OBJECT-TYPE
		SYNTAX  IpxIfEntry
		ACCESS  not-accessible
		STATUS  mandatory
		DESCRIPTION ""
		INDEX	{ ipxIfIndex } 
		::= { ipxIfTable 1 }

	IpxIfEntry ::= SEQUENCE {
		ipxIfIndex
			INTEGER,
		ipxIfNwkNumber
			OCTET STRING,
		ipxIfIPXAddress
			OCTET STRING,
		ipxIfEncapsulation
			INTEGER,
		ipxIfDelay
			INTEGER
	}

	ipxIfIndex OBJECT-TYPE
		SYNTAX  INTEGER
		ACCESS  read-only
		STATUS  mandatory
		DESCRIPTION ""
		::= { ipxIfEntry 1 }

	ipxIfNwkNumber OBJECT-TYPE
		SYNTAX  OCTET STRING(SIZE(8))
		ACCESS  read-write
		STATUS  mandatory
		DESCRIPTION ""
		::= { ipxIfEntry 2 }

	ipxIfIPXAddress OBJECT-TYPE
		SYNTAX  OCTET STRING(SIZE(26))
		ACCESS  read-only
		STATUS  mandatory
		DESCRIPTION ""
		::= { ipxIfEntry 3 }

	ipxIfEncapsulation OBJECT-TYPE
		SYNTAX  INTEGER(0..6)
		ACCESS  read-write
		STATUS  mandatory
		DESCRIPTION ""
		::= { ipxIfEntry 4 }

	ipxIfDelay OBJECT-TYPE
		SYNTAX  INTEGER
		ACCESS  read-write
		STATUS  mandatory
		DESCRIPTION ""
		::= { ipxIfEntry 5 }

	ipxRoutingTable OBJECT-TYPE
		SYNTAX  SEQUENCE OF IpxRITEntry
		ACCESS  not-accessible
		STATUS  mandatory
		DESCRIPTION ""
		::=  { ipx 4 }

	ipxRITEntry OBJECT-TYPE
		SYNTAX  IpxRITEntry
		ACCESS  not-accessible
		STATUS  mandatory
		DESCRIPTION ""
		INDEX	{ ipxRITDestNwkNumber }
		::=  { ipxRoutingTable 1 }

	IpxRITEntry ::= SEQUENCE {
		ipxRITDestNwkNumber
			OCTET STRING,
		ipxRITGwyHostAddress
			OCTET STRING,
		ipxRITHopCount
			INTEGER,
		ipxRITDelay
			INTEGER,
		ipxRITInterface
			INTEGER,
		ipxRITDirectConnect
			INTEGER
	}

	ipxRITDestNwkNumber OBJECT-TYPE
		SYNTAX  OCTET STRING
		ACCESS  read-only
		STATUS  mandatory
		DESCRIPTION ""
		::= { ipxRITEntry 1 }

	ipxRITGwyHostAddress OBJECT-TYPE
		SYNTAX  OCTET STRING(SIZE(10))
		ACCESS  read-only
		STATUS  mandatory
		DESCRIPTION ""
		::= { ipxRITEntry 2 }

	ipxRITHopCount OBJECT-TYPE
		SYNTAX  INTEGER
		ACCESS  read-only
		STATUS  mandatory
		DESCRIPTION ""
		::= { ipxRITEntry 3 }

	ipxRITDelay OBJECT-TYPE
		SYNTAX  INTEGER
		ACCESS  read-only
		STATUS  mandatory
		DESCRIPTION ""
		::= { ipxRITEntry 4 }

	ipxRITInterface OBJECT-TYPE
		SYNTAX  INTEGER
		ACCESS  read-only
		STATUS  mandatory
		DESCRIPTION ""
		::= { ipxRITEntry 5 }

	ipxRITDirectConnect OBJECT-TYPE
		SYNTAX  INTEGER
		ACCESS  read-only
		STATUS  mandatory
		DESCRIPTION ""
		::= { ipxRITEntry 6 }

	ipxSAPBinderyTable OBJECT-TYPE
		SYNTAX  SEQUENCE OF IpxSAPBinderyEntry
		ACCESS  not-accessible
		STATUS  mandatory
		DESCRIPTION ""
		::= { ipx 5 }

	ipxSAPBinderyEntry OBJECT-TYPE
		SYNTAX  IpxSAPBinderyEntry 
		ACCESS  not-accessible
		STATUS  mandatory
		DESCRIPTION ""
		INDEX	{ ipxSAPBinderyType, ipxSAPBinderyServerIPXAddress }
		::= { ipxSAPBinderyTable 1 }
	
	IpxSAPBinderyEntry ::= SEQUENCE {
		ipxSAPBinderyType
			INTEGER,
		ipxSAPBinderyServerIPXAddress
			OCTET STRING,
		ipxSAPBinderyServerName
			OCTET STRING,
		ipxSAPBinderyHopCount
			INTEGER,
		ipxSAPBinderySocket
			INTEGER
	}

	ipxSAPBinderyType OBJECT-TYPE
		SYNTAX  INTEGER
		ACCESS  read-only
		STATUS  mandatory
		DESCRIPTION ""
		::= { ipxSAPBinderyEntry 1 }

	ipxSAPBinderyServerIPXAddress OBJECT-TYPE
		SYNTAX  OCTET STRING(SIZE(26))
		ACCESS  read-only
		STATUS  mandatory
		DESCRIPTION ""
		::= { ipxSAPBinderyEntry 2 }

	ipxSAPBinderyServerName OBJECT-TYPE
		SYNTAX  OCTET STRING(SIZE(0..48))
		ACCESS  read-only
		STATUS  mandatory
		DESCRIPTION ""
		::= { ipxSAPBinderyEntry 3 }

	ipxSAPBinderyHopCount OBJECT-TYPE
		SYNTAX  INTEGER
		ACCESS  read-only
		STATUS  mandatory
		DESCRIPTION ""
		::= { ipxSAPBinderyEntry 4 }

	ipxSAPBinderySocket OBJECT-TYPE
		SYNTAX  INTEGER
		ACCESS  read-only
		STATUS  mandatory
		DESCRIPTION ""
		::= { ipxSAPBinderyEntry 5 }

	ipxDgmsReceived OBJECT-TYPE
		SYNTAX  Counter
		ACCESS  read-only
		STATUS  mandatory
		DESCRIPTION ""
		::= { ipx 6 }

	ipxDgmsTransmitted OBJECT-TYPE
		SYNTAX  Counter
		ACCESS  read-only
		STATUS  mandatory
		DESCRIPTION ""
		::= { ipx 7 } 

	ipxDgmsRxNotRouted OBJECT-TYPE
		SYNTAX  Counter
		ACCESS  read-only
		STATUS  mandatory
		DESCRIPTION ""
		::= { ipx 8 }

	ipxDgmsForwarded OBJECT-TYPE
		SYNTAX  Counter
		ACCESS  read-only
		STATUS  mandatory
		DESCRIPTION ""
		::= { ipx 9 }

	ipxInDelivers OBJECT-TYPE
		SYNTAX  Counter
		ACCESS  read-only
		STATUS  mandatory
		DESCRIPTION ""
		::= { ipx 10 } 

	ipxInHdrErrors OBJECT-TYPE
		SYNTAX  Counter
		ACCESS  read-only
		STATUS  mandatory
		DESCRIPTION ""
		::= { ipx 11 }

	ipxAccessViolation OBJECT-TYPE
		SYNTAX  Counter
		ACCESS  read-only
		STATUS  mandatory
		DESCRIPTION ""
		::= { ipx 12 }

	ipxInDiscards OBJECT-TYPE
		SYNTAX  Counter
		ACCESS  read-only
		STATUS  mandatory
		DESCRIPTION ""
		::= { ipx 13 }

	ipxOutDiscards OBJECT-TYPE
		SYNTAX  Counter
		ACCESS  read-only
		STATUS  mandatory
		DESCRIPTION ""
		::= { ipx 14 }

	ipxOtherDiscards OBJECT-TYPE
		SYNTAX  Counter
		ACCESS  read-only
		STATUS  mandatory
		DESCRIPTION ""
		::= { ipx 15 }

-- The Decnet Group

	dcntRouting OBJECT-TYPE
		SYNTAX  INTEGER (0..1)
		ACCESS  read-write
		STATUS  mandatory
		DESCRIPTION ""
		::= { decnet 1 }

	dcntIfNumber OBJECT-TYPE
		SYNTAX  INTEGER
		ACCESS  read-only
		STATUS  mandatory
		DESCRIPTION ""
		::= { decnet 2 }


	dcntIfTable OBJECT-TYPE
		SYNTAX  SEQUENCE OF DcntIfTableEntry
		ACCESS  not-accessible
		STATUS  mandatory
		DESCRIPTION ""
		::= { decnet 3 }

	dcntIfTableEntry OBJECT-TYPE
		SYNTAX  DcntIfTableEntry
		ACCESS  not-accessible
		STATUS  mandatory
		DESCRIPTION ""
		INDEX	{ dcntIfIndex }
		::= { dcntIfTable 1 }

	DcntIfTableEntry ::= SEQUENCE {
		dcntIfIndex
			INTEGER,
		dcntIfCost
			INTEGER (0..1023),
		dcntIfRtrPriority
			INTEGER (0..127),
		dcntIfDesgntdRtr
			INTEGER (0..1),
		dcntIfHelloTimerBCT3
			INTEGER
		}

	dcntIfIndex OBJECT-TYPE
		SYNTAX  INTEGER
		ACCESS  read-only
		STATUS  mandatory
		DESCRIPTION ""
		::= { dcntIfTableEntry 1 }

	dcntIfCost OBJECT-TYPE
		SYNTAX  INTEGER (0..1023)
		ACCESS  read-write
		STATUS  mandatory
		DESCRIPTION ""
		::= { dcntIfTableEntry 2 }

	dcntIfRtrPriority OBJECT-TYPE
		SYNTAX  INTEGER (0..127)
		ACCESS  read-write
		STATUS  mandatory
		DESCRIPTION ""
		::= { dcntIfTableEntry 3 }

	dcntIfDesgntdRtr OBJECT-TYPE
		SYNTAX  INTEGER
		ACCESS  read-only
		STATUS  mandatory
		DESCRIPTION ""
		::= { dcntIfTableEntry 4 }

	dcntIfHelloTimerBCT3 OBJECT-TYPE
		SYNTAX  INTEGER ( 1..8191 )
		ACCESS  read-write
		STATUS  mandatory
		DESCRIPTION ""
		::= { dcntIfTableEntry 5 }

-- DecNet Routing Information Table

	dcntRoutingTable OBJECT-TYPE
		SYNTAX  SEQUENCE OF DcntRITEntry
		ACCESS  not-accessible
		STATUS  mandatory
		DESCRIPTION ""
		::= { decnet 4 }

 	dcntRITEntry OBJECT-TYPE
		SYNTAX  DcntRITEntry
		ACCESS  not-accessible
		STATUS  mandatory
		DESCRIPTION ""
		INDEX	{ dcntRITDestNode }
		::= { dcntRoutingTable 1 }
 
	DcntRITEntry ::= SEQUENCE {
		dcntRITDestNode
			INTEGER,
		dcntRITNextHop
			OCTET STRING,
		dcntRITCost
			INTEGER,
		dcntRITHops
			INTEGER,
		dcntRITInterface
			INTEGER
		}

	 dcntRITDestNode OBJECT-TYPE
		SYNTAX  INTEGER
		ACCESS  read-only
		STATUS  mandatory
		DESCRIPTION ""
		::= { dcntRITEntry 1 }

	 dcntRITNextHop OBJECT-TYPE
		SYNTAX  OCTET STRING
		ACCESS  read-only
		STATUS  mandatory
		DESCRIPTION ""
		::= { dcntRITEntry 2 }

	 dcntRITCost OBJECT-TYPE
		SYNTAX  INTEGER
		ACCESS  read-only
		STATUS  mandatory
		DESCRIPTION ""
		::= { dcntRITEntry 3 }

	 dcntRITHops OBJECT-TYPE
		SYNTAX  INTEGER
		ACCESS  read-only
		STATUS  mandatory
		DESCRIPTION ""
		::= { dcntRITEntry 4 }

	 dcntRITInterface OBJECT-TYPE
		SYNTAX  INTEGER
		ACCESS  read-only
		STATUS  mandatory
		DESCRIPTION ""
		::= { dcntRITEntry 5 }

-- DecNet Area Routing Table

	 dcntAreaRoutingTable OBJECT-TYPE
		SYNTAX  SEQUENCE OF DcntAreaRITEntry
		ACCESS  not-accessible
		STATUS  mandatory
		DESCRIPTION ""
		::= { decnet 5 }

	 dcntAreaRITEntry OBJECT-TYPE
		SYNTAX  DcntAreaRITEntry
		ACCESS  not-accessible
		STATUS  mandatory
		DESCRIPTION ""
		INDEX	{ dcntAreaRITDestArea }
		::= { dcntAreaRoutingTable 1 }
 
	DcntAreaRITEntry ::= SEQUENCE {
		dcntAreaRITDestArea
			INTEGER,
		dcntAreaRITNextHop
			OCTET STRING,
		dcntAreaRITCost
			INTEGER,
		dcntAreaRITHops
			INTEGER,
		dcntAreaRITInterface
			INTEGER
		}

	 dcntAreaRITDestArea OBJECT-TYPE
		SYNTAX  INTEGER
		ACCESS  read-only
		STATUS  mandatory
		DESCRIPTION ""
		::= { dcntAreaRITEntry 1 }

	 dcntAreaRITNextHop OBJECT-TYPE
		SYNTAX  OCTET STRING
		ACCESS  read-only
		STATUS  mandatory
		DESCRIPTION ""
		::= { dcntAreaRITEntry 2 }

	 dcntAreaRITCost OBJECT-TYPE
		SYNTAX  INTEGER
		ACCESS  read-only
		STATUS  mandatory
		DESCRIPTION ""
		::= { dcntAreaRITEntry 3 }

	 dcntAreaRITHops OBJECT-TYPE
		SYNTAX  INTEGER
		ACCESS  read-only
		STATUS  mandatory
		DESCRIPTION ""
		::= { dcntAreaRITEntry 4 }

	 dcntAreaRITInterface OBJECT-TYPE
		SYNTAX  INTEGER
		ACCESS  read-only
		STATUS  mandatory
		DESCRIPTION ""
		::= { dcntAreaRITEntry 5 }

-- Decnet Statistics

	dcntNodeAddress OBJECT-TYPE
		SYNTAX  OCTET STRING
		ACCESS  read-write
		STATUS  mandatory
		DESCRIPTION ""
		::= { decnet 6 }

	 dcntInterAreaMaxCost OBJECT-TYPE
		SYNTAX  INTEGER ( 0..1023 )
		ACCESS  read-write
		STATUS  mandatory
		DESCRIPTION ""
		::= { decnet 7 }

	dcntInterAreaMaxHops OBJECT-TYPE
		SYNTAX  INTEGER ( 0..1023 )
		ACCESS  read-write
		STATUS  mandatory
		DESCRIPTION ""
		::= { decnet 8 }

	 dcntIntraAreaMaxCost OBJECT-TYPE
		SYNTAX  INTEGER ( 0..1023 )
		ACCESS  read-write
		STATUS  mandatory
		DESCRIPTION ""
		::= { decnet 9 }

	 dcntIntraAreaMaxHops OBJECT-TYPE
		SYNTAX  INTEGER ( 0..1023 )
		ACCESS  read-write
		STATUS  mandatory
		DESCRIPTION ""
		::= { decnet 10 }

	 dcntMaxVisits OBJECT-TYPE
		SYNTAX  INTEGER ( 0..63 )
		ACCESS  read-write
		STATUS  mandatory
		DESCRIPTION ""
		::= { decnet 11 }

	 dcntRtngMsgTimerBCT1 OBJECT-TYPE
		SYNTAX  INTEGER ( 5..30 )
		ACCESS  read-write
		STATUS  mandatory
		DESCRIPTION ""
		::= { decnet 12 }

	 dcntRateControlFreqTimerT2 OBJECT-TYPE
		SYNTAX  INTEGER ( 1..5 )
		ACCESS  read-write
		STATUS  mandatory
		DESCRIPTION ""
		::= { decnet 13 }

	dcntDgmsReceived OBJECT-TYPE
		SYNTAX  Counter
		ACCESS  read-only
		STATUS  mandatory
		DESCRIPTION ""
		::= { decnet 14 }

	dcntDgmsForwarded OBJECT-TYPE
		SYNTAX  Counter
		ACCESS  read-only
		STATUS  mandatory
		DESCRIPTION ""
		::= { decnet 15 }

	 dcntDgmsOutRequested OBJECT-TYPE
		SYNTAX  Counter
		ACCESS  read-only
		STATUS  mandatory
		DESCRIPTION ""
		::= { decnet 16 }

	 dcntInDiscards OBJECT-TYPE
		SYNTAX  Counter
		ACCESS  read-only
		STATUS  mandatory
		DESCRIPTION ""
		::= { decnet 17 }

	 dcntOutDiscards OBJECT-TYPE
		SYNTAX  Counter
		ACCESS  read-only
		STATUS  mandatory
		DESCRIPTION ""
		::= { decnet 18 }

	 dcntNoRoutes OBJECT-TYPE
		SYNTAX  Counter
		ACCESS  read-only
		STATUS  mandatory
		DESCRIPTION ""
		::= { decnet 19 }

	 dcntInHdrErrors OBJECT-TYPE
		SYNTAX  Counter
		ACCESS  read-only
		STATUS  mandatory
		DESCRIPTION ""
		::= { decnet 20 }


-- rmtLapb group 
-- This group takes the place of the lapb group in any bridge or
-- bridge/router which supports X.25.

-- Remote lapb configuration table

	rmtLapbConfigTable OBJECT-TYPE
		SYNTAX  SEQUENCE OF RmtLapbCTEntry
		ACCESS  not-accessible
		STATUS  mandatory
		DESCRIPTION ""
		::= { rmtLapb 1 }

	rmtLapbCTEntry OBJECT-TYPE
		SYNTAX  RmtLapbCTEntry
		ACCESS  not-accessible
		STATUS  mandatory
		DESCRIPTION ""
		INDEX	{ rmtLapbCTIndex }
		::= { rmtLapbConfigTable 1 }

	RmtLapbCTEntry ::= SEQUENCE {
		rmtLapbCTIndex
			INTEGER,
		rmtLapbCTLinkAddr
			INTEGER,
		rmtLapbCTExtSeqNumbering
			INTEGER,
		rmtLapbCTWindow
			INTEGER,
		rmtLapbCTModeT1
			INTEGER,
		rmtLapbCTManualT1Value
			INTEGER,
		rmtLapbCTT3LinkIdleTimer
			INTEGER,
		rmtLapbCTN2RetryCount
			INTEGER,
		rmtLapbCTLinkReset
			INTEGER,
		rmtLapbCTX25PortLineSpeed
			INTEGER,
		rmtLapbCTInitLinkConnect
			INTEGER
	}
	
	rmtLapbCTIndex OBJECT-TYPE
		SYNTAX  INTEGER
		ACCESS  read-only
		STATUS  mandatory
		DESCRIPTION ""
		::= { rmtLapbCTEntry 1 }
	
	rmtLapbCTLinkAddr OBJECT-TYPE
		SYNTAX  INTEGER ( 0..1 )
		ACCESS  read-write
		STATUS  mandatory
		DESCRIPTION ""
		::= { rmtLapbCTEntry 2 }

	rmtLapbCTExtSeqNumbering OBJECT-TYPE
		SYNTAX  INTEGER ( 0..1 )
		ACCESS  read-write
		STATUS  mandatory
		DESCRIPTION ""
		::= { rmtLapbCTEntry 3 }

	rmtLapbCTWindow OBJECT-TYPE
		SYNTAX  INTEGER (1..127)
		ACCESS  read-write
		STATUS  mandatory
		DESCRIPTION ""
		::= { rmtLapbCTEntry 4 }

	rmtLapbCTModeT1 OBJECT-TYPE
		SYNTAX  INTEGER (0..1)
		ACCESS  read-write
		STATUS  mandatory
		DESCRIPTION ""
		::= { rmtLapbCTEntry 5 }

	rmtLapbCTManualT1Value OBJECT-TYPE
		SYNTAX  INTEGER (10..5000)
		ACCESS  read-write
		STATUS  mandatory
		DESCRIPTION ""
		::= { rmtLapbCTEntry 6 }

	rmtLapbCTT3LinkIdleTimer OBJECT-TYPE
		SYNTAX  INTEGER (1..65535)
		ACCESS  read-write
		STATUS  mandatory
		DESCRIPTION ""
		::= { rmtLapbCTEntry 7 }

	rmtLapbCTN2RetryCount OBJECT-TYPE
		SYNTAX  INTEGER (1..255)
		ACCESS  read-write
		STATUS  mandatory
		DESCRIPTION ""
		::= { rmtLapbCTEntry 8 }

	rmtLapbCTLinkReset OBJECT-TYPE
		SYNTAX  INTEGER 
		ACCESS  read-write
		STATUS  mandatory
		DESCRIPTION ""
		::= { rmtLapbCTEntry 9 }

	rmtLapbCTX25PortLineSpeed OBJECT-TYPE
        SYNTAX  INTEGER {
            b1200 (1200),
            b2400 (2400),
            b4800 (4800),
            b9600 (9600),
            b19200 (19200),
            b32000 (32000),
            b48000 (48000),
            b64000 (64000)
            }
        ACCESS  read-write
        STATUS  mandatory
		DESCRIPTION ""
        ::= { rmtLapbCTEntry 10 }

    rmtLapbCTInitLinkConnect OBJECT-TYPE
        SYNTAX  INTEGER
        ACCESS  read-write
        STATUS  mandatory
		DESCRIPTION ""
        ::= { rmtLapbCTEntry 11 }

-- remote lapb statistics table

	rmtLapbStatsTable OBJECT-TYPE
		SYNTAX  SEQUENCE OF RmtLapbSTEntry
		ACCESS  not-accessible
		STATUS  mandatory
		DESCRIPTION ""
		::= { rmtLapb 2 }

	rmtLapbSTEntry OBJECT-TYPE
		SYNTAX  RmtLapbSTEntry
		ACCESS  not-accessible
		STATUS  mandatory
		DESCRIPTION ""
		INDEX	{rmtLapbSTIndex }
		::= { rmtLapbStatsTable 1 }

	RmtLapbSTEntry ::= SEQUENCE {
		rmtLapbSTIndex
			INTEGER,
		rmtLapbSTState
			INTEGER,
		rmtLapbSTAutoT1value
			INTEGER,
		rmtLapbSTLastResetTime
			OCTET STRING,
		rmtLapbSTLastResetReason
			INTEGER,
		rmtLapbSTResetCount
			Counter,
		rmtLapbSTSendFrameCount
			Counter,
		rmtLapbSTRcvFrameCount
			Counter,
		rmtLapbSTSendOctetCount
			Counter,
		rmtLapbSTRcvOctetCount
			Counter,
		rmtLapbSTAbortCount
			Counter,
		rmtLapbSTCrcErrorCount
			Counter
		}


	rmtLapbSTIndex OBJECT-TYPE
		SYNTAX  INTEGER
		ACCESS  read-only
		STATUS  mandatory
		DESCRIPTION ""
		::= { rmtLapbSTEntry 1 }

	rmtLapbSTState OBJECT-TYPE
		SYNTAX  INTEGER (0..3)
		ACCESS  read-only
		STATUS  mandatory
		DESCRIPTION ""
		::= { rmtLapbSTEntry 2 }

	rmtLapbSTAutoT1value OBJECT-TYPE
		SYNTAX  INTEGER
		ACCESS  read-only
		STATUS  mandatory
		DESCRIPTION ""
		::= { rmtLapbSTEntry 3 }

	rmtLapbSTLastResetTime OBJECT-TYPE
		SYNTAX  OCTET STRING (SIZE (13))
		ACCESS  read-only
		STATUS  mandatory
		DESCRIPTION ""
		::= { rmtLapbSTEntry 4 }

	rmtLapbSTLastResetReason OBJECT-TYPE
		SYNTAX  INTEGER (0..8)
		ACCESS  read-only
		STATUS  mandatory
		DESCRIPTION ""
		::= { rmtLapbSTEntry 5 }

	rmtLapbSTResetCount OBJECT-TYPE
		SYNTAX  Counter
		ACCESS  read-only
		STATUS  mandatory
		DESCRIPTION ""
		::= { rmtLapbSTEntry 6 }

	rmtLapbSTSendFrameCount OBJECT-TYPE
		SYNTAX  Counter
		ACCESS  read-only
		STATUS  mandatory
		DESCRIPTION ""
		::= { rmtLapbSTEntry 7 }

	rmtLapbSTRcvFrameCount OBJECT-TYPE
		SYNTAX  Counter
		ACCESS  read-only
		STATUS  mandatory
		DESCRIPTION ""
		::= { rmtLapbSTEntry 8 }

	rmtLapbSTSendOctetCount OBJECT-TYPE
		SYNTAX  Counter
		ACCESS  read-only
		STATUS  mandatory
		DESCRIPTION ""
		::= { rmtLapbSTEntry 9 }

	rmtLapbSTRcvOctetCount OBJECT-TYPE
		SYNTAX  Counter
		ACCESS  read-only
		STATUS  mandatory
		DESCRIPTION ""
		::= { rmtLapbSTEntry 10 }

	rmtLapbSTAbortCount OBJECT-TYPE
		SYNTAX  Counter
		ACCESS  read-only
		STATUS  mandatory
		DESCRIPTION ""
		::= { rmtLapbSTEntry 11 }

	rmtLapbSTCrcErrorCount OBJECT-TYPE
		SYNTAX  Counter
		ACCESS  read-only
		STATUS  mandatory
		DESCRIPTION ""
		::= { rmtLapbSTEntry 12 }


-- X.25 Group

	x25Operation OBJECT-TYPE
		SYNTAX  INTEGER ( 0..1 )
		ACCESS  read-only
		STATUS  mandatory
		DESCRIPTION ""
		::= { x25 1 }

	x25OperNextReset OBJECT-TYPE
		SYNTAX  INTEGER ( 0..1 )
		ACCESS  read-write
		STATUS  mandatory
		DESCRIPTION ""
		::= { x25 2 }

-- x25 Connection set-up table


	x25ConSetupTable OBJECT-TYPE
		SYNTAX	SEQUENCE OF  X25CSTEntry
		ACCESS  not-accessible
		STATUS  mandatory
		DESCRIPTION ""
		::= { x25 3 }
	
	x25CSTEntry OBJECT-TYPE
		SYNTAX X25CSTEntry
		ACCESS  not-accessible
		STATUS  mandatory
		DESCRIPTION ""
		INDEX	{ x25CSTIndex }
		::= { x25ConSetupTable 1 }
	
	X25CSTEntry ::= SEQUENCE {
		x25CSTIndex
			INTEGER,
		x25CST8084Switch
			INTEGER,
		x25CSTSrcDTEAddr
			OCTET STRING,
		x25CSTDestDTEAddr
			OCTET STRING,
		x25CST2WayLgclChanNum
			INTEGER,
		x25CSTPktSeqNumFlg
			INTEGER,
		x25CSTFlowCntrlNeg
			INTEGER,
		x25CSTDefaultWinSize
			INTEGER,
		x25CSTDefaultPktSize
			INTEGER,
		x25CSTNegWinSize
			INTEGER,
		x25CSTNegPktSize
			INTEGER,
		x25CSTCUGSub
			INTEGER,
		x25CSTLclCUGValue
			INTEGER,
		x25CSTRvrsChrgReq
			INTEGER,
		x25CSTRvrsChrgAcc
			INTEGER
	}
	
	x25CSTIndex OBJECT-TYPE
		SYNTAX  INTEGER 
		ACCESS  read-only
		STATUS  mandatory
		DESCRIPTION ""
		::= { x25CSTEntry 1 }

	x25CST8084Switch OBJECT-TYPE
		SYNTAX  INTEGER
		ACCESS  read-write
		STATUS  mandatory
		DESCRIPTION ""
		::= { x25CSTEntry 2 }

	x25CSTSrcDTEAddr OBJECT-TYPE
		SYNTAX  OCTET STRING ( SIZE( 15 ))
		ACCESS  read-write
		STATUS  mandatory
		DESCRIPTION ""
		::= { x25CSTEntry 3 }

	x25CSTDestDTEAddr OBJECT-TYPE
		SYNTAX  OCTET STRING ( SIZE( 15 ))
		ACCESS  read-write
		STATUS  mandatory
		DESCRIPTION ""
		::= { x25CSTEntry 4 }

	x25CST2WayLgclChanNum OBJECT-TYPE
		SYNTAX  INTEGER ( 1.. 4095 )
		ACCESS  read-write
		STATUS  mandatory
		DESCRIPTION ""
		::= { x25CSTEntry 5 }

	x25CSTPktSeqNumFlg OBJECT-TYPE
		SYNTAX  INTEGER
		ACCESS  read-write
		STATUS  mandatory
		DESCRIPTION ""
		::= { x25CSTEntry 6 }

	x25CSTFlowCntrlNeg OBJECT-TYPE
		SYNTAX  INTEGER ( 0..1 )
		ACCESS  read-write
		STATUS  mandatory
		DESCRIPTION ""
		::= { x25CSTEntry 7 }

	x25CSTDefaultWinSize OBJECT-TYPE
		SYNTAX  INTEGER ( 1..127 )
		ACCESS  read-write
		STATUS  mandatory
		DESCRIPTION ""
		::= { x25CSTEntry 8 }

	x25CSTDefaultPktSize OBJECT-TYPE
		SYNTAX  INTEGER
		ACCESS  read-write
		STATUS  mandatory
		DESCRIPTION ""
		::= { x25CSTEntry 9 }

	x25CSTNegWinSize OBJECT-TYPE
		SYNTAX  INTEGER ( 1..127 )
		ACCESS  read-write
		STATUS  mandatory
		DESCRIPTION ""
		::= { x25CSTEntry 10 }

	x25CSTNegPktSize OBJECT-TYPE
		SYNTAX  INTEGER
		ACCESS  read-write
		STATUS  mandatory
		DESCRIPTION ""
		::= { x25CSTEntry 11 }

	x25CSTCUGSub OBJECT-TYPE
		SYNTAX  INTEGER 
		ACCESS  read-write
		STATUS  mandatory
		DESCRIPTION ""
		::= { x25CSTEntry 12 }

	x25CSTLclCUGValue OBJECT-TYPE
		SYNTAX  INTEGER ( 0..99 )
		ACCESS  read-write
		STATUS  mandatory
		DESCRIPTION ""
		::= { x25CSTEntry 13 }

	x25CSTRvrsChrgReq OBJECT-TYPE
		SYNTAX  INTEGER ( 0..1)
		ACCESS  read-write
		STATUS  mandatory
		DESCRIPTION ""
		::= { x25CSTEntry 14 }

	x25CSTRvrsChrgAcc OBJECT-TYPE
		SYNTAX  INTEGER ( 0..1)
		ACCESS  read-write
		STATUS  mandatory
		DESCRIPTION ""
		::= { x25CSTEntry 15 }

-- x25 Connection Control Table

	x25ConControlTable OBJECT-TYPE
		SYNTAX  SEQUENCE OF  X25CCTEntry
		ACCESS  not-accessible
		STATUS  mandatory
		DESCRIPTION ""
		::= { x25 4 }
	
	x25CCTEntry OBJECT-TYPE
		SYNTAX  X25CCTEntry
		ACCESS  not-accessible
		STATUS  mandatory
		DESCRIPTION ""
		INDEX	{ x25CCTIndex }
		::= { x25ConControlTable 1 }

	X25CCTEntry ::= SEQUENCE {
		x25CCTIndex
			INTEGER,
		x25CCTManualConnect
			INTEGER,
		x25CCTManualDisconnect
			INTEGER,
		x25CCTCfgAutoConRetry
			INTEGER,
		x25CCTOperAutoConRetryFlg
			INTEGER,
		x25CCTAutoConRetryTimer
			INTEGER,
		x25CCTMaxAutoConRetries
			INTEGER,
		x25CCTCfgTODControl
			INTEGER,
		x25CCTCurrentTODControl
	            INTEGER,
		x25CCTTODToConnect
			OCTET STRING,
		x25CCTTODToDisconnect
			OCTET STRING
		}
	
	x25CCTIndex OBJECT-TYPE
		SYNTAX  INTEGER 
		ACCESS  read-only
		STATUS  mandatory
		DESCRIPTION ""
		::= { x25CCTEntry 1 }	

	x25CCTManualConnect OBJECT-TYPE
		SYNTAX  INTEGER 
		ACCESS  read-write
		STATUS  mandatory
		DESCRIPTION ""
		::= { x25CCTEntry 2 }
	
	x25CCTManualDisconnect OBJECT-TYPE
		SYNTAX  INTEGER 
		ACCESS  read-write
		STATUS  mandatory
		DESCRIPTION ""
		::= { x25CCTEntry 3 }
	
	x25CCTCfgAutoConRetry OBJECT-TYPE
		SYNTAX  INTEGER ( 0..1 )
		ACCESS  read-write
		STATUS  mandatory
		DESCRIPTION ""
		::= { x25CCTEntry 4 }

	x25CCTOperAutoConRetryFlg OBJECT-TYPE
        SYNTAX  INTEGER ( 0..1 )
        ACCESS  read-only
        STATUS  mandatory
		DESCRIPTION ""
        ::= { x25CCTEntry 5 }

	x25CCTAutoConRetryTimer OBJECT-TYPE
		SYNTAX  INTEGER ( 1..3600 )
		ACCESS  read-write
		STATUS  mandatory
		DESCRIPTION ""
		::= { x25CCTEntry 6 }

	x25CCTMaxAutoConRetries  OBJECT-TYPE
		SYNTAX  INTEGER ( 0..255 )
		ACCESS  read-write
		STATUS  mandatory
		DESCRIPTION ""
		::= { x25CCTEntry 7 }

	x25CCTCfgTODControl OBJECT-TYPE
		SYNTAX  INTEGER ( 0..1 )
		ACCESS  read-write
		STATUS  mandatory
		DESCRIPTION ""
		::= { x25CCTEntry 8 }

	x25CCTCurrentTODControl OBJECT-TYPE
	        SYNTAX  INTEGER ( 0..1 )
       	 	ACCESS  read-write
        	STATUS  mandatory
		DESCRIPTION ""
        	::= { x25CCTEntry 9 }

	
	x25CCTTODToConnect OBJECT-TYPE
		SYNTAX  OCTET STRING ( SIZE( 4 ) )
		ACCESS  read-write
		STATUS  mandatory
		DESCRIPTION ""
		::= { x25CCTEntry 10 }

	x25CCTTODToDisconnect  OBJECT-TYPE
		SYNTAX  OCTET STRING ( SIZE( 4 ) )
		ACCESS  read-write
		STATUS  mandatory
		DESCRIPTION ""
		::= { x25CCTEntry 11 }

-- x25 Timer Table

	x25TimerTable  OBJECT-TYPE
		SYNTAX  SEQUENCE OF  X25TTEntry
		ACCESS  not-accessible
		STATUS  mandatory
		DESCRIPTION ""
		::= { x25 5 }	

	x25TTEntry OBJECT-TYPE
		SYNTAX  X25TTEntry
		ACCESS  not-accessible
		STATUS  mandatory
		DESCRIPTION ""
		INDEX	{ x25TTIndex }
		::= { x25TimerTable 1 }

	X25TTEntry ::= SEQUENCE {
		x25TTIndex
			INTEGER,
		x25TTT20Timer
			INTEGER,
		x25TTT21Timer
			INTEGER,
		x25TTT22Timer
			INTEGER,
		x25TTT23Timer
			INTEGER,
		x25TTR20Limit
			INTEGER,
		x25TTR22Limit
			INTEGER,
		x25TTR23Limit
			INTEGER
	}
	
	x25TTIndex  OBJECT-TYPE
		SYNTAX  INTEGER 
		ACCESS  read-only
		STATUS  mandatory
		DESCRIPTION ""
		::= { x25TTEntry 1 }

	x25TTT20Timer  OBJECT-TYPE
		SYNTAX  INTEGER ( 1..1024 )
		ACCESS  read-write
		STATUS  mandatory
		DESCRIPTION ""
		::= { x25TTEntry 2 }

	x25TTT21Timer  OBJECT-TYPE
		SYNTAX  INTEGER ( 1..1024 )
		ACCESS  read-write
		STATUS  mandatory
		DESCRIPTION ""
		::= { x25TTEntry 3 }

	x25TTT22Timer  OBJECT-TYPE
		SYNTAX  INTEGER ( 1..1024 )
		ACCESS  read-write
		STATUS  mandatory
		DESCRIPTION ""
		::= { x25TTEntry 4 }

	x25TTT23Timer  OBJECT-TYPE
		SYNTAX  INTEGER ( 1..1024 )
		ACCESS  read-write
		STATUS  mandatory
		DESCRIPTION ""
		::= { x25TTEntry 5 }

	x25TTR20Limit  OBJECT-TYPE
		SYNTAX  INTEGER ( 1..255 )
		ACCESS  read-write
		STATUS  mandatory
		DESCRIPTION ""
		::= { x25TTEntry 6 }

	x25TTR22Limit  OBJECT-TYPE
		SYNTAX  INTEGER ( 1..255 )
		ACCESS  read-write
		STATUS  mandatory
		DESCRIPTION ""
		::= { x25TTEntry 7 }

	x25TTR23Limit  OBJECT-TYPE
		SYNTAX  INTEGER ( 1..255 )
		ACCESS  read-write
		STATUS  mandatory
		DESCRIPTION ""
		::= { x25TTEntry 8 }
	
-- x25 Status Table 

	x25StatusTable  OBJECT-TYPE
		SYNTAX  SEQUENCE OF  X25StatusTableEntry
		ACCESS  not-accessible
		STATUS  mandatory
		DESCRIPTION ""
		::= { x25 6 }

	x25StatusTableEntry OBJECT-TYPE
		SYNTAX  X25StatusTableEntry
		ACCESS  not-accessible
		STATUS  mandatory
		DESCRIPTION ""
		INDEX	{ x25StatusIndex }
		::= { x25StatusTable 1 }

	X25StatusTableEntry ::= SEQUENCE {
		x25StatusIndex
			INTEGER,
		x25StatusIfStatus
			INTEGER,
		x25StatusSVCStatus
			INTEGER,
		x25StatusWinSize
			INTEGER,
		x25StatusPktSize
			INTEGER,
		x25StatusCauseLastInClear
			INTEGER,
		x25StatusDiagLastInClear
			INTEGER
		}
	
	x25StatusIndex  OBJECT-TYPE
		SYNTAX  INTEGER 
		ACCESS  read-only
		STATUS  mandatory
		DESCRIPTION ""
		::= { x25StatusTableEntry 1 }
	
	x25StatusIfStatus  OBJECT-TYPE
		SYNTAX  INTEGER
		ACCESS  read-only
		STATUS  mandatory
		DESCRIPTION ""
		::= { x25StatusTableEntry 2 }	
	
	x25StatusSVCStatus  OBJECT-TYPE
		SYNTAX  INTEGER
		ACCESS  read-only
		STATUS  mandatory
		DESCRIPTION ""
		::= { x25StatusTableEntry 3 }	
	
	x25StatusWinSize  OBJECT-TYPE
		SYNTAX  INTEGER
		ACCESS  read-only
		STATUS  mandatory
		DESCRIPTION ""
		::= { x25StatusTableEntry 4 }	
	
	x25StatusPktSize  OBJECT-TYPE
		SYNTAX  INTEGER
		ACCESS  read-only
		STATUS  mandatory
		DESCRIPTION ""
		::= { x25StatusTableEntry 5 }	
	
	x25StatusCauseLastInClear  OBJECT-TYPE
		SYNTAX  INTEGER (0..255)
		ACCESS  read-only
		STATUS  mandatory
		DESCRIPTION ""
		::= { x25StatusTableEntry 6 }	
	
	x25StatusDiagLastInClear  OBJECT-TYPE
		SYNTAX  INTEGER (0..255)
		ACCESS  read-only
		STATUS  mandatory
		DESCRIPTION ""
		::= { x25StatusTableEntry 7 }	

-- x25 Statistics Table
	
	x25StatsTable  OBJECT-TYPE
		SYNTAX  SEQUENCE OF  X25StatsTableEntry
		ACCESS  not-accessible
		STATUS  mandatory
		DESCRIPTION ""
		::= { x25 7 }

	x25StatsTableEntry OBJECT-TYPE
		SYNTAX  X25StatsTableEntry
		ACCESS  not-accessible
		STATUS  mandatory
		DESCRIPTION ""
		INDEX	{ x25STSVCIndex }
		::= { x25StatsTable 1 }

	X25StatsTableEntry ::= SEQUENCE {
		x25STSVCIndex
			Counter,
		x25STDataPktsTx
			Counter,
		x25STDataPktsRx
			Counter,
		x25STConnectReqPktsTx
			Counter,
		x25STIncomingCallPktsRx
			Counter,
		x25STClearReqPktsTx
			Counter,
		x25STClearIndPktsRx
			Counter,
		x25STResetReqPktsTx
			Counter,
		x25STResetIndPktsRx
			Counter,
		x25STRestartReqPktsTx
			Counter,
		x25STRestartIndPktsRx
			Counter
	}

	x25STSVCIndex  OBJECT-TYPE
		SYNTAX  INTEGER
		ACCESS  read-only
		STATUS  mandatory
		DESCRIPTION ""
		::= { x25StatsTableEntry 1 }
	
	x25STDataPktsTx  OBJECT-TYPE
		SYNTAX  Counter
		ACCESS  read-only
		STATUS  mandatory
		DESCRIPTION ""
		::= { x25StatsTableEntry 2 }
	
	x25STDataPktsRx  OBJECT-TYPE
		SYNTAX  Counter
		ACCESS  read-only
		STATUS  mandatory
		DESCRIPTION ""
		::= { x25StatsTableEntry 3 }
	
	x25STConnectReqPktsTx  OBJECT-TYPE
		SYNTAX  Counter
		ACCESS  read-only
		STATUS  mandatory
		DESCRIPTION ""
		::= { x25StatsTableEntry 4 }
	
	x25STIncomingCallPktsRx  OBJECT-TYPE
		SYNTAX  Counter 
		ACCESS  read-only
		STATUS  mandatory
		DESCRIPTION ""
		::= { x25StatsTableEntry 5 }
	
	x25STClearReqPktsTx  OBJECT-TYPE
		SYNTAX  Counter
		ACCESS  read-only
		STATUS  mandatory
		DESCRIPTION ""
		::= { x25StatsTableEntry 6 }
	
	x25STClearIndPktsRx  OBJECT-TYPE
		SYNTAX  Counter
		ACCESS  read-only
		STATUS  mandatory
		DESCRIPTION ""
		::= { x25StatsTableEntry 7 }
	
	x25STResetReqPktsTx  OBJECT-TYPE
		SYNTAX  Counter
		ACCESS  read-only
		STATUS  mandatory
		DESCRIPTION ""
		::= { x25StatsTableEntry 8 }
	
	
	x25STResetIndPktsRx  OBJECT-TYPE
		SYNTAX  Counter
		ACCESS  read-only
		STATUS  mandatory
		DESCRIPTION ""
		::= { x25StatsTableEntry 9 }
	
	x25STRestartReqPktsTx  OBJECT-TYPE
		SYNTAX  Counter
		ACCESS  read-only
		STATUS  mandatory
		DESCRIPTION ""
		::= { x25StatsTableEntry 10 }
	
	x25STRestartIndPktsRx  OBJECT-TYPE
		SYNTAX  Counter
		ACCESS  read-only
		STATUS  mandatory
		DESCRIPTION ""
		::= { x25StatsTableEntry 11 }


		END
