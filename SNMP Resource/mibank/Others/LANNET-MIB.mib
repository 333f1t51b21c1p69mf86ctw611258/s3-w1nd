LANNET-MIB DEFINITIONS ::= BEGIN

-- Title:       LANNET's MIB
-- Version:     2.0.3
-- Date:        Mar 15 , 1992
-- By:          Dan R. 
-- Comments:    LANNET's agents support also standard mibs:
--              - MIB-II  ( RFC1213-MIB )
--              - dot5    ( RFC1231-MIB, updated by RFC1239 )
IMPORTS
    NetworkAddress, IpAddress,
    Counter, Gauge, TimeTicks,
    enterprises
    FROM RFC1155-SMI
	 OBJECT-TYPE FROM RFC-1212;

-- Some MIB Compilers need these two lines:
--  enterprises  OBJECT IDENTIFIER ::= 
--                         { iso org(3) dod(6) internet(1) private(4) 1 }

lannet      OBJECT IDENTIFIER ::= { enterprises 81 }

lntStandard OBJECT IDENTIFIER ::= { lannet 1 } -- standard lannet tree

--
-- standard Hub structure
--

standardHub OBJECT IDENTIFIER ::= { lntStandard 1 } 


standardHubID OBJECT-TYPE  
      SYNTAX  OCTET STRING   
      ACCESS  read-only
      STATUS  obsolete 
      DESCRIPTION
      "A 48-bit unique identifier of the hub. Not to be confused with the
       48-bit address of the MAC that may be used to obtain management
       access to the hub when in-band signaling is used.
       If a manufacturer builds a hub with an on-board MAP for communicating
       network management information, the manufacturer has the option
       to use the same address for both HubID and MAC address. This option
       is implemented by LANNET agents for LET-18 and LET- 36."
      ::= { standardHub 1 }

standardHubElapsedTimeSinceRest OBJECT-TYPE
      SYNTAX  TimeTicks      
      ACCESS  read-write  
      STATUS  mandatory
      DESCRIPTION
      "The time in tens of milliseconds since the last time the hub was reset.
       This may have been caused by a RESET HUB action or by other means. This 
       counter has a value of 0 when initialized. Setting the value of this
       attribute to zero is interpreted by LANNET agents as a RESET commnand.
       The required resolution is to the nearest 100 milliseconds."
      ::= { standardHub 2 }

standardHubExecuteSelfTest1 OBJECT-TYPE
      SYNTAX  INTEGER {  
	off(0),
	on(1)
      }
      ACCESS  read-write    
      STATUS  optional 
      DESCRIPTION
      "Perform self-test 1 on the hub. When this attribute is set to ON by the 
      management console, the agent starts executing the hub test procedure.
      The attribute is reset to OFF at the end of the test procedure."
      ::= { standardHub 3 }


standardHubExecuteSelfTest2 OBJECT-TYPE   
      SYNTAX  INTEGER {  
	off(0), 	
	on(1)	
      }
      ACCESS  read-write    
      STATUS  optional 
      DESCRIPTION
      "Perform self test 2 on the hub. When this attribute is set to ON by the 
      management console, he agent starts executing the hub test procedure.
      The attribute is reset to OFF at the end of the test procedure."
      ::= { standardHub 4 }

  
-- standard Relay structure
--

standardRelayTable OBJECT-TYPE
      SYNTAX  SEQUENCE OF StandardRelayEntry
      ACCESS  not-accessible
      STATUS  mandatory
      ::= { lntStandard 2 } 	

StandardRelayEntry ::=
      SEQUENCE {
         standardRelayID
            INTEGER,
         standardRelayNumberOfGroups
            INTEGER,
         standardRelayTotalCollisions
            Counter,    
         standardRelayReset
           INTEGER,
         standardRelayCurTraffic
           OCTET STRING,
         standardRelayTrafficTrsh
           INTEGER,
         standardRelayPeakTraffic
           INTEGER
      }
            
standardRelayID OBJECT-TYPE   
      SYNTAX  INTEGER       
      ACCESS  read-only
      STATUS  mandatory
      DESCRIPTION
      "The value used in addressing the relay.
      Value 1 is returned by LANNET SNMP agents for hubs LE-18 and LET-36"
      ::= { standardRelayTable 1 }

standardRelayNumberOfGroups OBJECT-TYPE  
      SYNTAX  INTEGER      
      ACCESS  read-only
      STATUS  mandatory
      DESCRIPTION
      "Number of groups related to relay. Range 1-255.
      In LANNET implementation it describes the number of manageable slots
      in the hub (not all slots should be ocuppied)." 
      ::= { standardRelayTable 2 }

standardRelayTotalCollisions OBJECT-TYPE 
      SYNTAX  Counter    
      ACCESS  read-only
      STATUS  optional 
      DESCRIPTION
      "Counter incremented every time the hub enters a condition caused by
      simultaneous transmission and detection of external activity on one or
      more of its ports."
      ::= { standardRelayTable 3 }

standardRelayReset OBJECT-TYPE   
      SYNTAX  INTEGER {  
	off(0), 
	on(1)
      }
      ACCESS  read-write    
      STATUS  mandatory
      DESCRIPTION
      "Setting the value of this attribute to ON is interpreted as a relay reset
      command, which leads to the zeroing of all relay-related counters." 
      ::= { standardRelayTable 4 }

standardRelayCurTraffic OBJECT-TYPE 
      SYNTAX  OCTET STRING	  
      ACCESS  read-only
      STATUS  mandatory
      DESCRIPTION
      "Record of traffic for the last second with a resolution of 100 msec. The
       traffic is expressed in percents of the maximum Ethernet traffic and each
      record contains 10 readings, in the range 1..20, expressed on a log(10) 
      scale ( value = 10*log10(percent) )."
      ::= { standardRelayTable 5 }

standardRelayTrafficTrsh OBJECT-TYPE 
      SYNTAX  INTEGER		    
      ACCESS  read-write
      STATUS  mandatory
      DESCRIPTION
      "Traffic threshold value. When exceeded, a trap is send to the management
      console. Expressed in percents of the maximum Ethernet traffic, in the 
      range 1..20, expressed on a log(10) scale."
      ::= { standardRelayTable 6 }


standardRelayPeakTraffic OBJECT-TYPE -- Maximal traffic
      SYNTAX  INTEGER 	  	     -- Values 1..20 (Log(10) scale)
      ACCESS  read-only
      STATUS  mandatory
      DESCRIPTION
      "Maximal traffic value since last reset of hub or relay. Expressed in per-
      cents of the maximum Ethernet traffic, in the range 1..20, 
      expressed on log(10) scale."
      ::= { standardRelayTable 7 }



--
-- standard Group structure
--

standardGroupTable OBJECT-TYPE
      SYNTAX  SEQUENCE OF StandardGroupEntry
      ACCESS  not-accessible
      STATUS  mandatory
      ::= { lntStandard 3 } 	

StandardGroupEntry ::=
      SEQUENCE {
         standardGroupID
            INTEGER,   
         standardGroupNumberOfPorts
            INTEGER,
         standardGroupAutoMan
            INTEGER,
         standardGroupReset
            INTEGER
       }
            
standardGroupID OBJECT-TYPE  
      SYNTAX  INTEGER      
      ACCESS  read-only
      STATUS  mandatory
      DESCRIPTION
      "Unique value identifying the group. In LANNET enclosures it equals the
      slot number of the related module (FRU)."
      ::= { standardGroupTable 1 }


standardGroupNumberOfPorts OBJECT-TYPE 
      SYNTAX  INTEGER  
      ACCESS  read-only
      STATUS  mandatory
      DESCRIPTION
      "Number of ports contained within the group. Valid range 1..255. Within
      each group the ports are assigned unique numbers  range from 1 to 
      standardGroupNumberOfPorts. They correspond to the number of ports in the
      module (FRU)."
      ::= { standardGroupTable 2 }


standardGroupAutoMan OBJECT-TYPE  
      SYNTAX  INTEGER {
	man(0),		
	auto(1)	
      }
      ACCESS  read-only
      STATUS  mandatory 
      DESCRIPTION
      "This attribute reflects the status of the AUTO/MANual switch which defi-
      nes the working mode of LANNET sensors. In the Manual mode, no set operations
      may be performed on attributes related to the sensor. The sensor works accor-
      ding to configuration switches set in hardware and transmits all the
      configuration information to the agent. In the Auto, mode hardware switches 
      are overridden by set commands."
      ::= { standardGroupTable 3 }


standardGroupReset OBJECT-TYPE   
      SYNTAX  INTEGER {  
	off(0), 
	on(1)
      }
      ACCESS  read-write    
      STATUS  mandatory
      DESCRIPTION
      "Setting the value of this attribute to ON is interpreted as a software
      RESET command. Sensor software is reinitialized and according to the 
      sensor specifications, partial or total reset of the module hardware may
      be performed."
      ::= { standardGroupTable 4 }


--
-- standard Port structure
--

standardPortTable OBJECT-TYPE
      SYNTAX  SEQUENCE OF StandardPortEntry
      ACCESS  not-accessible
      STATUS  mandatory
      ::= { lntStandard 4 } 	

StandardPortEntry ::=
      SEQUENCE {
         standardPortType
            INTEGER,
         standardPortID
            INTEGER,
         standardPortAdminStatus -- NEW   standardPortAdminState
            INTEGER,
         standardPortAutoPartitionState
            INTEGER,
         standardPortFramesReceivedOK
            Counter,
         standardPortOctetsReceivedOK
            Counter,
         standardPortCollisions
            Counter,
         standardPortLateCollisions
            Counter,
         standardPortFrameCheckSequence
            Counter,
         standardPortSQETestNotDisabled
            INTEGER,
         standardPortRunt
            Counter,
         standardPortPygmy
            Counter,
         standardPortOutOfRangeLenField
            Counter,
         standardPortFramesTooLong
            Counter,
         standardPortAlignmentErrors 
            Counter,
         standardPortAutoPartitionLog
            Counter,
         standardPortOutOfSpecBitRate
            Counter,
         standardPortLastSourceAddress
            OCTET STRING,
         standardPortSourceAdressChanges
            Counter,
         standardPortExecuteTest
            INTEGER,
         standardPortTraffic    --    NEW
            Counter,
         standardPortPacketErrors   -- NEW
            Counter,
         standardPortUserStatus   -- NEW
            INTEGER,
         standardPortGroupID     --  NEW
            INTEGER
       }
            
standardPortType OBJECT-TYPE   -- Type of port.
      SYNTAX  INTEGER {  
	private(0),		-- Other
	repeaterAUI(1), 	-- Repeater AUI port
	repeaterThin(2), 	-- Repeater Thin port
	repeater10BaseT(3), 	-- Repeater 10BASET port
	tenBaseFSyncAct(4),	-- 10BASEF Synchronous Active
	foirl(5),       	-- 10BASEF FOIRL
	xcvr(6),           -- XCVR port
	lobe(7),           -- Token ring lobe port
	ri(8),             -- Token ring input  port 
	ro(9),             -- Token ring output  port 
        serial(10),        -- Serial port
        localTalk(11)      -- Local Talk
      }
      ACCESS  read-only
      STATUS  mandatory
      DESCRIPTION
      "Describes the port type from the point of view of its network functionali-
      ty. This characterization describes adherence to physical layer standards,
      while LANNET standard extensions are generally defined as private." 
      ::= { standardPortTable 1 }



standardPortID OBJECT-TYPE 
      SYNTAX  INTEGER     
      ACCESS  read-only
      STATUS  mandatory
      DESCRIPTION
      "A value unique in each group. It is assumed that ports are partitioned into
      groups that also have IDs and are related to FRUs. This value can never 
      exceed standardGroupNumberOfPorts. Range 0..255."
      ::= { standardPortTable 2 }


standardPortAdminStatus OBJECT-TYPE   -- Administrative state of port
      SYNTAX  INTEGER {
	disabled(0),
	enabled(1)
      }
      ACCESS  read-write
      STATUS  mandatory
      DESCRIPTION
      "A disabled port neither transmits nor receives. The port must be explici-
      tenly enabled to restore operation. 
      standardPortAdminStatus takes precedence over AutoPartition."
      ::= { standardPortTable 3 }

standardPortAutoPartitionState OBJECT-TYPE
      SYNTAX  INTEGER {
	notAutoPart(0),
	autoPart(1)
      }
      ACCESS  read-only
      STATUS  mandatory
     DESCRIPTION
     "The AutoPart condition indicates that the port is currently partitioned
     by the auto-partition protection mechanism."
      ::= { standardPortTable 4 }

standardPortFramesReceivedOK OBJECT-TYPE   
      SYNTAX  Counter
      ACCESS  read-only
      STATUS  mandatory
     DESCRIPTION
      "A representation of the total  number of frames of legal length that have not been
      corrupted in transmission. These frames can be encoded and decoded by the
      commonly available MACs and provide a measure of the network bandwidth
      being used. The number does not include frames received with frame-too-long, FCS,
      alignment errors, frames lost due to internal MAC sublayer errors, runts
      or pygmys."
      ::= { standardPortTable 5 }

standardPortOctetsReceivedOK OBJECT-TYPE   
      SYNTAX  Counter
      ACCESS  read-only
      STATUS  optional 
     DESCRIPTION
     "Counter for the number of data and padding octets contained in the
     FramesReceivedOK counter."
      ::= { standardPortTable 6 }

standardPortCollisions OBJECT-TYPE   
      SYNTAX  Counter
      ACCESS  read-only
      STATUS  optional 
      DESCRIPTION
      "Counter incremented every time the hub enters a condition caused by
      simultaneous transmission and detection of external activity on this  
      port."
      ::= { standardPortTable 7 }

standardPortLateCollisions OBJECT-TYPE   
      SYNTAX  Counter
      ACCESS  read-only
      STATUS  optional 
      ::= { standardPortTable 8 }

standardPortFrameCheckSequence OBJECT-TYPE   
      SYNTAX  Counter
      ACCESS  read-only
      STATUS  optional 
      DESCRIPTION
      "Counter for the number of frames received on this port that are an 
      integral number of octets in length and do not pass the FCS check."
      ::= { standardPortTable 9 }

standardPortSQETestNotDisabled OBJECT-TYPE   
      SYNTAX  INTEGER {
	disabled(0),
	notDisabled(1)
      }
      ACCESS  read-write
      STATUS  mandatory
      DESCRIPTION
      "Settable attribute which allows activation of SQE test for LANNET 
       integrated transceivers."
      ::= { standardPortTable 10 }

standardPortRunt OBJECT-TYPE   
      SYNTAX  Counter
      ACCESS  read-only
      STATUS  mandatory
      DESCRIPTION
      "Counter for the number of collision fragments longer than a pygmy and
      shorter than a legal packet, detected on this port."
      ::= { standardPortTable 11 }

standardPortPygmy OBJECT-TYPE   
      SYNTAX  Counter
      ACCESS  read-only
      STATUS  optional 
      DESCRIPTION
      "Counter for the number of pygmy fragments received on this port. These
      fragments, less than 64 +/- 10 bits long, may indicate an external noise
      hit,  a network problem."
      ::= { standardPortTable 12 }

standardPortOutOfRangeLenField OBJECT-TYPE   
      SYNTAX  Counter
      ACCESS  read-only
      STATUS  optional 
      DESCRIPTION
      "Counter for the number of packets received on this port whose length 
      field indicate values greater than 2 ** 15      . Such packets gene-
      rally do not point to a network problem, but merely to the use of  the                                                    
      IEEE 802.3 protocol instead of Ethernet, in which case the field has a 
      different significance - protocol type. It may be used for counting the
      number of frames transmitted in each protocol."
      ::= { standardPortTable 13 }

standardPortFramesTooLong OBJECT-TYPE   
      SYNTAX  Counter
      ACCESS  read-only
      STATUS  optional 
      DESCRIPTION
      "Counter for the number of packets received on this port that are longer 
      than 1518 octets, yet do not exceed the maximum range for the 
      range field."
      ::= { standardPortTable 14 }

standardPortAlignmentErrors OBJECT-TYPE   
      SYNTAX  Counter
      ACCESS  read-only
      STATUS  optional 
      DESCRIPTION
      "Counter for the number of frames received though this port that are not 
      an integral number of octets in length. Although these frames will not
      pass the FCS check, they are not counted as FCS errors, as the alignment
      errors have precedence in the standard error counting scheme."
      ::= { standardPortTable 15 }

standardPortAutoPartitionLog OBJECT-TYPE   
      SYNTAX  Counter
      ACCESS  read-only
      STATUS  mandatory
      DESCRIPTION
      "Counter for the number of times the repeater has automatically partitio-
      ned this port."
      ::= { standardPortTable 16 }

standardPortOutOfSpecBitRate OBJECT-TYPE   
      SYNTAX  Counter
      ACCESS  read-only
      STATUS  optional
      DESCRIPTION
      "Counter for the number of times a packet has been received by this port
      with the transmission frequency (data rate) detectable out of spec."
      ::= { standardPortTable 17 }

standardPortLastSourceAddress OBJECT-TYPE   
      SYNTAX  OCTET STRING 
      ACCESS  read-only
      STATUS  mandatory
      DESCRIPTION
      "Ethernet source address of the last readable frame received by this 
      port."
      ::= { standardPortTable 18 }

standardPortSourceAdressChanges OBJECT-TYPE 
      SYNTAX  Counter
      ACCESS  read-only
      STATUS  mandatory
      DESCRIPTION
      "Counter for the number of times the last source address has
      changed."
      ::= { standardPortTable 19 }

standardPortExecuteTest OBJECT-TYPE   -- Perform self test.
      SYNTAX  INTEGER {  
	off(0), 	-- Ignore this value
	on(1)		-- Perform test
      }
      ACCESS  read-write    
      STATUS  optional 
      DESCRIPTION
      "Setting to the value of this attribute to ON (determines the port to enter)
      self-test mode."
      ::= { standardPortTable 20 }

standardPortTraffic OBJECT-TYPE 
      SYNTAX  Counter	   
      ACCESS  read-only
      STATUS  mandatory
      DESCRIPTION
      "Counter for the number of bits received on this port in frames with legal
      length information."
      ::= { standardPortTable 21 }

standardPortPacketErrors OBJECT-TYPE 
      SYNTAX  Counter	   
      ACCESS  read-only
      STATUS  mandatory
      DESCRIPTION
      "Counter for the number of frames with errors detected on the port by
      the LANNET agent hardware. This generic port error comprises too long
      packets, CRC and alignment errors."
      ::= { standardPortTable 22 }

standardPortUserStatus OBJECT-TYPE
      SYNTAX  INTEGER {
	singleUser(1),
	multiUser(2)	
      }
      ACCESS  read-only
      STATUS  mandatory
      DESCRIPTION
      "Attribute defining the connection of a port to a single Ethernet source
      or to a multi-source (segment or star)."
      ::= { standardPortTable 23 }

standardPortGroupID OBJECT-TYPE 
      SYNTAX  INTEGER
      ACCESS  read-only
      STATUS  mandatory
      DESCRIPTION
      "ID of group which contains the port"
      ::= { standardPortTable 24 }




lntSpecific OBJECT IDENTIFIER ::= { lannet 2 } -- Specific LANNET tree

--
--		 Mgr table definition 
--


mgrTable OBJECT-TYPE
      SYNTAX  SEQUENCE OF MgrEntry
      ACCESS  not-accessible
      STATUS  mandatory
      ::= { lntSpecific 1 }

MgrEntry ::= SEQUENCE {
	mgrIPaddr
	  IpAddress,
	mgrMngmntState
          INTEGER,
	mgrTrapRepStat
          INTEGER,
	mgrContPerfornamceRep
          INTEGER
    }

mgrIPaddr OBJECT-TYPE		
      SYNTAX  IpAddress
      ACCESS  read-write
      STATUS  obsolete
      DESCRIPTION
      "IP address of the network management console."
      ::= { mgrTable 1 }

mgrTrapRepStat OBJECT-TYPE
      SYNTAX  INTEGER {
	off(0),		
	on(1)	
      }
      ACCESS  read-write
      STATUS  mandatory
      DESCRIPTION
      "ON indicates that SNMP agent should send SNMP traps (relay traffic ex-
      cluded) to the manager."
      ::= { mgrTable 2 }

mgrContPerformanceRep OBJECT-TYPE	
      SYNTAX  INTEGER {
	off(0),		
	on(1)
      }
      ACCESS  read-write
      STATUS  mandatory
      DESCRIPTION
      "ON indicates that the SNMP agent should send relay traffic SNMP traps to
      the manager."
      ::= { mgrTable 3 }

mgrMngmntState OBJECT-TYPE
      SYNTAX  INTEGER {
	off(0),		
	on(1)
      }
      ACCESS  read-write
      STATUS  mandatory
      DESCRIPTION
      "Attribute to be set by manager in order to instruct the agent 
      to enter into a management session with the console. 
      Setting this value to ON has the effect of performing 
      an 'I am your manager' action upon the agent."
      ::= { mgrTable 4 }

--
--		 sw Load definition
--

swLoad  OBJECT IDENTIFIER ::= { lntSpecific 2 }

swLoadInit OBJECT-TYPE
      SYNTAX  OCTET STRING
      ACCESS  read-write
      STATUS  optional 
      DESCRIPTION
      "Sensors software download procedure initialization message. Includes spe-
      cific information about the download procedure, such as type of target sen-
      sor, number of blocks, version."
      ::= { swLoad 1 }

swLoadSWBlock OBJECT-TYPE
      SYNTAX  OCTET STRING
      ACCESS  read-write
      STATUS  optional
      DESCRIPTION
      "Block of sensor software."
      ::= { swLoad 2 }

--
--		 Hub Agent Definition
--

lntHubAgent OBJECT IDENTIFIER ::= { lntSpecific 3 }

lntHubAgentSWFault OBJECT-TYPE
      SYNTAX  OCTET STRING
      ACCESS  read-only
      STATUS  mandatory
      DESCRIPTION
      "Generic fault emitted by agent software. It generally covers all types
      of faults which cannot be transmitted by the standard types of generic
      SNMP traps. Uses EnterpriseSpecific traps mechanism."
      ::= { lntHubAgent 1 }

lntHubAgentEthernetAddr OBJECT-TYPE   -- Hub agent Ethernet Address
      SYNTAX  OCTET STRING            -- Represented as 48 bit INTEGER 
      ACCESS  read-only
      STATUS  obsolete
      DESCRIPTION
      "Hub agent Ethernet Address - used in previous implementations. Today
       replaced by interface address in standard MIB II."
      ::= { lntHubAgent 2 }

lntHubAgentHWVersion OBJECT-TYPE
      SYNTAX  OCTET STRING
      ACCESS  read-only
      STATUS  mandatory
      DESCRIPTION
      "ASCII string for description and display of the agent hardware version,
      as  known to the agent software."
      ::= { lntHubAgent 3 }

lntHubAgentSWVersion OBJECT-TYPE
      SYNTAX  OCTET STRING
      ACCESS  read-only
      STATUS  mandatory
      DESCRIPTION
      "ASCII string for description and display of the agent software version."
      ::= { lntHubAgent 4 }

lntHubAgentKernelVersion OBJECT-TYPE
      SYNTAX  OCTET STRING
      ACCESS  read-only
      STATUS  mandatory
      DESCRIPTION
      "ASCII string for description and display of the agent operating system
      (kernel) version."
      ::= { lntHubAgent 5 }

lntHubAgentFullConfig OBJECT-TYPE  -- Hub full config 
      SYNTAX  OCTET STRING
      ACCESS  read-only
      STATUS  mandatory
      DESCRIPTION
      "Full configuration message sent by agent upon enrollment and at periodic
      interrogation times. Coded in internal LANNET application format. Up to
      release 1.5, this attribute was trasmitted to the management console by
      generic EnterpriseSpecific traps. Starting with release 2.0,  it is retrieved by
      means of Get interogations."
      ::= { lntHubAgent 6 }

lntHubAgentPerfBusSelection OBJECT-TYPE      -- NEW
      SYNTAX  INTEGER
      ACCESS  read-write
      STATUS  mandatory
      DESCRIPTION
      "Attribute describing the bus attached to the performance data collection 
      hardware on those LANNET agent hardware implementations which support
      configuration management on multi-Ethernet bus enclosures, but performan-
      ce data collection on a single bus."
      ::= { lntHubAgent 7 } 

lntHubAgentLastAddressConfig OBJECT-TYPE   
      SYNTAX  OCTET STRING
      ACCESS  read-only
      STATUS  mandatory
      DESCRIPTION
      "Configuration attribute describing the last physical address detected 
       at each Ethernet port. Coded in internal LANNET application format. "
      ::= { lntHubAgent 8 }

lntHubAgentMgmtBusSelection OBJECT-TYPE      -- NEW
      SYNTAX  INTEGER
      ACCESS  read-only
      STATUS  mandatory
      DESCRIPTION
      "Attribute describing the bus attached to the performance data collection 
      hardware on those LANNET agent hardware implementations which support
      configuration management on multi-Ethernet bus enclosures, but performan-
      ce data collection on a single bus."
      ::= { lntHubAgent 9 } 

lntHubAgentSLIPIpAddress OBJECT-TYPE
      SYNTAX  IpAddress
      ACCESS  read-only
      STATUS  mandatory
      DESCRIPTION
      "IP address of the SLIP channel of the agent"
      ::= { lntHubAgent 10 } 

lntHubAgentType OBJECT-TYPE
      SYNTAX  INTEGER {
         nma1-et(1),
         nma1-etd(2),
         nma1-tr(3),
         nma2-et(4),
         nma2-tr(5)           -- 2.03 last minute
      }
      ACCESS  read-only
      STATUS  mandatory
      DESCRIPTION
      "Agent type."
      ::= { lntHubAgent 11 } 

lntHubAgentHC11CommunicationStatus OBJECT-TYPE      -- 2.0.2
      SYNTAX  INTEGER {
              ok(1),
              commProblems(2),
              timeout(3)
         }
      ACCESS  read-only
      STATUS  mandatory
      DESCRIPTION
      "Attribute describing the status of the communication with the Master 
      HC11 as detected by the Agent software."
      ::= { lntHubAgent 12 } 

lntHubAgentCommunicationDebugMode OBJECT-TYPE      -- 2.0.3
      SYNTAX  INTEGER {
              off(0),
              on(1)
         }
      ACCESS  read-write
      STATUS  mandatory
      DESCRIPTION
      "Attribute describing the agent mode in which communication problem
      traps are sent to managers (value on) or are not sent to managers
      (value off)."
      ::= { lntHubAgent 13 }

--
--		 Hub Hardware Definition
--

lntHubHW OBJECT IDENTIFIER ::= { lntSpecific 4 }

lntHubHWInternalTemp OBJECT-TYPE
      SYNTAX  INTEGER
      ACCESS  read-write
      STATUS  optional 
      DESCRIPTION
      "Internal enclosure temperature expressed in degrees Celsius."
      ::= { lntHubHW 1 }


lntHubHWExternalTemp OBJECT-TYPE
      SYNTAX  INTEGER
      ACCESS  read-write
      STATUS  optional 
      DESCRIPTION
      "External enclosure temperature expressed in degrees Celsius."
      ::= { lntHubHW 2 }

lntHubHWInternalPower OBJECT-TYPE
      SYNTAX  INTEGER {
	none(0),
	exist(1)
      }
      ACCESS  read-only
      STATUS  optional 
      DESCRIPTION
      "Value EXIST of this attribute signifies existence of an internal power 
      supply on hardware configurations which may contain two (external 
      and internal) power supply units."
      ::= { lntHubHW 3 }

lntHubHWExternalPower OBJECT-TYPE
      SYNTAX  INTEGER {
	none(0),
	exist(1) 
      }
      ACCESS  read-only
      STATUS  optional 
      DESCRIPTION
      "Value EXIST of this attribute signifies existence of an external power sup-
      ply on hardware configurations which may contain two (external 
      and internal) power supply units."
      ::= { lntHubHW 4 }

lntHubHWMainPower OBJECT-TYPE
      SYNTAX  INTEGER {
	internal(0),
	external(1)
      }
      ACCESS  read-write
      STATUS  optional 
      DESCRIPTION
      "This attribute defines the main power supply (internal or external) 
      on hardware configurations represented upon the model of 2 (external 
      and internal) power supply units."
      ::= { lntHubHW 5 }

lntHubHWCoolingFan OBJECT-TYPE
      SYNTAX  INTEGER {
	off(0),
	on(1)
      }
      ACCESS  read-only
      STATUS  optional 
      DESCRIPTION
      "Value ON of this attribute indicates operation of a cooling fan in the 
      enclosure."
      ::= { lntHubHW 6 }

lntHubHWType OBJECT-TYPE
      SYNTAX  INTEGER {
	unknown(0),
	let18(1),
	let3(2),
	let36(3),
	let18Dual(4)
      }
      ACCESS  read-only
      STATUS  mandatory
      DESCRIPTION
      "Indicates type of enclosure in which the LANNET SNMP agent operates."
      ::= { lntHubHW 7 }

lntHubHWNumberOfEthernetBuses OBJECT-TYPE
      SYNTAX  INTEGER
      ACCESS  read-only
      STATUS  mandatory
      DESCRIPTION
      "Indicates the number of internal Ethernet buses provided by the box."
      ::= { lntHubHW 8 }

lntHubHWNumberOfTRBuses OBJECT-TYPE
      SYNTAX  INTEGER
      ACCESS  read-only
      STATUS  mandatory
      DESCRIPTION
      "Indicates the number of internal Token Ring buses provided by the box."
      ::= { lntHubHW 9 }

lntHubHWNumberOfFDDIBuses OBJECT-TYPE
      SYNTAX  INTEGER
      ACCESS  read-only
      STATUS  mandatory
      DESCRIPTION
      "Indicates the number of internal FDDI buses provided by the box."
      ::= { lntHubHW 10 }

        
--
--		 LANNET Relay Definition
--

lntRelay  OBJECT IDENTIFIER ::= { lntSpecific 5 }

--
--		 standard LANNET Group Definition
--

lntGroupTable OBJECT-TYPE
      SYNTAX  SEQUENCE OF LntGroupEntry
      ACCESS  not-accessible
      STATUS mandatory
      ::= { lntSpecific 6 }

LntGroupEntry ::= SEQUENCE {
      lntGroupHWVersion
         OCTET STRING,
      lntGroupSWVersion
         OCTET STRING,
      lntGroupKernelVersion
         OCTET STRING,
      lntGroupType
         INTEGER,
      lntGroupFIFO
         INTEGER,
      lntGroupJabber
         INTEGER,
      lntGroupBusPartition
         INTEGER,
      lntGroupRedun12
         INTEGER,
      lntGroupRedun34
         INTEGER,
      lntGroup10BTPlus
         INTEGER,
      lntGroupFullConfig
         OCTET STRING,
      lntGroupAgentIfType          -- NEW
         INTEGER,
      lntGroupAgentAddress                  -- NEW
         OCTET STRING (SIZE (0..15)),       
      lntGroupWrongPortSelection           -- NEW
         INTEGER,
      lntGroupSupplyVoltageFault         -- NEW
         INTEGER,
      lntGroupNumberOfIntPorts         -- NEW
         INTEGER (0..255),
      lntGroupInPortsRedundancy        -- NEW
         INTEGER,
      lntGroupStandAloneModeSwitch      -- NEW
         INTEGER,
      lntGroupId                        -- NEW
         INTEGER,
      lntGroupDescr           -- NEW
	 OCTET STRING,
      lntGroupBackboneMode    -- 2.0.2
         INTEGER,
      lntGroupFOIRLPlusMode    -- 2.0.2
         INTEGER,
      lntGroupLATStatus         -- 2.0.2
         INTEGER,
      lntGroupInterProcCommStatus  -- 2.0.2
         INTEGER,
      lntGroupOperationMode        -- 2.0.2
         INTEGER,
      lntGroupCommunicationStatus  -- 2.0.2
         INTEGER,
      lntGroupHardwareStatus       -- 2.0.2
         INTEGER
      }
      
lntGroupHWVersion OBJECT-TYPE
      SYNTAX  OCTET STRING
      ACCESS  read-only
      STATUS  mandatory
      DESCRIPTION
      "ASCII string for description and display of the sensor hardware version,
      as it is known to the agent software."
      ::= { lntGroupTable 1 }

lntGroupSWVersion OBJECT-TYPE
      SYNTAX  OCTET STRING
      ACCESS  read-only
      STATUS  mandatory
      DESCRIPTION
      "ASCII string for description and display of the sensor application soft-
      ware version ."
      ::= { lntGroupTable 2 }

lntGroupKernelVersion OBJECT-TYPE
      SYNTAX  OCTET STRING
      ACCESS  read-only
      STATUS  mandatory
      DESCRIPTION
      "ASCII string for description and display of the sensor kernel software
      version."
      ::= { lntGroupTable 3 }

lntGroupType OBJECT-TYPE
      SYNTAX  INTEGER {
	  unknown(0),
	  le10b(1),
	  le10b-2(2),
	  le10c(3),
	  le10c-2(4),
	  le15(5),
	  le15-2(6),
	  le20(7),
	  le30x(8),
	  le30x-2(9),
	  le30xd(10),
	  le40x(11),
	  le40xt(12),
	  le10b-2r(25),         -- NEW TYPE
          le10c-2r(26),         -- NEW TYPE
          le80xt(27),         -- NEW TYPE
          le140xt(28),         -- NEW TYPE
          ielb(29),         -- NEW TYPE
          lts16(32),        -- 2.0.2
          le20n(33),        -- 2.0.2
          le20r(35),        -- 2.0.2
          le20s(37),        -- 2.0.2
          le10b2n(38)       -- 2.0.2
	}
      ACCESS  read-only
      STATUS  mandatory
      DESCRIPTION
      "Attribute describing the type of LANNET Ethernet group."
      ::= { lntGroupTable 4 }

lntGroupFIFO OBJECT-TYPE -- Module FIFO valid for :
			 -- LE-10C, LE-10C-2, LE-10B-2, LE-10B, LE-40XT
      SYNTAX  INTEGER {
	off(0),
	on(1)
      }
      ACCESS  read-only
      STATUS  mandatory
      DESCRIPTION
      "Value ON of this attribute describes an internal FIFO error sensed by the
      internal hardware mechanism of a LANNET repeater."
      ::= { lntGroupTable 5 }

lntGroupJabber OBJECT-TYPE 
      SYNTAX  INTEGER {
	off(0),
	on(1)
      }
      ACCESS  read-only
      STATUS  mandatory
      DESCRIPTION
      "Value ON of this attribute reflects jabber being transmitted to the bus by 
      the hardware of a LANNET repeater, as a result of collisions detec-
      ted on the internal bus of the enclosure. Valid for modules LE-10 (all 
      types) and LE-40XT."
      ::= { lntGroupTable 6 }

lntGroupBusPartition OBJECT-TYPE 
      SYNTAX  INTEGER {
	off(0),
	on(1)
      }
      ACCESS  read-only
      STATUS  obsolete
     DESCRIPTION
     "The AutoPart condition indicates that a LANNET repeater is currently par-
     titioned from the internal bus by the auto-partition mechanism. Valid for 
     all types of LE-10 modules."
      ::= { lntGroupTable 7 }


lntGroupRedun12 OBJECT-TYPE
      SYNTAX  INTEGER {
	off(0),
	on(1)
      }
      ACCESS  read-write
      STATUS  mandatory
     DESCRIPTION
     "Value ON of this attribute defines a redundancy (backup) relationship between
     synchronous external ports 1 and 2 on a LANNET module. Valid for modules 
     LE-10B-2, LE-10C-2, LE-20, LE-30X, LE-30X-2, LE-30XD, LE-40X, LE-40XT, 
     LE-80XT, LE-140XT."
      ::= { lntGroupTable 8 }

lntGroupRedun34 OBJECT-TYPE 
      SYNTAX  INTEGER {
	off(0),
	on(1)
      }
      ACCESS  read-write
      STATUS  mandatory
     DESCRIPTION
     "Value ON of this attribute defines a redundancy (backup) relationship between
     synchronous external ports 3 and 4 on a LANNET module. Valid for modules 
     LE-30X, LE-30XD, LE-40X, LE-40XT."
      ::= { lntGroupTable 9 }

lntGroup10BTPlus OBJECT-TYPE 
      SYNTAX  INTEGER {
	off(0),
	on(1)
      }
      ACCESS  read-write
      STATUS  mandatory
     DESCRIPTION
     "Value ON of this attribute defines activation of the 10BaseT+ mode of
     one of the LE-40XT, LE-80XT, LE-140XT modules. 10BaseT+ is a LANNET exten-
     sion of the 10BaseT standard."
      ::= { lntGroupTable 10 }


lntGroupFullConfig OBJECT-TYPE  -- Module full config 
      SYNTAX  OCTET STRING
      ACCESS  read-only
      STATUS  mandatory
     DESCRIPTION
     "Attribute describing the full configuration of a group, in internal LANNET
     application format."
      ::= { lntGroupTable 11 }

lntGroupAgentIfType OBJECT-TYPE  
      SYNTAX  INTEGER {
	      none(1),
	      regular1822(2),
	      hdh1822(3),
	      ddn-x25(4),
	      rfc877-x25(5),
	      ethernet-csmacd(6),
	      iso88023-csmacd(7),
	      iso88024-tokenBus(8),
	      iso88025-tokenRing(9),
	      iso88026-man(10),
	      starLan(11),
	      proteon-10MBit(12),
	      proteon-80MBit(13),
	      hyperchannel(14),
	      fddi(15),
	      lapb(16),
	      sdlc(17),
	      t1-carrier(18),
	      cept(19),
	      basicIsdn(20),
	      primaryIsdn(21),
	      propPointToPointSerial(22),    -- proprietary serial
	      ppp(23),
	      softwareLoopback(24),
	      eon(25),                       -- CLNP over IP
	      ethernet-3Mbit(26),
	      nsip(27),                      -- XNS over IP
	      slip(28),                      -- generic SLIP
	      ip(255)
      }
      ACCESS  read-only 
      STATUS  mandatory
     DESCRIPTION
     "This attribute describes the interfaces of agents eventually existing on
     LANNET modules and their type. Value none defines the lack of an agent or 
     of an interface recognized by the management console.  Any other value
     defines an interface whose type is recognized by the management console
     and may be used as a management channel."
      ::= { lntGroupTable 12 }

lntGroupAgentAddress OBJECT-TYPE  
      SYNTAX  OCTET STRING       -- ( SIZE (0..15)) 
      ACCESS  read-only                   
      STATUS  mandatory
     DESCRIPTION
     "This attribute defines an unique address by which the agent may be addres-
     sed by the management console. The address format should be consistent with
     the type defined by lntGroupAgentIfType." 
      ::= { lntGroupTable 13 }

lntGroupWrongPortSelection OBJECT-TYPE    
      SYNTAX  INTEGER { 
	off(0),
	on(1)
      }
      ACCESS  read-only
      STATUS  mandatory
     DESCRIPTION
     "A value ON of this attribute warns of incorrect selection of enabled
     ports on sensors which impose restrictions on this configura-
     tion (e.g. integrated local bridges."
      ::= { lntGroupTable 14 }

lntGroupSupplyVoltageFault OBJECT-TYPE  
      SYNTAX  INTEGER {
	off(0),
	on(1)
      }
      ACCESS read-only
      STATUS mandatory
     DESCRIPTION
     "A value ON of this attribute informs of a 'voltage supply out-of-range' 
     error candition on sensor hardware which checks this condition."
      ::= { lntGroupTable 15 }

lntGroupNumberOfIntPorts OBJECT-TYPE 
      SYNTAX  INTEGER (0..255)
      ACCESS read-only
      STATUS mandatory
     DESCRIPTION
     "Number of internal ports (ports connected to the enclosure buses) on
     the sensor."
      ::= { lntGroupTable 16 }

lntGroupInPortsRedundancy OBJECT-TYPE
      SYNTAX  INTEGER {
	off(0),
	on(1)
	}
      ACCESS read-write
      STATUS mandatory
     DESCRIPTION
     "Value ON of this attribute defines a redundancy (backup) relationship
     between internal ports 1 and 2 on a LANNET module." 
      ::= { lntGroupTable 17 }

lntGroupStandAloneModeSwitch OBJECT-TYPE 
      SYNTAX  INTEGER {
	off(0),
	on(1)
	}

      ACCESS read-write
      STATUS mandatory
     DESCRIPTION
     "Value ON of this attribute indicates the sensor's operation Stand Alone mode . 
     Internal ports are disabled and the card functions in a local star configuration 
     toward its external ports."
      ::= { lntGroupTable 18 }
				     
lntGroupId  OBJECT-TYPE
      SYNTAX  INTEGER
      ACCESS  read-only
      STATUS  mandatory
     DESCRIPTION
     "Unique ID number for the group in the lntGroupTable."
      ::= { lntGroupTable 19 }

lntGroupDescr  OBJECT-TYPE
      SYNTAX  OCTET STRING
      ACCESS  read-only
      STATUS  mandatory
     DESCRIPTION
     "Descriptor of the group in ASCII (readable) format, mainly for use with
     generic management applications."
      ::= { lntGroupTable 20 }

lntGroupBackboneMode OBJECT-TYPE 
      SYNTAX  INTEGER {
	off(0),
	on(1)
	}
      ACCESS read-write
      STATUS mandatory
     DESCRIPTION
     "Value On of this attribute defines Backbone Mode of a sensor. Internal
     ports are enabled and the information path goes straightly from external 
     port to internal bus, via corresponding internal port."
      ::= { lntGroupTable 21 }
				     
lntGroupFOIRLPlusMode OBJECT-TYPE 
      SYNTAX  INTEGER {
	off(0),
	on(1)
	}
      ACCESS read-write
      STATUS mandatory
     DESCRIPTION
     "Value On of this attribute defines FOIRL of a sensor. When this attribute
     has value ON, FOIRL Plus mode is enabled, while value OFF indicates stan-
     dard FOIRL mode."
      ::= { lntGroupTable 22 }
				     
lntGroupLATStatus OBJECT-TYPE
      SYNTAX  INTEGER {
	off(0),
	on(1)
	}
      ACCESS read-only 
      STATUS mandatory
     DESCRIPTION
     "Value ON of this attribute means that LAT protocol is Enabled on the 
     LANNET Ethernet module." 
      ::= { lntGroupTable 23 }

lntGroupInterProcCommStatus OBJECT-TYPE  
      SYNTAX  INTEGER {
              ok(1),
              commProblems(2),
              noCommunication(3)
      }
      ACCESS  read-only                   
      STATUS  mandatory
     DESCRIPTION
     "This attribute describes the status of the communication between the
     microprocessor of the sensor and the microprocessor of the agent on cards
     with embedded agents." 
      ::= { lntGroupTable 24 }

lntGroupOperationMode OBJECT-TYPE  
      SYNTAX  INTEGER {
              diagnostics(1),
              diagnosticsFailure(2),
              loading(3),
              loadingFailure(4),
              operational(5)
      }
      ACCESS  read-only                   
      STATUS  mandatory
     DESCRIPTION
     "This attribute describes the operation mode of the module in a 
     multiprocessor configuration sensor, as reported by interprocessors 
     communication." 
      ::= { lntGroupTable 25 }

lntGroupCommunicationStatus OBJECT-TYPE  
      SYNTAX  INTEGER {
              ok(1),
              commProblems(2)
      }
      ACCESS  read-only
      STATUS  mandatory
     DESCRIPTION
     "This attribute describes the communication status of the group with
     the SNMP Agent as detected and reported by the agent."
      ::= { lntGroupTable 26 }
      
lntGroupHardwareStatus OBJECT-TYPE  
      SYNTAX  INTEGER {
              ok(1),
              hardwareProblems(2)
      }
      ACCESS  read-only
      STATUS  mandatory
     DESCRIPTION
     "This attribute describes the status of the group hardware as detected
     by the sensors software."
           ::= { lntGroupTable 27 }
      
--
--		 LANNET Port Definition
--


lntPortTable OBJECT-TYPE 
      SYNTAX  SEQUENCE OF LntPortEntry
      ACCESS  not-accessible
      STATUS mandatory
      ::= { lntSpecific 7 }

LntPortEntry ::=
   SEQUENCE {
      lntPortType
         INTEGER,
      lntPortJabber
         INTEGER,
      lntPortNoAUILoop
         INTEGER,
      lntPortFunctionalStatus
         INTEGER,
      lntPortManPart
         INTEGER,
      lntPortLinkTest
         INTEGER,
      lntPortPeer
         INTEGER,
      lntPortAgent
         INTEGER,
      lntPortAgentAddr
         IpAddress,
      lntPortActivityStatus         -- NEW
         INTEGER,
      lntPortGroupId                -- NEW
         INTEGER,
      lntPortId                     -- NEW
         INTEGER,
      lntPortDescr                  -- NEW
	 OCTET STRING,
      lntPortIntPortConnection      -- 2.0.2
	 INTEGER
      }

lntPortType OBJECT-TYPE
      SYNTAX  INTEGER {
	  unknownPort(0),
	  le10bPort(1),
	  le10cPort(2),
	  le15Port(3),
	  le20Port(4),
	  le30xPort(5),
	  le30xdPort(6),
	  le40xPort(7),
	  le40xtPort(8),
          le80xtPort(27),
          le140xtPort(28),
          ielb-AUIPort(29),
          ielb-10btPort(30),
          le20rPort(35),        -- 2.0.2
          le10bnPort(40)        -- 2.0.2 for 'le10b2n' group
	}
      ACCESS  read-only
      STATUS  mandatory
      DESCRIPTION
      "Attribute describing the type of LANNET port."
      ::= { lntPortTable 1 }

lntPortJabber OBJECT-TYPE 
      SYNTAX  INTEGER {
	off(0),
	on(1)
      }
      ACCESS  read-only
      STATUS  mandatory
      DESCRIPTION
      "Value ON of this attribute reflects jabber transmitted to the port by 
      the hardware of a LANNET repeater or transceiver, as a result of 
      collisions detected on the port. Valid for all modules in the LE-10 and
      LE-15 families."
      ::= { lntPortTable 2 }

lntPortNoAUILoop OBJECT-TYPE
      SYNTAX  INTEGER {
	off(0),
	on(1)
      }
      ACCESS  read-only
      STATUS  mandatory
      DESCRIPTION
      "Value ON of this attribute indicates that a No AUI Loop fault condition
      was detected on an AUI repeater port. Valid for LE-10C family of modu-
      les."
      ::= { lntPortTable 3 }

lntPortFunctionalStatus OBJECT-TYPE
      SYNTAX  INTEGER {
	ok(0),
	rld(1),            -- RxLinkDown
	localJabber(2),
	tld(3),            -- TxLinkDown
	remoteJabber(4),
	illSeq(5),
	shortCirq(6)
      }
      ACCESS  read-only
      STATUS  mandatory
      DESCRIPTION
      "The value of this attribute reflects the functional status of LANNET
      synchronous ports. Note that it is not mandatory that all ports
      support all the enumerated states. Here is the minimal set possible
      states:
      OK - fully functional port, transmitting and receiving packets.
      RLD - receive link down condition on the port.
      TLD - transmit link down condition on the port.
      LocalJabber - fault condition indicating that the port emitted jabber.
      RemoteJabber - fault condition indicating that remote jabber was sensed 
      at the port.
      IllSeq - Fault condition indicating an illegal synchronization sequence
      at the port.
      ShortCircuit - short-circuit fault condition detected at the port."
      ::= { lntPortTable 4 }

lntPortManPart OBJECT-TYPE -- Manual partition valid for:
			   -- LE-10C  LE-10B
      SYNTAX  INTEGER {
	off(0),
	on(1)
      }
      ACCESS  read-write
      STATUS  mandatory
      DESCRIPTION
      "Setting to the value of this attribute to ON activates the manual  
      partition mechanism at the port  level. Setting the value of this   
      attribute to OFF cancels the partition sechanism. The segment  
       may reconnect after the reception of 32 packets. Attribute vaild
       for repeater modules from the LE-10 family."
        ::= { lntPortTable 5 } 

lntPortLinkTest OBJECT-TYPE  
      SYNTAX  INTEGER {
	off(0),
	on(1)
      }
      ACCESS  read-write
      STATUS  obsolete
      ::= { lntPortTable 6 }

lntPortPeer OBJECT-TYPE   -- Peer state valid for LE-40XT only.
      SYNTAX  INTEGER {
	noPeer(0),
	xcvrOn(1),
	xcvrOff(2),
	hubOn(3),
	hubOff(4),
	notAvailable(5)
      }
      ACCESS  read-only
      STATUS  obsolete
      ::= { lntPortTable 7 }

lntPortAgent OBJECT-TYPE
      SYNTAX  INTEGER {
	none(0),
	exist(1)
      }
      ACCESS  read-only
      STATUS  obsolete 
      ::= { lntPortTable 8 }

lntPortAgentAddr OBJECT-TYPE
      SYNTAX  IpAddress
      ACCESS  read-only
      STATUS  obsolete 
      ::= { lntPortTable 9 }

lntPortActivityStatus OBJECT-TYPE         -- NEW
      SYNTAX  INTEGER {
	notActive(1),
	dormant(2),
	active(3)
      }
      ACCESS  read-only
      STATUS  mandatory
      DESCRIPTION
      "This attribute defines the status of ports that may be part of a redundan-
      cy scheme. 
      NotActive - indicates a disabled port which cannot transmit or receive pac-
      kets even if included in a redundancy scheme.
      Dormant - indicates an enabled port which does not transmit or receive pac-
      kets, but because it is included in a redundancy scheme, it may at any moment  
      become responsible packet transmission and reception.
      Active - indicates that the port transmits and receives packets, serving as the 
      main path in the redundant configuration."
      ::= { lntPortTable 10 }

lntPortGroupId  OBJECT-TYPE                    -- NEW
      SYNTAX  INTEGER
      ACCESS  read-only
      STATUS  mandatory
      DESCRIPTION
      "Id of the group to which the port belongs."
      ::= { lntPortTable 11 }

lntPortId  OBJECT-TYPE                       -- NEW
      SYNTAX  INTEGER
      ACCESS  read-only
      STATUS  mandatory
      DESCRIPTION
      "Unique Id of the port in the lntPortTable."
      ::= { lntPortTable 12 }


lntPortDescr  OBJECT-TYPE
      SYNTAX  OCTET STRING
      ACCESS  read-only
      STATUS  mandatory
     DESCRIPTION
     "Descriptor of the port in ASCII (readable) format, mainly for use with
     generic management applications."
      ::= { lntPortTable 13 }

lntPortIntPortConnection OBJECT-TYPE  
      SYNTAX  INTEGER (0..255)
      ACCESS  read-write
      STATUS  mandatory
     DESCRIPTION
     "The value of this attribute defines the internal port to which the port
     is connected."
     ::= { lntPortTable 14 }



lntIntPortTable OBJECT-TYPE                       -- NEW
      SYNTAX  SEQUENCE OF LntIntPortEntry
      ACCESS  not-accessible
      STATUS mandatory
      ::= { lntSpecific 8 }

lntIntPortEntry OBJECT-TYPE
      SYNTAX  LntIntPortEntry
      ACCESS  not-accessible
      STATUS  mandatory
      ::= { lntIntPortTable 1 }

LntIntPortEntry ::=
   SEQUENCE {
      lntIntPortGroupId                           -- NEW
         INTEGER,
      lntIntPortId                                -- NEW
         INTEGER,
      lntIntPortAdminStatus                       -- NEW
         INTEGER,
      lntIntPortActivityStatus                    -- NEW
         INTEGER,
      lntIntPortPartition                         -- NEW
         INTEGER,
      lntIntPortBusConnection                      -- NEW
         INTEGER
      }

lntIntPortGroupId  OBJECT-TYPE
      SYNTAX  INTEGER (0..255)
      ACCESS  read-only
      STATUS  mandatory
      DESCRIPTION
      "ID of the group to which the internal port belongs."
      ::= { lntIntPortEntry 1 }

lntIntPortId OBJECT-TYPE
      SYNTAX  INTEGER (0..255)
      ACCESS  read-only
      STATUS  mandatory
      DESCRIPTION
      "ID of the internal port in the lntPortTable."
      ::= { lntIntPortEntry 2 }

lntIntPortAdminStatus OBJECT-TYPE  
      SYNTAX  INTEGER {
	disabled(0),
	enabled(1)
      }
      ACCESS  read-write
      STATUS  mandatory
      DESCRIPTION
      "A disabled internal port neither transmits or receives. The port must be
      explicitly enabled to restore operation." 
      ::= { lntIntPortEntry 3 }

lntIntPortActivityStatus OBJECT-TYPE  
      SYNTAX  INTEGER {
	notActive(1),
	dormant(2),
	active(3)
      }
      ACCESS  read-only
      STATUS  mandatory
      DESCRIPTION
      "This attribute defines the status of internal ports that may be part of a
      redundancy scheme. 
      NotActive - indicates a disabled port which cannot transmit or receive pac-
      kets even if included in a redundancy scheme.
      Dormant - indicates an enabled port which does not transmit or receive pac-
      kets, but because it is included in a redundancy scheme, it may at any moment 
      become responsible for packet transmission and reception.
      Active - indicates that the port transmits and receives packets, serving as the 
      main path in the redundant configuration."
      ::= { lntIntPortEntry 4 }

lntIntPortPartition OBJECT-TYPE 
      SYNTAX  INTEGER {
        off(0),
	on(1) 
      }
      ACCESS  read-only
      STATUS  mandatory
     DESCRIPTION
     "This condition indicates that the internal port is currently partitioned 
     from the bus by the auto-partition protection mechanism." 
     ::= { lntIntPortEntry 5 }

lntIntPortBusConnection OBJECT-TYPE  
      SYNTAX  INTEGER (0..255)
      ACCESS  read-write
      STATUS  mandatory
     DESCRIPTION
     "The value of this attribute defines the bus to which the internal port
     is connected. Internal Ethernet buses are numbered 1 and 2 in LET-18 
     enclosures and 1 to 4 in LET-36 enclosures."
     ::= { lntIntPortEntry 6 }



trSpecific OBJECT IDENTIFIER ::= { lannet 3 } -- Specific Token Ring  Tree

--
--		 Token Ring Group Definition
--


trGroupTable OBJECT-TYPE
      SYNTAX SEQUENCE OF TRGroupEntry
      ACCESS not-accessible
      STATUS mandatory 
      ::= { trSpecific 1 }

-- tRGroupEntry OBJECT-TYPE
--      SYNTAX TRGroupEntry
--      ACCESS not-accessible
--      STATUS mandatory 
--      ::= { trGroupTable 1 }

TRGroupEntry ::= SEQUENCE {
      trGroupID
         INTEGER,
      trGroupNumberOfPorts
         INTEGER,
      trGroupAutoMan
         INTEGER,
      trGroupReset
         INTEGER,
      trGroupHWVersion
         OCTET STRING,
      trGroupSWVersion
         OCTET STRING,
      trGroupKernelVersion
         OCTET STRING,
      trGroupType
         INTEGER,
      trGroupFullConfig
         OCTET STRING,
      trGroupAutoRightLoop
         INTEGER,
      trGroupAutoLeftLoop
         INTEGER,
      trGroupManRightLoop
         INTEGER,
      trGroupManLeftLoop
         INTEGER,
      trGroupRightNeigbour
         INTEGER,
      trGroupLeftNeigbour
         INTEGER,
      trGroupIoMode
         INTEGER,
      trGroupRingSpeed           -- NEW
         INTEGER,
      trGroupTxLinkDown          -- NEW
         INTEGER,
      trGroupRxLinkDown           -- NEW
         INTEGER,
      trGroupManLinkLoop           -- NEW
         INTEGER,
      trGroupManBusLoop           -- NEW
         INTEGER,
      trGroupAutoLinkLoop           -- NEW
         INTEGER,
      trGroupAutoBusLoop           -- NEW
         INTEGER,
      trGroupIOModeF               -- NEW
         INTEGER,
      trGroupDescr                 -- NEW
	 OCTET STRING,
      trGroupAgentIfType           -- 2.0.2
         INTEGER,
      trGroupAgentAddress          -- 2.0.2
         OCTET STRING (SIZE (0..15)),       
      trGroupSecondRingSpeed       -- 2.0.2
         INTEGER,
      trGroupBridgeMode            -- 2.0.2
         INTEGER,
      trGroupFirstRingInserted     -- 2.0.2
         INTEGER,
      trGroupSecondRingInserted    -- 2.0.2
         INTEGER,
      trGroupStandAloneModeSwitch  -- 2.0.2
         INTEGER,
      trGroupRedun12              -- 2.0.2
         INTEGER,
      trGroupRedun34               -- 2.0.2
         INTEGER,
      trGroupSuperRedundancy       -- 2.0.2
         INTEGER,
      trGroupInterProcCommStatus   -- 2.0.2
         INTEGER,    
      trGroupCommunicationStatus   -- 2.0.2
         INTEGER,
      trGroupHardwareStatus        -- 2.0.2
         INTEGER
      }      				     

trGroupID OBJECT-TYPE  
      SYNTAX  INTEGER         
      ACCESS  read-only
      STATUS  mandatory
      DESCRIPTION
      "Unique ID of the group in trGroupTable. Equivalent to slot number in 
      LANNET enclosures."
      ::= { trGroupTable 1 }


trGroupNumberOfPorts OBJECT-TYPE
      SYNTAX  INTEGER    
      ACCESS  read-only
      STATUS  mandatory
      DESCRIPTION
      "Number of ports in group. Range 1..255. It is assumed that on 
      each group the ports are assigned unique numbers in the range from 1 to
      TRGroupNumberOfPorts. They correspond to the number of ports on the
      module (FRU)"
      ::= { trGroupTable 2 }


trGroupAutoMan OBJECT-TYPE 
      SYNTAX  INTEGER {
	man(0),		  
	auto(1)		 
      }
      ACCESS  read-only
      STATUS  mandatory
      DESCRIPTION
      "This attribute reflects the status of the Auto/Manual switch which defines
      the working mode of LANNET sensors. In the MANUAL mode no set
      operations may be performed on attributes related to the sensor. The  
      sensor works according to configuration switches set by hardware and  
      transmits all configuration information to the agent. In the AUTO mode,   
      hardware switches are overridden by set commands."
      ::= { trGroupTable 3 }


trGroupReset OBJECT-TYPE   
      SYNTAX  INTEGER {  
	off(0),
	on(1)	
      }
      ACCESS  read-write    
      STATUS  mandatory
      DESCRIPTION
      "Setting the value of this attribute to ON is interpreted as a software
      RESET command. Sensor software is reinitialised and acording to the 
      sensor specifications, partial or total reset of the module hardware may
      be performed."
      ::= { trGroupTable 4 }

trGroupHWVersion OBJECT-TYPE
      SYNTAX  OCTET STRING
      ACCESS  read-only
      STATUS  mandatory
      DESCRIPTION
      "ASCII string for description and display of the sensor hardware version,
      as it is known to the agent software."
      ::= { trGroupTable 5 }

trGroupSWVersion OBJECT-TYPE
      SYNTAX  OCTET STRING
      ACCESS  read-only
      STATUS  mandatory
      DESCRIPTION
      "ASCII string for description and display of the sensor application soft-
      ware version. "
      ::= { trGroupTable 6 }

trGroupKernelVersion OBJECT-TYPE
      SYNTAX  OCTET STRING
      ACCESS  read-only
      STATUS  mandatory
      DESCRIPTION
"ASCII string for description and display of the sensor kernel software
version."
::= { trGroupTable 7 }

trGroupType OBJECT-TYPE
      SYNTAX  INTEGER {
	  ltr4-RJ45(13),
	  ltr4-D9(14),
          ltr4-D25(15),
          ltr4-FO(16),
          ltrio-RJ45(19),
          ltrio-D9(20),
          ltrio-D25(21),
          ltrio-FO(22),
          ltrio-Con1(23),
	  ltrio-Con2(24),
          ltrf4(30),       -- NEW TYPE
          ltrf16(31),      -- NEW TYPE
          ltr104-RJ45(34), -- 2.0.2
          ltr104-D9(39),   -- 2.0.2
          ltr104-D25(40),  -- 2.0.2
          ltrt-RJ45(41),   -- 2.0.2          
          ltrt-D9(42),     -- 2.0.2
          ltr104f(43),     -- 2.0.2
          itlb(44)         -- 2.0.2
	}
      ACCESS  read-only
      STATUS  mandatory
      DESCRIPTION
      "Attribute describing the type of LANNET token ring group."
      ::= { trGroupTable 8 }

trGroupFullConfig OBJECT-TYPE   
      SYNTAX  OCTET STRING
      ACCESS  read-only
      STATUS  mandatory
     DESCRIPTION
     "Attribute describing the full configuration of a token ring group in in-
     ternal LANNET application format."
      ::= { trGroupTable 9 }

trGroupAutoRightLoop OBJECT-TYPE 
      SYNTAX  INTEGER {
	off(0),
	on(1)
      }
      ACCESS  read-only
      STATUS  mandatory
     DESCRIPTION
     "Value ON of this attribute signifies that a hardware loop was 
      automatically created on a Token Ring module which does not sense 
      the existence of another token ring group on the right hand side."
      ::= { trGroupTable 10 }

trGroupAutoLeftLoop OBJECT-TYPE 
      SYNTAX  INTEGER {
	off(0),
	on(1)
      }
      ACCESS  read-only
      STATUS  mandatory
     DESCRIPTION
     "Value ON of this attribute signifies that a hardware loop was 
      automatically created on a Token Ring module which does not sense 
      the existence of another token ring group on the left hand side."
      ::= { trGroupTable 11 }

trGroupManRightloop OBJECT-TYPE 
      SYNTAX  INTEGER {
	off(0),
	on(1)
      }
      ACCESS  read-write
      STATUS  mandatory
     DESCRIPTION
     "Setting this attribute to ON signifies a command to the hardware 
     to create a loop on the Token Ring module which isolates the ring
     from the right hand side."
      ::= { trGroupTable 12 }

trGroupManLeftLoop OBJECT-TYPE 
      SYNTAX  INTEGER {
	off(0),
	on(1)
      }
      ACCESS  read-write
      STATUS  mandatory
     DESCRIPTION
     "Setting this attribute to ON signifies a command to the hardware 
     to create a loop on the Token Ring module which isolates the ring
     from the left hand side."
      ::= { trGroupTable 13 }


trGroupRightNeigbour OBJECT-TYPE 
      SYNTAX  INTEGER {
	   notExist(0),
	   exist(1)
      }
      ACCESS  read-only
      STATUS  mandatory
      DESCRIPTION
      "Attribute defining the existence of a neighbor another token ring   
      group on the right hand side of the module."
      ::= { trGroupTable 14 }

trGroupLeftNeigbour OBJECT-TYPE 
      SYNTAX  INTEGER {
	   notExist(0),
	   exist(1)
      }
      ACCESS  read-only
      STATUS  mandatory
      DESCRIPTION
      "Attribute defining the existence of a neighbor another token ring  
      group on the left hand side of the module."
      ::= { trGroupTable 15 }


trGroupIoMode OBJECT-TYPE 
      SYNTAX  INTEGER {
 		single(0),
		dualRingIn(1),
 		dualRingOut(2),
 		lobe(4),
 		intRepeater(5),
 		star(6)
      }
      ACCESS  read-write
      STATUS  mandatory
      DESCRIPTION
      "Attribute defining the I/O mode (single, dual-ring-in, dual-ring-out) 
      Lobe, Internal Repeater or Star) of a module from the the LTR-IO family."
      ::= { trGroupTable 16 }

trGroupRingSpeed OBJECT-TYPE                      
      SYNTAX  INTEGER {
                unknown(1),
		oneMegabit(2),
		fourMegabit(3),
		sixteenMegabit(4)
      }
      ACCESS  read-write
      STATUS  mandatory
      DESCRIPTION
      "Attribute describing the bandwidth of the ring. In case of bridges it 
      describes the speed of the first ring."
      ::= { trGroupTable 17 }

trGroupTxLinkDown OBJECT-TYPE 
      SYNTAX  INTEGER {
	off(0),
	on(1)
      }
      ACCESS  read-only 
      STATUS  mandatory
      DESCRIPTION
      "Value ON of this attribute defines a TxLinkDown fault condition on a 
      LANNET Token Ring repeater module."
      ::= { trGroupTable 18 }

trGroupRxLinkDown OBJECT-TYPE  
      SYNTAX  INTEGER {
	off(0),
	on(1)
      }
      ACCESS  read-only 
      STATUS  mandatory
      DESCRIPTION
      "Value ON of this attribute defines an RxLinkDown fault condition on a 
      LANNET Token Ring repeater module."
      ::= { trGroupTable 19 }

trGroupManLinkLoop OBJECT-TYPE
      SYNTAX  INTEGER {
	off(0),
	on(1)
      }
      ACCESS  read-write
      STATUS  mandatory
      DESCRIPTION
      "Setting the value of this attribute to ON instructs the
      hardware of a LANNET Token Ring repeater module to close the loop in the 
      direction of the external connection."
      ::= { trGroupTable 20 }

trGroupManBusLoop OBJECT-TYPE 
      SYNTAX  INTEGER {
	off(0),
	on(1)
      }
      ACCESS  read-write
      STATUS  mandatory
      DESCRIPTION
      "Setting the value of this attribute to ON instructs the
      hardware of a LANNET Token Ring repeater module to close the loop in the 
      direction of the internal bus."
      ::= { trGroupTable 21 }

trGroupAutoLinkLoop OBJECT-TYPE -- Link loop request
      SYNTAX  INTEGER {
	off(0),
	on(1)
      }
      ACCESS  read-only 
      STATUS  mandatory
      DESCRIPTION
      "Value ON of this attribute signifies that a hardware loop has been auto-
      matically closed by the hardwar of the LANNET Token Ring repeater
      as a result of problems on the external link." 
      ::= { trGroupTable 22 }

trGroupAutoBusLoop OBJECT-TYPE -- Bus loop request
      SYNTAX  INTEGER {
	off(0),
	on(1)
      }
      ACCESS  read-only 
      STATUS  mandatory
      DESCRIPTION
      "Value ON of this attribute signifies that a hardware loop has been auto-
      matically closed by the hardware of the LANNET Token Ring repeater
      as a result of problems on the internal bus." 
      ::= { trGroupTable 23 }

trGroupIOModeF OBJECT-TYPE -- IO mode for LTRF
      SYNTAX  INTEGER {
		ringIn(1),
 		ringOut(2),
        illegalMode(3)
      }
      ACCESS  read-only 
      STATUS  mandatory
      DESCRIPTION
      "Attribute defining the I/O mode (Ring-in, Ring-out) of a LANNET Token Ring
      repeater."
      ::= { trGroupTable 24 }


trGroupDescr  OBJECT-TYPE
      SYNTAX  OCTET STRING
      ACCESS  read-only
      STATUS  mandatory
     DESCRIPTION
     "Descriptor of the group in ASCII (readable) format, mainly for use with
     generic management applications."
      ::= { trGroupTable 25 }

trGroupAgentIfType OBJECT-TYPE  
      SYNTAX  INTEGER {
	      none(1),
	      regular1822(2),
	      hdh1822(3),
	      ddn-x25(4),
	      rfc877-x25(5),
	      ethernet-csmacd(6),
	      iso88023-csmacd(7),
	      iso88024-tokenBus(8),
	      iso88025-tokenRing(9),
	      iso88026-man(10),
	      starLan(11),
	      proteon-10MBit(12),
	      proteon-80MBit(13),
	      hyperchannel(14),
	      fddi(15),
	      lapb(16),
	      sdlc(17),
	      t1-carrier(18),
	      cept(19),
	      basicIsdn(20),
	      primaryIsdn(21),
	      propPointToPointSerial(22),    -- proprietary serial
	      ppp(23),
	      softwareLoopback(24),
	      eon(25),                       -- CLNP over IP
	      ethernet-3Mbit(26),
	      nsip(27),                      -- XNS over IP
	      slip(28),                      -- generic SLIP
	      ip(255)
      }
      ACCESS  read-only 
      STATUS  mandatory
     DESCRIPTION
     "This attribute describes the interfaces of agents eventually existing on
     LANNET modules and their type. Value none defines the lack of agent or of
     an interface recognized by the management console, while any other value
     defines an interface whose type is recognized by the the management console
     and may be used as a management channel."
      ::= { trGroupTable 26 }

trGroupAgentAddress OBJECT-TYPE  
      SYNTAX  OCTET STRING -- (SIZE (0..15)) 
      ACCESS  read-only                   
      STATUS  mandatory
     DESCRIPTION
     "This attribute defines an unique address by which the agent may be addres-
     sed by the management console. The address format should be consistent with
     the type defined by trGroupAgentIfType." 
      ::= { trGroupTable 27 }

trGroupSecondRingSpeed OBJECT-TYPE                      
      SYNTAX  INTEGER {
                unknown(1),
		oneMegabit(2),
		fourMegabit(3),
		sixteenMegabit(4)
      }
      ACCESS  read-write
      STATUS  mandatory
      DESCRIPTION
      "Attribute describing bandwidth of the ring. In case of bridges it 
      describes the speed of the second ring."
      ::= { trGroupTable 28 }

trGroupBridgeMode OBJECT-TYPE                      
      SYNTAX  INTEGER {
                modeA(1),
		modeB(2),
		modeC(3)
      }
      ACCESS  read-write
      STATUS  mandatory
      DESCRIPTION
      "Attribute describing the operational mode of the bridge.
       For ITLB the following modes are defined:
       - Mode A: First channel connected to an external ring (RI,RO connectors)
      and second channel connected to an internal ring;
       - Mode B: First channel connected to an external ring by a DTE connector
      and second channel connected to an internal ring;
       - Mode C: First channel connected to an internal left ring and second 
      channel connected to an internal right ring."
      ::= { trGroupTable 29 }

trGroupFirstRingInserted OBJECT-TYPE
      SYNTAX  INTEGER {
                notInserted(1),
                inserted(2)
      }
      ACCESS  read-only 
      STATUS  mandatory
      DESCRIPTION
      "Attribute describing that the first ring in the case of a bridge
      requires or not insertion."
      ::= { trGroupTable 30 }

trGroupSecondRingInserted OBJECT-TYPE
      SYNTAX  INTEGER {
                notInserted(1),
                inserted(2)
      }
      ACCESS  read-only 
      STATUS  mandatory
      DESCRIPTION
      "Attribute describing that the second ring in the case of a bridge
      requires or not insertion."
      ::= { trGroupTable 31 }

trGroupStandAloneModeSwitch OBJECT-TYPE 
      SYNTAX  INTEGER {
	off(0),
	on(1)
	}
      ACCESS read-write
      STATUS mandatory
     DESCRIPTION
     "Value On of this attribute defines Stand Alone Mode of a sensor. Internal
     ports are disabled and the card functions in a local star configuration to-
     ward its external ports."
      ::= { trGroupTable 32 }
				     
trGroupRedun12 OBJECT-TYPE
      SYNTAX  INTEGER {
	off(0),
	on(1)
      }
      ACCESS  read-write
      STATUS  mandatory
     DESCRIPTION
     "Value ON of this attribute defines a redundancy (back-up) relation between
     synchronous external ports 1 and 2 on a LANNET module."
      ::= { trGroupTable 33 }

trGroupRedun34 OBJECT-TYPE 
      SYNTAX  INTEGER {
	off(0),
	on(1)
      }
      ACCESS  read-write
      STATUS  mandatory
     DESCRIPTION
     "Value ON of this attribute defines a redundancy (back-up) relation between
     synchronous external ports 3 and 4 on a LANNET module."
      ::= { trGroupTable 34 }

trGroupSuperRedundancy OBJECT-TYPE 
      SYNTAX  INTEGER {
	off(0),
	on(1)
      }
      ACCESS  read-write
      STATUS  mandatory
     DESCRIPTION
     "Value ON of this attribute defines a redundancy (back-up) relation between
     all the internal ports on a LANNET module. By default port 1 is active, 
     backed by port 2, backed by port 3 (if existing), etc."
      ::= { trGroupTable 35 }

trGroupInterProcCommStatus OBJECT-TYPE  
      SYNTAX  INTEGER {
              ok(1),
              commProblems(2),
              noCommunication(3)
      }
      ACCESS  read-only                   
      STATUS  mandatory
     DESCRIPTION
     "This attribute describes the status of the communication between the
     microprocessor of the sensor and the microprocessor of the agent on cards
     with embedded agents." 
      ::= { trGroupTable 36 }

trGroupCommunicationStatus OBJECT-TYPE  
      SYNTAX  INTEGER {
              ok(1),
              commProblems(2)
      }
      ACCESS  read-only
      STATUS  mandatory
     DESCRIPTION
     "This attribute describes the communication status of the group with
     the SNMP Agent as detected and reported by the agent."
      ::= { trGroupTable 37 }
      
trGroupHardwareStatus OBJECT-TYPE  
      SYNTAX  INTEGER {
              ok(1),
              hardwareProblems(2)
      }
      ACCESS  read-only
      STATUS  mandatory
     DESCRIPTION
     "This attribute describes the status of the group hardware as detected
     by the sensors software."
           ::= { lntGroupTable 38 }
      
 
 
trPortTable OBJECT-TYPE
      SYNTAX SEQUENCE OF TRPortEntry
      ACCESS not-accessible
      STATUS mandatory 
      ::= { trSpecific 2 }

-- tRPortEntry OBJECT-TYPE
--      SYNTAX  TRPortEntry
--      ACCESS  not-accessible
--      STATUS  mandatory
--      ::= { trPortTable 1 }

TRPortEntry ::= SEQUENCE {
      trPortType
         INTEGER,
      trPortID
         INTEGER,
      trPortBypass
         INTEGER,
      trPortConnected
         INTEGER,
      trPortTcp
         INTEGER,
      trPortCableFault
         INTEGER,
      trPortGroupID         -- NEW
         INTEGER,
      trPortDescr           -- NEW
	 OCTET STRING,
      trPortFunctionalStatus -- 2.0.2
         INTEGER,
      trPortActivityStatus  -- 2.0.2
         INTEGER
      }

trPortType OBJECT-TYPE
      SYNTAX  INTEGER {
      lobeRJ45(9),             
	  lobeD9(10),
      lobeD25(11),
	  lobeFO(12),
      ri104D25(13),
	  ro104D25(14),
      riRJ45(15),
	  riD9(16),
      riD25(17),
	  riFO(18),
      ri104RJ45(19),
	  ri104D9(20),
      roRJ45(21),
	  roD9(22),
      roD25(23),
	  roFO(24),
	  ro104RJ45(25),
      ro104D9(26),
          ltrf4Port(31),      -- NEW
      ltrf16Port(32),         -- NEW
          itlbRoPort(36),     -- 2.0.2
      itlbRiPort(37),         -- 2.0.2
          itlbDTEPort(38),    -- 2.0.2
      starFO(39)              -- 2.0.2
	}
      ACCESS  read-only
      STATUS  mandatory
      DESCRIPTION
      "Attribute describing the type of Token Ring LANNET port."
      ::= { trPortTable 1 }

trPortID OBJECT-TYPE   
      SYNTAX  INTEGER
      ACCESS  read-only
      STATUS  mandatory
      DESCRIPTION
      "Unique ID of the port in the trPortTable."
      ::= { trPortTable 2 }

trPortBypass OBJECT-TYPE   
      SYNTAX  INTEGER {  
	  off(0),
	  on(1)
      }
      ACCESS  read-write
      STATUS  mandatory
      DESCRIPTION
      "Setting the value of this attribute to ON causes the by-
      passing of the TokenRing LANNET port."
      ::= { trPortTable 3 }

trPortConnected OBJECT-TYPE   
      SYNTAX  INTEGER {  
	  notConnected(0),
	  connected(1)
      }
      ACCESS  read-only
      STATUS  mandatory
      DESCRIPTION
      "Attribute which describes the connection status of a Token Ring port (in-
      clusion of the Token Ring controller in the ring)."
      ::= { trPortTable 4 }

trPortTcp OBJECT-TYPE  
      SYNTAX  INTEGER {  
	  off(0),
	  on(1)
      }
      ACCESS  read-write
      STATUS  mandatory
      DESCRIPTION
      "Setting the value of this attribute to ON causes the activation of the
      cable-fault detection mechanism."
      ::= { trPortTable 5 }

trPortCableFault OBJECT-TYPE 
      SYNTAX  INTEGER {
		off(0),
		on(1)
	  }
      ACCESS  read-only
      STATUS  mandatory
      DESCRIPTION
      "Value ON of this attribute signifies the detection of a cable-fault on
      this specific Token Ring port."
      ::= { trPortTable 6 }

trPortGroupID OBJECT-TYPE
      SYNTAX  INTEGER
      ACCESS  read-only
      STATUS  mandatory
      DESCRIPTION
      "ID of group to which the Token Ring port belongs."
      ::= { trPortTable 7 }


trPortDescr  OBJECT-TYPE
      SYNTAX  OCTET STRING
      ACCESS  read-only
      STATUS  mandatory
     DESCRIPTION
     "Descriptor of the group in ASCII (readable) format, mainly for use with
     generic management applications."
      ::= { trPortTable 8 }

trPortFunctionalStatus OBJECT-TYPE
      SYNTAX  INTEGER {
	ok(0),
	rld(1),            -- RxLinkDown
	tld(3)            -- TxLinkDown
      }
      ACCESS  read-only
      STATUS  mandatory
      DESCRIPTION
      "The value of this attribute reflects the functional status of LANNET
      Token Ring ports. Note that it is not mandatory that a certain port
      support all the enumerated states. Here is the lest of the possible
      states:
      OK - fully functional port, transmitting and receiving packets.
      RLD - receive link down condition on the port.
      TLD - transmit link down condition on the port."
      ::= { trPortTable 9 }

trPortActivityStatus OBJECT-TYPE 
      SYNTAX  INTEGER {
	notActive(1),
	dormant(2),
	active(3)
      }
      ACCESS  read-only
      STATUS  mandatory
      DESCRIPTION
      "This attribute defines the status of ports who may be part of a redundan-
      cy schema. 
      NotActive indicates a disabled port which cannot transmit or receive pac-
      kets even if included in a redundancy scheme.
      Dormant indicates an enabled port which does not transmit or receive pac-
      kets, but included in a redundancy schema is at any moment disponible for
      packets transmission and reception.
      Active indicates that the port transmits and receives packets, as the 
      main path in the redundant configuration."
      ::= { trPortTable 10 }


trIntPortTable OBJECT-TYPE                       -- 2.0.2
      SYNTAX  SEQUENCE OF TrIntPortEntry
      ACCESS  not-accessible
      STATUS mandatory
      ::= { trSpecific 3 }

trIntPortEntry OBJECT-TYPE
      SYNTAX  TrIntPortEntry
      ACCESS  not-accessible
      STATUS  mandatory
      ::= { trIntPortTable 1 }

TrIntPortEntry ::=
   SEQUENCE {
      trIntPortGroupId                           -- 2.0.2
         INTEGER,
      trIntPortId                                -- 2.0.2
         INTEGER,
      trIntPortBusConnection                     -- 2.0.2
         INTEGER,
      trIntPortAdminStatus                       -- 2.0.2
         INTEGER   
      }

trIntPortGroupId  OBJECT-TYPE
      SYNTAX  INTEGER (0..255)
      ACCESS  read-only
      STATUS  mandatory
      DESCRIPTION
      "Id of the group to which the internal port belongs."
      ::= { trIntPortEntry 1 }

trIntPortId OBJECT-TYPE
      SYNTAX  INTEGER (0..255)
      ACCESS  read-only
      STATUS  mandatory
      DESCRIPTION
      "Id of the internal port in the trInPortTable."
      ::= { trIntPortEntry 2 }

trIntPortBusConnection OBJECT-TYPE  
      SYNTAX  INTEGER (0..255)
      ACCESS  read-write
      STATUS  mandatory
     DESCRIPTION
     "The value of this attribute defines the bus to which the internal port
     is connected. Internal Ethernet buses are numbered 1,2 in LET18 enclosures
     and 1 to 4 in LET36 enclosures."
     ::= { trIntPortEntry 3 }

trIntPortAdminStatus OBJECT-TYPE  
      SYNTAX  INTEGER {
	disabled(0),
	enabled(1)
      }
      ACCESS  read-only
      STATUS  mandatory
      DESCRIPTION
      "A disabled port neither transmits or receives. The port must be
      explicitely enabled to restore operation." 
      ::= { trIntPortEntry 4 }


trRingTable OBJECT-TYPE                       -- 2.0.2
      SYNTAX  SEQUENCE OF TrRingEntry
      ACCESS  not-accessible
      STATUS mandatory
      ::= { trSpecific 4 }

trRingEntry OBJECT-TYPE
      SYNTAX  TrRingEntry
      ACCESS  not-accessible
      STATUS  mandatory
      ::= { trRingTable 1 }

TrRingEntry ::=
   SEQUENCE {
      trRingIndex                                -- 2.0.2
         INTEGER,
      trRingCurTraffic                           -- 2.0.2
         OCTET STRING,
      trRingTrafficTrsh                          -- 2.0.2
           INTEGER,
      trRingPeakTraffic                          -- 2.0.2
           INTEGER
      }

trRingIndex OBJECT-TYPE
      SYNTAX  INTEGER (0..255)
      ACCESS  read-only
      STATUS  mandatory
      DESCRIPTION
      "Id of the ring in the trRingTable."
      ::= { trRingEntry 1 }

trRingCurTraffic OBJECT-TYPE 
      SYNTAX  OCTET STRING	  
      ACCESS  read-only
      STATUS  mandatory
      DESCRIPTION
      "Record of traffic for the last second with a resolution of 100 msec. 
      The traffic is expressed in percents of the maximum effective TR traffic 
      (token messages are excluded) and each record contains 10 readings,
      in range 1..20 on log(10) scale."
      ::= { trRingEntry 2 }

trRingTrafficTrsh OBJECT-TYPE 
      SYNTAX  INTEGER		    
      ACCESS  read-write
      STATUS  mandatory
      DESCRIPTION
      "Traffic threshold value. When exceeded, a trap is send to the management
      console. Expressed in percents of the maximum effective TR traffic 
      (token messages are excluded) in the range 1..20 on log(10) scale."
      ::= { trRingEntry 3 }


trRingPeakTraffic OBJECT-TYPE        -- Maximal traffic
      SYNTAX  INTEGER 	  	     -- Values 1..20 (Log(10) scale)
      ACCESS  read-only
      STATUS  mandatory
      DESCRIPTION
      "Maximal traffic value since last reset of agent. Expressed in percents
      of the maximum effective TR traffic (token messages are excluded), in the
      range 1..20 on log(10) scale."
      ::= { trRingEntry 4 }





srlSpecific OBJECT IDENTIFIER ::= { lannet 4 } -- Specific serial tree

--
--		 Serial Group definition
--


srlportTable OBJECT-TYPE
      SYNTAX SEQUENCE OF SRLPortEntry
      ACCESS not-accessible
      STATUS mandatory 
      ::= { srlSpecific 2 }

srlportEntry OBJECT-TYPE
      SYNTAX  SRLPortEntry
      ACCESS  not-accessible
      STATUS  mandatory
      ::= { srlportTable 1 }

SRLPortEntry ::= SEQUENCE {
      srlportGroupID         -- 2.0.2
         INTEGER,
      srlportID             -- 2.0.2
         INTEGER,
      srlportType            -- 2.0.2
         INTEGER,
      srlportAdminStatus     -- 2.0.2
         INTEGER,
      srlportDescr           -- 2.0.2
	 OCTET STRING
      }

srlportGroupID OBJECT-TYPE
      SYNTAX  INTEGER
      ACCESS  read-only
      STATUS  mandatory
      DESCRIPTION
      "ID of group to which the Terminal Server port belongs."
      ::= { srlportEntry 1 }

srlportID OBJECT-TYPE   
      SYNTAX  INTEGER
      ACCESS  read-only
      STATUS  mandatory
      DESCRIPTION
      "Unique Id of the port in the srlportEntry."
      ::= { srlportEntry 2 }

srlportType OBJECT-TYPE
      SYNTAX  INTEGER {
              lts16Port(33)
      }
      ACCESS  read-only
      STATUS  mandatory
      DESCRIPTION
      "Attribute describing the type of the LANNET Terminal Server port."
      ::= { srlportEntry 3 }

srlportAdminStatus OBJECT-TYPE  
      SYNTAX  INTEGER {
	disabled(0),
	enabled(1)
      }
      ACCESS  read-write
      STATUS  mandatory
      DESCRIPTION
      "A disabled port neither transmits or receives. The port must be
      explicitely enabled to restore operation." 
      ::= { srlportEntry 4 }

srlportDescr  OBJECT-TYPE
      SYNTAX  OCTET STRING
      ACCESS  read-only
      STATUS  mandatory
     DESCRIPTION
     "Descriptor of the group in ASCII (readable) format, mainly for use with
     generic management applications."
      ::= { srlportEntry 5 }




ltSpecific OBJECT IDENTIFIER ::= { lannet 5 } -- Specific Local Talk tree

--
--		 Local Talk Group definition
--


ltGroupTable OBJECT-TYPE
      SYNTAX SEQUENCE OF LTGroupEntry
      ACCESS not-accessible
      STATUS mandatory 
      ::= { ltSpecific 1 }

ltGroupEntry OBJECT-TYPE
      SYNTAX LTGroupEntry
      ACCESS not-accessible
      STATUS mandatory 
      ::= { ltGroupTable 1 }

LTGroupEntry ::= SEQUENCE {
      ltGroupID                   -- 2.0.2
         INTEGER,
      ltGroupNumberOfPorts        -- 2.0.2
         INTEGER,
      ltGroupAutoMan             -- 2.0.2
         INTEGER,
      ltGroupReset               -- 2.0.2
         INTEGER,
      ltGroupHWVersion            -- 2.0.2
         OCTET STRING,
      ltGroupSWVersion            -- 2.0.2
         OCTET STRING,
      ltGroupKernelVersion        -- 2.0.2
         OCTET STRING,
      ltGroupType                -- 2.0.2
         INTEGER,
      ltGroupFullConfig           -- 2.0.2
         OCTET STRING,
      ltGroupDescr                -- 2.0.2
	 OCTET STRING,
      ltGroupInterProcCommStatus  -- 2.0.2
         INTEGER,
      ltGroupStandAloneModeSwitch  -- 2.0.2
         INTEGER,
      ltGroupCommunicationStatus   -- 2.0.2
         INTEGER
       }      				     

ltGroupID OBJECT-TYPE  
      SYNTAX  INTEGER         
      ACCESS  read-only
      STATUS  mandatory
      DESCRIPTION
      "Unique ID of the group in ltGroupTable. Equivalent to slot number in 
      LANNET enclosures."
      ::= { ltGroupEntry 1 }

ltGroupNumberOfPorts OBJECT-TYPE
      SYNTAX  INTEGER    
      ACCESS  read-only
      STATUS  mandatory
      DESCRIPTION
      "Number of ports in group. Range 1..255. It is assumed that on 
      each group the ports are numbered uniquely in the range from 1 to
      standardGroupNumberOf Ports. They corespond to the number of ports of the
      module (FRU)"
      ::= { ltGroupEntry 2 }


ltGroupAutoMan OBJECT-TYPE 
      SYNTAX  INTEGER {
	man(0),		  
	auto(1)		 
      }
      ACCESS  read-only
      STATUS  mandatory
      DESCRIPTION
      "This attribute reflects the status of the auto/manual switch which defi-
      nes the working mode of LANNET sensors. On Manual mode no set operations
      may be performed on attributes related to sensor. The sensor works acor-
      ding to configuration switches set by hardware methods and transmits all 
      configuration information to the agent. On Auto mode hardware switches 
      are overridden by set commands."
      ::= { ltGroupEntry 3 }


ltGroupReset OBJECT-TYPE   
      SYNTAX  INTEGER {  
	off(0),
	on(1)	
      }
      ACCESS  read-write    
      STATUS  mandatory
      DESCRIPTION
      "Setting the value of this attribute to ON is interpreted as a software
      RESET command. Sensor software is reinitialised and acording to the 
      sensor specifications, partial or total reset of the module hardware may
      be performed."
      ::= { ltGroupEntry 4 }

ltGroupHWVersion OBJECT-TYPE
      SYNTAX  OCTET STRING
      ACCESS  read-only
      STATUS  mandatory
      DESCRIPTION
      "ASCII string for description and display of the sensor hardware version,
      as it is known by the agent software."
      ::= { ltGroupEntry 5 }

ltGroupSWVersion OBJECT-TYPE
      SYNTAX  OCTET STRING
      ACCESS  read-only
      STATUS  mandatory
      DESCRIPTION
      "ASCII string for description and display of the sensor application soft-
      ware."
      ::= { ltGroupEntry 6 }

ltGroupKernelVersion OBJECT-TYPE
      SYNTAX  OCTET STRING
      ACCESS  read-only
      STATUS  mandatory
      DESCRIPTION
      "ASCII string for description and display of the sensor kernel software."
      ::= { ltGroupEntry 7 }

ltGroupType OBJECT-TYPE
      SYNTAX  INTEGER {
          llt8(36)        -- 2.0.2          
	}
      ACCESS  read-only
      STATUS  mandatory
      DESCRIPTION
      "Attribute describing the type of LANNET Terminal Server group."
      ::= { ltGroupEntry 8 }

ltGroupFullConfig OBJECT-TYPE   
      SYNTAX  OCTET STRING
      ACCESS  read-only
      STATUS  mandatory
     DESCRIPTION
     "Attribute describing the full configuration of a terminal server group 
     in internal LANNET application format."
      ::= { ltGroupEntry 9 }

ltGroupDescr  OBJECT-TYPE
      SYNTAX  OCTET STRING
      ACCESS  read-only
      STATUS  mandatory
     DESCRIPTION
     "Descriptor of the group in ASCII (readable) format, mainly for use with
     generic management applications."
      ::= { ltGroupEntry 10 }

ltGroupInterProcCommStatus OBJECT-TYPE  
      SYNTAX  INTEGER {
              ok(1),
              commProblems(2),
              noCommunication(3)
      }
      ACCESS  read-only                   
      STATUS  mandatory
     DESCRIPTION
     "This attribute describes the status of the communication between the
     microprocessor of the sensor and the microprocessor of the agent on cards
     with embedded agents." 
      ::= { ltGroupEntry 11 }

ltGroupStandAloneModeSwitch OBJECT-TYPE 
      SYNTAX  INTEGER {
	off(0),
	on(1)
	}
      ACCESS read-write
      STATUS mandatory
     DESCRIPTION
     "Value On of this attribute defines Stand Alone Mode of a sensor. Internal
     ports are disabled and the card functions in a local star configuration to-
     ward its external ports."
      ::= { ltGroupEntry 12 }
				     
ltGroupCommunicationStatus OBJECT-TYPE  
      SYNTAX  INTEGER {
              ok(1),
              commProblems(2)
      }
      ACCESS  read-only
      STATUS  mandatory
     DESCRIPTION
     "This attribute describes the communication status of the group with
     the SNMP Agent as detected and reported by the agent."
      ::= { ltGroupEntry 13 }
      



ltPortTable OBJECT-TYPE
      SYNTAX SEQUENCE OF LTPortEntry
      ACCESS not-accessible
      STATUS mandatory 
      ::= { ltSpecific 2 }

ltPortEntry OBJECT-TYPE
      SYNTAX  LTPortEntry
      ACCESS  not-accessible
      STATUS  mandatory
      ::= { ltPortTable 1 }

LTPortEntry ::= SEQUENCE {
      ltPortGroupID         -- 2.0.2
         INTEGER,
      ltPortID             -- 2.0.2
         INTEGER,
      ltPortType            -- 2.0.2
         INTEGER,
      ltPortAdminStatus     -- 2.0.2
         INTEGER,
      ltPortTest            -- 2.0.2
         INTEGER,
      ltPortTestResult      -- 2.0.2
         INTEGER,
      ltPortJam             -- 2.0.2
         INTEGER,
      ltPortDescr           -- 2.0.2
	 OCTET STRING
      }

ltPortGroupID OBJECT-TYPE
      SYNTAX  INTEGER
      ACCESS  read-only
      STATUS  mandatory
      DESCRIPTION
      "ID of group to which the Local Talk card belongs."
      ::= { ltPortEntry 1 }

ltPortID OBJECT-TYPE   
      SYNTAX  INTEGER
      ACCESS  read-only
      STATUS  mandatory
      DESCRIPTION
      "Unique Id of the port in the ltPortEntry."
      ::= { ltPortEntry 2 }

ltPortType OBJECT-TYPE
      SYNTAX  INTEGER {
              llt8Port(34)
      }
      ACCESS  read-only
      STATUS  mandatory
      DESCRIPTION
      "Attribute describing the type of the LANNET Local Talk card port."
      ::= { ltPortEntry 3 }

ltPortAdminStatus OBJECT-TYPE  
      SYNTAX  INTEGER {
	disabled(0),
	enabled(1)
      }
      ACCESS  read-write
      STATUS  mandatory
      DESCRIPTION
      "A disabled port neither transmits or receives. The port must be
      explicitely enabled to restore operation." 
      ::= { ltPortEntry 4 }

ltPortTest OBJECT-TYPE  
      SYNTAX  INTEGER {
	off(0),
	on(1)
      }
      ACCESS  write-only
      STATUS  mandatory
      DESCRIPTION
      "A value ON of this attribute indicates that a port test should be 
      performed upon the port defined be the attribute instance." 
      ::= { ltPortEntry 5 }

ltPortTestResult OBJECT-TYPE  
      SYNTAX  INTEGER {
	ok(1),
	faulty(2)
      }
      ACCESS  read-only
      STATUS  mandatory
      DESCRIPTION
      " Indicates the result of a port test performed on this port." 
      ::= { ltPortEntry 6 }

ltPortJam  OBJECT-TYPE  
      SYNTAX  INTEGER {
	off(0),
	on(1)
      }
      ACCESS  read-only
      STATUS  mandatory
      DESCRIPTION
      "An ON value of this attribute indicates a Jam error on the specific
      port." 
      ::= { ltPortEntry 7 }

ltPortDescr  OBJECT-TYPE
      SYNTAX  OCTET STRING
      ACCESS  read-only
      STATUS  mandatory
     DESCRIPTION
     "Descriptor of the group in ASCII (readable) format, mainly for use with
     generic management applications."
      ::= { ltPortEntry 8 }

ltIntPortTable OBJECT-TYPE                       -- 2.0.2
      SYNTAX  SEQUENCE OF LTIntPortEntry
      ACCESS  not-accessible
      STATUS mandatory
      ::= { ltSpecific 3 }

ltIntPortEntry OBJECT-TYPE
      SYNTAX  LTIntPortEntry
      ACCESS  not-accessible
      STATUS  mandatory
      ::= { ltIntPortTable 1 }

LTIntPortEntry ::=
   SEQUENCE {
      ltIntPortGroupId                           -- 2.0.2
         INTEGER,
      ltIntPortId                                -- 2.0.2
         INTEGER,
      ltIntPortAdminStatus                       -- 2.0.2
         INTEGER,
      ltIntPortBusConnection                     -- 2.0.2
         INTEGER
      }

ltIntPortGroupId  OBJECT-TYPE
      SYNTAX  INTEGER (0..255)
      ACCESS  read-only
      STATUS  mandatory
      DESCRIPTION
      "Id of the group to which the internal port belongs."
      ::= { ltIntPortEntry 1 }

ltIntPortId OBJECT-TYPE
      SYNTAX  INTEGER (0..255)
      ACCESS  read-only
      STATUS  mandatory
      DESCRIPTION
      "Id of the internal port in the ltIntPortTable."
      ::= { ltIntPortEntry 2 }

ltIntPortAdminStatus OBJECT-TYPE  
      SYNTAX  INTEGER {
	disabled(0),
	enabled(1)
      }
      ACCESS  read-only 
      STATUS  mandatory
      DESCRIPTION
      "A disabled internal port neither transmits or receives. The port must be
      explicitely enabled to restore operation." 
      ::= { ltIntPortEntry 3 }

ltIntPortBusConnection OBJECT-TYPE  
      SYNTAX  INTEGER (0..255)
      ACCESS  read-write
      STATUS  mandatory
     DESCRIPTION
     "The value of this attribute defines the bus to which the internal port
     is connected. Local Talk cards inserted in LET18 type enclosures may
     access 2 buses, while Local Talk cards inserted in LET18 type enclosures 
     may access 4 buses."
     ::= { ltIntPortEntry 4 }

END
