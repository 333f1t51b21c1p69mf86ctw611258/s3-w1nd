PDN-ATMEXT-MIB DEFINITIONS ::= BEGIN

	IMPORTS
		MODULE-IDENTITY , OBJECT-TYPE, Integer32,  NOTIFICATION-TYPE
			FROM SNMPv2-SMI
		DisplayString,TruthValue
			FROM SNMPv2-TC
		pdnAtm
			FROM PDN-HEADER-MIB
         ifIndex,ifOperStatus
			FROM IF-MIB
		atmInterfaceConfEntry, atmTrafficDescrParamEntry
			FROM ATM-MIB;

-- ===============================================================
--
--  Extentions to the ATM MIB (RFC 2515)
--
-- ===============================================================

	pdnAtmExtMIB MODULE-IDENTITY
		LAST-UPDATED "0004280000Z"
		ORGANIZATION "Paradyne Networks
					  MIB Working Group"
		CONTACT-INFO
				      "Paradyne Networks
					   331 Newman Springs Road
		               Red Bank, NJ 07701
					   www.paradyne.com

					   General Comments to: mibwg_team@eng.paradyne.com"

		DESCRIPTION
		"This MIB Module extends the ATM-MIB defined in rfc2515"

        REVISION "0004280000Z"
		DESCRIPTION "J. Strain
			o  added the following objects to pdnAtmIfConfExtTable
				o pdnAtmIfConfExtBandwidthUtilCbrReserved
				o pdnAtmIfConfExtBandwidthUtilCbrAssigned
				o pdnAtmIfConfExtBandwidthUtilVbrRtReserved
				o pdnAtmIfConfExtBandwidthUtilVbrRtAssigned
				o pdnAtmIfConfExtBandwidthUtilVbrNrtReserved
				o pdnAtmIfConfExtBandwidthUtilVbrNrtAssigned
				o pdnAtmIfConfExtBandwidthUtilUbrReserved
				o pdnAtmIfConfExtBandwidthUtilUbrAssigned"

        REVISION "0003110000Z"
		DESCRIPTION "P. Easwar
			o  added pdnAtmIfConfExtUnknownCellThreshold
				and pdnAtmIfConfExtOcdEventThreshold"
        REVISION "0002180000Z"
		DESCRIPTION "P. Easwar
			o  Initial Release"

		::= {  pdnAtm 5 }

    pdnAtmExtMIBObjects    OBJECT IDENTIFIER ::= { pdnAtmExtMIB 1 }
    pdnAtmExtMIBTraps      OBJECT IDENTIFIER ::= { pdnAtmExtMIB 2 }
    pdnAtmExtMIBTrapPrefix OBJECT IDENTIFIER ::= { pdnAtmExtMIBTraps 0 }
--	 pdnAtmExtMIBConformance OBJECT IDENTIFIER ::= { pdnAtmExtMIB 3 }
	 

-- ===============================================================
--
--  Extentions to the ATM Interface Config Table (RFC 2515)
--
--  Release: 1.0  02/18/00 (Initial Release) Prakash Easwar
--
--  This MIB is intended to AUGMENT the atmInterfaceConfTable of the ATM-MIB
--

pdnAtmIfConfExtTable OBJECT-TYPE
    SYNTAX  SEQUENCE OF PdnAtmIfConfExtEntry
    MAX-ACCESS  not-accessible
    STATUS  current
    DESCRIPTION
      "The Paradyne Extension to the atmInterfaceConfTable of the ATM-MIB."
    ::= { pdnAtmExtMIBObjects 1   }

pdnAtmIfConfExtEntry OBJECT-TYPE
    SYNTAX  PdnAtmIfConfExtEntry
    MAX-ACCESS  not-accessible
    STATUS  current
    DESCRIPTION
       "An entry in the Paradyne Extension to the atmInterfaceConfTable of 
       the ATM-MIB."
    AUGMENTS { atmInterfaceConfEntry }
    ::= { pdnAtmIfConfExtTable  1 }

PdnAtmIfConfExtEntry ::=
    SEQUENCE {
    
    pdnAtmIfConfExtVbrRtBandwidthUtil
        Integer32,

    pdnAtmIfConfExtVbrNrtBandwidthUtil
        Integer32,
      
    pdnAtmIfConfExtHecErrorThreshold     
        Integer32,

    pdnAtmIfConfExtUnknownCellThreshold
        Integer32,

    pdnAtmIfConfExtOcdEventThreshold
        Integer32,

    pdnAtmIfConfExtBandwidthUtilCbrReserved
        Integer32,

    pdnAtmIfConfExtBandwidthUtilCbrAssigned
        Integer32,

    pdnAtmIfConfExtBandwidthUtilVbrRtReserved
        Integer32,

    pdnAtmIfConfExtBandwidthUtilVbrRtAssigned
        Integer32,

    pdnAtmIfConfExtBandwidthUtilVbrNrtReserved
        Integer32,

    pdnAtmIfConfExtBandwidthUtilVbrNrtAssigned
        Integer32,

    pdnAtmIfConfExtBandwidthUtilUbrReserved
        Integer32,

    pdnAtmIfConfExtBandwidthUtilUbrAssigned
        Integer32

    }

pdnAtmIfConfExtVbrRtBandwidthUtil OBJECT-TYPE
    SYNTAX  Integer32 (0..9999)
    MAX-ACCESS  read-write
    STATUS  current
    DESCRIPTION
           "The bandwidth utilization for realtime vbr type traffic
            expressed as a percentage

            RtVbrBandwidth =
                  (TotalBandwidth - CBRBandwidth) * (thisObject/100)"
    DEFVAL  { 150 }
    ::= { pdnAtmIfConfExtEntry 1 }

pdnAtmIfConfExtVbrNrtBandwidthUtil OBJECT-TYPE
   SYNTAX  Integer32 (0..9999)
   MAX-ACCESS  read-write
   STATUS  current
   DESCRIPTION
           "The bandwidth utilization for non-realtime VBR type traffic
            expressed as a percentage.
            NrtVbrBandwidth =
                  (TotalBandwidth - CBRBandwidth) * (thisObject/100)"
   DEFVAL  { 150 }
   ::= { pdnAtmIfConfExtEntry 2 }
 
pdnAtmIfConfExtHecErrorThreshold OBJECT-TYPE
   SYNTAX  Integer32
   MAX-ACCESS  read-write
   STATUS  current
   DESCRIPTION
       "The value of this object represents the threshold value for
        the number of uncrorrectable HEC errors in a 15 minutes interval.
        An SNMP link Up/Down trap would be generated if the number of
        uncorrectable HEC errors in a 15 minutes interval exceeds this threshold.
        The valid range of this object is 0 to 1000. A value of 0 will cause
        a trap to be sent on each occurrence of a HEC error. A value of
        -9999 disables the threshold check.
        The default value for this object is 100. "
   DEFVAL  { 100 }
   ::= { pdnAtmIfConfExtEntry 3 }
  
 pdnAtmIfConfExtUnknownCellThreshold OBJECT-TYPE
   SYNTAX  Integer32
   MAX-ACCESS  read-write
   STATUS  current
   DESCRIPTION
       "The value of this object represents the threshold value for
        the number of unknown cells in a 15 minutes interval.
        An SNMP trap would be generated if the number of unknown
        cell in a 15 minutes interval exceeds this threshold.
        The valid range of this object is 0 to 1000. A value of 0 will
        cause a trap to be sent on each occurrence of an unknown cell.
        A value of -9999 disables the threshold check.
        The default value for this object is 10"
   DEFVAL  { 10 }
   ::= { pdnAtmIfConfExtEntry 4 }

 pdnAtmIfConfExtOcdEventThreshold OBJECT-TYPE
   SYNTAX  Integer32
   MAX-ACCESS  read-write
   STATUS  current
   DESCRIPTION
       "The value of this object represents the threshold value for
        the number of Out of Cell Delineation(OCD) events in a 15
        minutes interval. An SNMP trap would be generated if the number
        of OCD events in a 15 minutes interval exceeds this threshold.
        The valid range of this object is 0 to 1000. A value of 0 will
        cause a trap to be sent on each occurrence of a HEC error.
        A value of -9999 disables the threshold check.
        The default value for this object is 0"
   DEFVAL  { 0 }
   ::= { pdnAtmIfConfExtEntry 5 }


pdnAtmIfConfExtBandwidthUtilCbrReserved OBJECT-TYPE
          SYNTAX  Integer32
          MAX-ACCESS     read-write
          STATUS         current
          DESCRIPTION
           "This object specifies the percent of the interface bandwidth to
			be allocated to the CBR traffic class."
          ::= { pdnAtmIfConfExtEntry  6}

pdnAtmIfConfExtBandwidthUtilCbrAssigned OBJECT-TYPE
          SYNTAX  Integer32
          MAX-ACCESS     read-only
          STATUS         current
          DESCRIPTION
           "This object specifies the percent of bandwidth utilization
			(sometimes reffered to as over subscription) the connection
			Addmission Control algorithm has already allowed for the CBR class
			of service."
          ::= { pdnAtmIfConfExtEntry  7}

pdnAtmIfConfExtBandwidthUtilVbrRtReserved OBJECT-TYPE
          SYNTAX  Integer32
          MAX-ACCESS     read-write
          STATUS         current
          DESCRIPTION
           "This object specifies the percent of the interface bandwidth to
            be allocated to the VBR-rt traffic class."
          ::= { pdnAtmIfConfExtEntry  8}

pdnAtmIfConfExtBandwidthUtilVbrRtAssigned OBJECT-TYPE
          SYNTAX  Integer32
          MAX-ACCESS     read-only
          STATUS         current
          DESCRIPTION
           "This object specifies the percent of bandwidth utilization
            (sometimes reffered to as over subscription) the connection
            Addmission Control algorithm has already allowed for the VBR-rt class
            of service."
          ::= { pdnAtmIfConfExtEntry  9}

pdnAtmIfConfExtBandwidthUtilVbrNrtReserved OBJECT-TYPE
          SYNTAX  Integer32
          MAX-ACCESS     read-write
          STATUS         current
          DESCRIPTION
           "This object specifies the percent of the interface bandwidth to
            be allocated to the VBR-nrt traffic class."
          ::= { pdnAtmIfConfExtEntry  10}

pdnAtmIfConfExtBandwidthUtilVbrNrtAssigned OBJECT-TYPE
          SYNTAX  Integer32
          MAX-ACCESS     read-only
          STATUS         current
          DESCRIPTION
           "This object specifies the percent of bandwidth utilization
            (sometimes reffered to as over subscription) the connection
            Addmission Control algorithm has already allowed for the VBR-nrt class
            of service."
          ::= { pdnAtmIfConfExtEntry  11}

pdnAtmIfConfExtBandwidthUtilUbrReserved OBJECT-TYPE
          SYNTAX  Integer32
          MAX-ACCESS     read-write
          STATUS         current
          DESCRIPTION
           "This object specifies the percent of the interface bandwidth to
            be allocated to the UBR traffic class."
          ::= { pdnAtmIfConfExtEntry  12}

pdnAtmIfConfExtBandwidthUtilUbrAssigned OBJECT-TYPE
          SYNTAX  Integer32
          MAX-ACCESS     read-only
          STATUS         current
          DESCRIPTION
           "This object specifies the percent of bandwidth utilization
            (sometimes reffered to as over subscription) the connection
            Addmission Control algorithm has already allowed for the UBR class
            of service."
          ::= { pdnAtmIfConfExtEntry 13}


-- ===============================================================
--
--   Extentions to the ATM Interface Config Table (RFC 2515)
--
--  Release: 1.0  02/18/00 (Initial Release) Prakash Easwar
--
-- This MIB is intended to AUGMENT the atmTrafficDescrParamTable of the ATM-MIB
--

pdnAtmTrafficDescrParamExtTable OBJECT-TYPE
    SYNTAX  SEQUENCE OF PdnAtmTrafficDescrParamExtEntry
    MAX-ACCESS  not-accessible
    STATUS  current
    DESCRIPTION
       "The Paradyne Extension to the atmTrafficDescrParamTable of the ATM-MIB."
    ::= { pdnAtmExtMIBObjects 2   }

pdnAtmTrafficDescrParamExtEntry OBJECT-TYPE
    SYNTAX  PdnAtmTrafficDescrParamExtEntry
    MAX-ACCESS  not-accessible
    STATUS  current
    DESCRIPTION
           "An entry in the Paradyne Extension to the atmTrafficDescrParamTable
           of the ATM-MIB."
    AUGMENTS { atmTrafficDescrParamEntry }
    ::= { pdnAtmTrafficDescrParamExtTable  1 }

PdnAtmTrafficDescrParamExtEntry ::=
    SEQUENCE {

    pdnAtmTrafficDescrParamName
        DisplayString (SIZE(1..12)),

    pdnAtmTrafficPolicing
        TruthValue
    }

pdnAtmTrafficDescrParamName OBJECT-TYPE
          SYNTAX  DisplayString (SIZE(1..12))
          MAX-ACCESS     read-create
          STATUS         current
          DESCRIPTION
           "The value of this Object identifies the traffic descriptor by a
            by a name."
          ::= { pdnAtmTrafficDescrParamExtEntry  1}

pdnAtmTrafficPolicing OBJECT-TYPE
          SYNTAX  TruthValue
          MAX-ACCESS     read-create
          STATUS         current
          DESCRIPTION
           "The value of this Object determines whether or not
            the vcl/vpl to which this traffic descriptor
            is bound will be policed"
          ::= { pdnAtmTrafficDescrParamExtEntry  2}


-- ===============================================================
--
-- Trap group
--

pdnAtmIfConfExtExcessInvalidCellsAlarm NOTIFICATION-TYPE
   OBJECTS { ifOperStatus,
             pdnAtmIfConfExtUnknownCellThreshold
           }
   STATUS current
   DESCRIPTION
       "This alarm indicates that the number of cells with
        uncorrectable HEC erros has exceeded the used defined
        the threshold. "
   ::= { pdnAtmExtMIBTrapPrefix 1 }

END

-- ===============================================================
-- Copyright (C) 2000 Paradyne Corporation.
--  ATM Extension Group
-- ==============================================================
