-- *****************************************************************************
-- PKT-STORM-CTRL-MIB
-- *****************************************************************************
-- Version 1.3
-- 2007/02/13 18:37
-- Rename "DLF" to "Unicast"
-- *****************************************************************************
-- Version 1.2
-- 2005/11/1 11:37
-- this version will support individual(BCast,MCast,DLF) threshold configure.
-- obsolete object swPktStormCtrlthreshold
-- added objects  swPktStormCtrlBCastThreshold,swPktStormCtrlMCastThreshold,
--                swPktStormCtrlDlfThreshold .
-- *****************************************************************************

-- Version 1.1
-- 2005/9/16 05:15
-- Added swPktStormCtrlCountDown object into swPktStormCtrlTable
-- remove swPktStormCtrlBackoff object from swPktStormCtrlTable
-- *****************************************************************************
-- Version 1.0
-- 2005/8/3 11:44
-- Added swPktStormCtrldlfStatus object into swPktStormCtrlTable
-- *****************************************************************************
-- 0.9 Draft
-- 2005/7/11 11:49
-- Create PKT-STORM-CTRL-MIB
-- *****************************************************************************

PKT-STORM-CTRL-MIB DEFINITIONS ::= BEGIN

    IMPORTS
        NOTIFICATION-TYPE, MODULE-IDENTITY,OBJECT-TYPE,IpAddress, Unsigned32,Integer32
                                        FROM SNMPv2-SMI
        MacAddress, RowStatus           FROM SNMPv2-TC
        DisplayString                   FROM RFC1213-MIB
    	SnmpAdminString					FROM SNMP-FRAMEWORK-MIB

        dlink-common-mgmt				FROM DLINK-ID-REC-MIB;



    swPktStormMIB MODULE-IDENTITY
	    LAST-UPDATED "0007150000Z"
	    ORGANIZATION " "
	    CONTACT-INFO
	        "    "
	    DESCRIPTION
		    "The Structure of packet storm control management for the
		    proprietary enterprise."
        ::= { dlink-common-mgmt 25 }

   PortList                ::= OCTET STRING(SIZE (0..127))

   swPktStormCtrl            OBJECT IDENTIFIER ::= { swPktStormMIB 1 }
   swPktStormInfo			       OBJECT IDENTIFIER ::= { swPktStormMIB 2 }
   swPktStormMgmt            OBJECT IDENTIFIER ::= { swPktStormMIB 3 }
   swPktStormNotify			     OBJECT IDENTIFIER ::= { swPktStormMIB 5 }
--*********************************************************
--swPktStormCtrl  OBJECT IDENTIFIER ::= { swPktStormMIB 1 }
--*********************************************************

--swPktStormRecover  OBJECT-TYPE
--        SYNTAX  PortList
--        MAX-ACCESS  read-write
--        STATUS  current
--        DESCRIPTION
--            "Manually recover port from disabled state.If a port is disabled repeatedly up to 6 times,
--            this port will be disabled forever. This command recover it manually."
--        ::= { swPktStormCtrl 1 }

swPktStormTrapCtrl OBJECT-TYPE
	    SYNTAX  INTEGER {
	           none          (1),
		 		 		 stormOccurred (2),
		 		 		 stormCleared  (3),
		 		 		 both          (4)
	            }
	    MAX-ACCESS  read-write
	    STATUS  current
	    DESCRIPTION
	        "This object controls when a storm control notification will be generated.

		    If the object is set to
		    none(1): no notificationswill be generated.
			stormOccurred(2):
			stormCleared(3):A notification will be generated when a storm event is
			                detected or cleared  respectively.
		    both(4): a notification  will be generated both when a storm event is detected and
		             cleared.

		    NOTE:The default value of this object is none(1). "
	    ::= { swPktStormCtrl 2}

-- **************************************************************************
--  swPktStormCtrlTable            OBJECT IDENTIFIER ::= { swPktStormMIB 2 }
-- **************************************************************************

    swPktStormCtrlTable OBJECT-TYPE
        SYNTAX  SEQUENCE OF SwPktStormCtrlEntry
        MAX-ACCESS  not-accessible
        STATUS  current
        DESCRIPTION
            "A table that contains information about packet storm control.
            S/W mechanism is provided to monitor the traffic rate in addition
            to the H/W storm control mechanism. If traffic rate is too high,
            this port will be shut down. When action of packet storm control
            is drop, port's information will be applied to all block members.
            (port 1-8 belong to 1 block,....)"
        ::= { swPktStormMgmt 1 }

    swPktStormCtrlEntry OBJECT-TYPE
        SYNTAX  SwPktStormCtrlEntry
        MAX-ACCESS  not-accessible
        STATUS  current
        DESCRIPTION
            "A list of information for each port of the device."
        INDEX   { swPktStormCtrlPortIndex }
        ::= { swPktStormCtrlTable 1 }

    SwPktStormCtrlEntry ::=
        SEQUENCE {
            swPktStormCtrlPortIndex
                INTEGER,
--            swPktStormCtrlthreshold
--                Integer32,
            swPktStormCtrlBroadcastStatus
                INTEGER,
            swPktStormCtrlMulticastStatus
                INTEGER,
            swPktStormCtrlUnicastStatus
                INTEGER,
            swPktStormCtrlActionStatus
                INTEGER,
            swPktStormCtrlCountDown
                INTEGER,
            swPktStormCtrlTimeinterval
                INTEGER,
            swPktStormCtrlShutdownForever
                INTEGER,
            swPktStormCtrlBCastThreshold
                INTEGER,
            swPktStormCtrlMCastThreshold
                INTEGER,
            swPktStormCtrlUnicastThreshold
                INTEGER
        }

    swPktStormCtrlPortIndex  OBJECT-TYPE
        SYNTAX  INTEGER (0..65535)
        MAX-ACCESS  read-only
        STATUS  current
        DESCRIPTION
        "This object indicates the device's port number.(1..Max port
        number in the device).Used to specify a range of ports to be
        configured."
    ::= { swPktStormCtrlEntry 1 }

--    swPktStormCtrlthreshold  OBJECT-TYPE
--        SYNTAX  Integer32
--        MAX-ACCESS  read-write
--        STATUS  obsolete
--        DESCRIPTION
--        "The upper threshold at which the specified storm control will turn on. ."
--    ::= { swPktStormCtrlEntry 2 }

    swPktStormCtrlBroadcastStatus  OBJECT-TYPE
        SYNTAX  INTEGER
                {
                    disabled(1),
                    enabled(2)
                }
        MAX-ACCESS  read-write
        STATUS  current
        DESCRIPTION
        "This object indicates the broadcast strom control enabled or disabled."
    ::= { swPktStormCtrlEntry 3 }

    swPktStormCtrlMulticastStatus  OBJECT-TYPE
        SYNTAX  INTEGER
                {
                    disabled(1),
                    enabled(2)
                }
        MAX-ACCESS  read-write
        STATUS  current
        DESCRIPTION
        "This object indicates the multicast strom control enabled or disabled."
    ::= { swPktStormCtrlEntry 4 }

    swPktStormCtrlUnicastStatus  OBJECT-TYPE
        SYNTAX  INTEGER
                {
                    disabled(1),
                    enabled(2)
                }
        MAX-ACCESS  read-write
        STATUS  current
        DESCRIPTION
        "This object indicates the unicast(Destination Loopback Fail) strom control enabled
         or disabled."
    ::= { swPktStormCtrlEntry 5 }

   swPktStormCtrlActionStatus  OBJECT-TYPE
        SYNTAX  INTEGER
                {
                    shutdown(1),
                    drop(2)
                }
        MAX-ACCESS  read-write
        STATUS  current
        DESCRIPTION
        "There are two actions to take for strom control, shutdown and drop. The
        former is implemented in S/W, and the latter is implemented in H/W. If user
        choose shutdown, Needs configure countdown and time_interval as well."
    ::= { swPktStormCtrlEntry 6 }

    swPktStormCtrlCountDown  OBJECT-TYPE
        SYNTAX  INTEGER (0..30)
        MAX-ACCESS  read-write
        STATUS  current
        DESCRIPTION
        "If packet storm has been encountered continuously on given port for a long
        period of time (indicated by the value of this object), the port will be shut
        down forever until it's recovered manually.The range of the countdown time is
        5-30 minutes. User can configure countdown to 0 to disable the function of shutdown
        forever.If set this value from 1 to 4 will get 'bad value' return code."
    ::= { swPktStormCtrlEntry 7 }

    swPktStormCtrlTimeinterval  OBJECT-TYPE
        SYNTAX  INTEGER (5..30)
        MAX-ACCESS  read-write
        STATUS  current
        DESCRIPTION
        "The sampling interval of received packet counts. The possible value will be 5~30 seconds."
    ::= { swPktStormCtrlEntry 8 }

    swPktStormCtrlShutdownForever  OBJECT-TYPE
        SYNTAX  INTEGER
                {
                    yes(1),
                    no(2)
                }
        MAX-ACCESS  read-only
        STATUS  current
        DESCRIPTION
        "This object indicates thestrom control whether or not shutted down forever."
    ::= { swPktStormCtrlEntry 9 }

    swPktStormCtrlBCastThreshold  OBJECT-TYPE
        SYNTAX  INTEGER (0..255000)
        MAX-ACCESS  read-write
        STATUS  current
        DESCRIPTION
        "The upper threshold at which the specified storm control will turn on. ."
    ::= { swPktStormCtrlEntry 10 }

    swPktStormCtrlMCastThreshold  OBJECT-TYPE
        SYNTAX  INTEGER (0..255000)
        MAX-ACCESS  read-write
        STATUS  current
        DESCRIPTION
        "The upper threshold at which the specified storm control will turn on. ."
    ::= { swPktStormCtrlEntry 11 }

    swPktStormCtrlUnicastThreshold  OBJECT-TYPE
        SYNTAX  INTEGER (0..255000)
        MAX-ACCESS  read-write
        STATUS  current
        DESCRIPTION
        "The upper threshold at which the specified storm control will turn on. ."
    ::= { swPktStormCtrlEntry 12 }


-- *****************************************************************************************

	swPktStormNotifyPrefix OBJECT IDENTIFIER ::= { swPktStormNotify 0 }

    swPktStormOccurred NOTIFICATION-TYPE
        OBJECTS         { swPktStormCtrlPortIndex
                        }
        STATUS  current
        DESCRIPTION
            "The trap is sent when packet storm is detected by packet storm mechanism and take
             shutdown as action. "

        ::= { swPktStormNotifyPrefix 1 }

    swPktStormCleared NOTIFICATION-TYPE
        OBJECTS         { swPktStormCtrlPortIndex
                        }
        STATUS  current
        DESCRIPTION
            "The trap is sent when the packet storm is cleared by packet storm mechanism. "

        ::= { swPktStormNotifyPrefix 2 }

END
