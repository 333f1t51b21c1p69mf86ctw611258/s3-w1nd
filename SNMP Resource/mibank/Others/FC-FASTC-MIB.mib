FC-FASTC-MIB DEFINITIONS ::= BEGIN

-- Title:       FastComm Communications Adapter MIB in concise format
-- Version      5.0.4
-- Date:        September 30, 2000

-- Copyright 1993,1994,1995,1996,1997,1998 FastComm Communications, Inc. 
-- All Rights Reserved.  Reproduction of this document is authorized 
-- on condition that the foregoing copyright notice is included.
-- This FastComm SNMP Management Information Base Specification
-- (Specification) embodies FastComm's confidential and proprietary
-- intellectual property.  FastComm retains all title and ownership 
-- in the Specification, including any revisions.  
--
-- It is FastComm's intent to encourage the widespread use of this
-- Specification in connection with the management of FastComm
-- products. FastComm grants vendors, end-users, and other interested 
-- parties a non-exclusive license to use this Specification in 
-- connection with the management of FastComm products.
--
-- This Specification is supplied "AS IS," and FastComm makes no
-- warranty, either express or implied, as to the use, operation, 
-- condition, or performance of the Specification.


IMPORTS
   	fsFrad
        	FROM FC-MIB
    	IpAddress
        	FROM RFC1155-SMI
    	OBJECT-TYPE
        	FROM RFC-1212
    	DisplayString
        	FROM RFC1213-MIB
    	TRAP-TYPE
        	FROM RFC-1215;

fsGeneralParms    OBJECT IDENTIFIER ::= { fsFrad 1 }
fsRouting         OBJECT IDENTIFIER ::= { fsFrad 2 }
fsStats           OBJECT IDENTIFIER ::= { fsFrad 3 }
fsT1DsuConfig	OBJECT IDENTIFIER ::= { fsFrad 4 }
fsE1DsuConfig     OBJECT IDENTIFIER ::= { fsFrad 5 }
fsGpt             OBJECT IDENTIFIER ::= { fsFrad 6 }
fsIsdnConfig	OBJECT IDENTIFIER ::= { fsFrad 7 }
fsExtDialupDev    OBJECT IDENTIFIER ::= { fsFrad 8 }
fsVoiceConfig     OBJECT IDENTIFIER ::= { fsFrad 9 }
fsPortProtocol    OBJECT IDENTIFIER ::= { fsFrad 10 }
fsPortInterface   OBJECT IDENTIFIER ::= { fsFrad 11 }

-- ***************************************************************************
-- frad general parameters

fsReloadFactoryValues OBJECT-TYPE
	SYNTAX  INTEGER {
		other		(0),
		initiate	(1)
		}
	ACCESS  read-write
	STATUS  mandatory
	DESCRIPTION
		"Setting this object to initiate reloads factory defaults."
	::= { fsGeneralParms 1 }

fsResetUnit OBJECT-TYPE
	SYNTAX  INTEGER {
		other		(0),
		initiate	(1)
		}
	ACCESS  read-write
	STATUS  mandatory
	DESCRIPTION
		"Setting this object to initiate resets the control logic of
		all modules."
	::= { fsGeneralParms 2 }

fsSaveToNonVolatile OBJECT-TYPE
	SYNTAX  INTEGER {
		other		(0),
		initiate	(1)
		}
	ACCESS  read-write
	STATUS  mandatory
	DESCRIPTION
		"Setting this object to initiate saves the database to
		non-volatile memory."
	::= { fsGeneralParms 3 }

fsFirmwareVersion OBJECT-TYPE
	SYNTAX  DisplayString (SIZE (0..50))
	ACCESS  read-only
	STATUS  mandatory
	DESCRIPTION
		"Firmware Name and Version number."
	::= { fsGeneralParms 4 }

fsParamModStatus OBJECT-TYPE
	SYNTAX  INTEGER {
		notModified		(0),
		parameterModified	(1)
		}
	ACCESS  read-only
	STATUS  mandatory
	DESCRIPTION
		"Indicates if any parameters have been modified."
	::= { fsGeneralParms 5 }

fsClearAllStats OBJECT-TYPE
	SYNTAX  INTEGER {
		other		(0),
		initiate	(1)
		}
	ACCESS  read-write
	STATUS  mandatory
	DESCRIPTION  "Set this to clear all of the statistics."
	::= { fsGeneralParms 6 }

fsClockSource OBJECT-TYPE
	SYNTAX  INTEGER {
		external	(0),
		internal	(1)
		}
	ACCESS  read-write
	STATUS  mandatory
	DESCRIPTION  "Select the clock source."
	::= { fsGeneralParms 7 }

fsActiveCodeRegion OBJECT-TYPE
	SYNTAX  INTEGER
	ACCESS  read-only
	STATUS  mandatory
	DESCRIPTION  "Displays the active code region. There can be 
			  two (2) code regions."
	::= { fsGeneralParms 8 }  

fsSoftwareVersion OBJECT-TYPE
	SYNTAX  DisplayString (SIZE (0..50))
	ACCESS  read-only
	STATUS  mandatory
	DESCRIPTION  "Software version."
	::= { fsGeneralParms 9 }

fsMACAddress OBJECT-TYPE
	SYNTAX  DisplayString (12)
	ACCESS  read-only
	STATUS  mandatory
	DESCRIPTION  "MAC address."
	::= { fsGeneralParms 10 }

fsDatabase OBJECT IDENTIFIER ::= { fsGeneralParms 11 }  

fsActiveDataBase OBJECT-TYPE
	SYNTAX  INTEGER
	ACCESS  read-only
	STATUS  mandatory
	DESCRIPTION  "Displays the active database.  There can be 
			  two (2) databases."
	::= { fsDatabase 1 }

fsDatabaseToBeUsed OBJECT-TYPE
	SYNTAX  INTEGER {
		one	(1),
		two	(2)
		}
	ACCESS  read-write
	STATUS  mandatory
	DESCRIPTION  "Select the database to use and make active."
	::= { fsDatabase 2 }

fsClearDatabase OBJECT-TYPE
	SYNTAX  INTEGER {
		one	(1),
		two	(2)
		}
	ACCESS  read-write
	STATUS  mandatory
	DESCRIPTION  "Clear the database."
	::= { fsDatabase 3 }

fsSystemOne OBJECT IDENTIFIER ::= { fsGeneralParms 12 }

fsLoadSysOneDefaults OBJECT-TYPE
	SYNTAX  INTEGER {
		other		(0),
		initiate	(1)
		}
	ACCESS  read-write
	STATUS  mandatory
	DESCRIPTION  "System One defaults."
	::= { fsSystemOne 1 }  

fsLoadAmadeusDefaults OBJECT-TYPE
	SYNTAX  INTEGER {
		other		(0),
		initiate	(1)
		}
	ACCESS  read-write
	STATUS  mandatory
	DESCRIPTION  "Load Amadeus defaults."
	::= { fsSystemOne 2 }  

fsLoadSysOneNet97Defaults OBJECT-TYPE
	SYNTAX  INTEGER {
		other		(0),
		initiate	(1)
		}
	ACCESS  read-write
	STATUS  mandatory
	DESCRIPTION  "System One Net97 defaults."
	::= { fsSystemOne 3 }  

fsNetworkLoader OBJECT IDENTIFIER ::= { fsGeneralParms 13 }

fsHostIPAddr OBJECT-TYPE
	SYNTAX  IpAddress
	ACCESS  read-write
	STATUS  mandatory
	DESCRIPTION  
		"Remote Host Address"
	::= { fsNetworkLoader 1 }

fsCodeFileName OBJECT-TYPE
	SYNTAX  DisplayString (SIZE (1..128))
	ACCESS  read-write
	STATUS  mandatory
	DESCRIPTION 
		"Path to remote download file"
	::= { fsNetworkLoader 2 }

fsLoadTimeOut OBJECT-TYPE
	SYNTAX  INTEGER
	ACCESS  read-write
	STATUS  mandatory
	DESCRIPTION 
		"Time out for downloading"
	::= { fsNetworkLoader 3 }

fsRegion1Priority OBJECT-TYPE
	SYNTAX  INTEGER {
		primary	(1),
		secondary	(2),
		undefined	(3)
		}
	ACCESS  read-write
	STATUS  mandatory
	DESCRIPTION 
		"Primary setting for region #1"
	::= { fsNetworkLoader 4 }

fsRegion2Priority OBJECT-TYPE
	SYNTAX  INTEGER {
		primary	(1),
		secondary	(2),	    
		undefined	(3)
		}
	ACCESS  read-write
	STATUS  mandatory
	DESCRIPTION 
		"Primary setting for region #2"
	::= { fsNetworkLoader 5 }

fsActiveDatabase OBJECT-TYPE
	SYNTAX  INTEGER {
		one		(1),
		two		(2),
		undefined	(3)
		}
	ACCESS  read-write
	STATUS  mandatory
	DESCRIPTION 
		"Active database"
	::= { fsNetworkLoader 6 }

fsEraseInactiveRegion OBJECT-TYPE
	SYNTAX  INTEGER {
		other		(0),
		initiate	(1)
		}
	ACCESS  read-write
	STATUS  mandatory
	DESCRIPTION 
		"Trigger to erase inactive code region"
	::= { fsNetworkLoader 7 }

fsInitDownload OBJECT-TYPE
	SYNTAX  INTEGER {
		other		(0),
		initiate	(1)
		}
	ACCESS  read-write
	STATUS  mandatory
	DESCRIPTION 
		"Trigger to downloading"
	::= { fsNetworkLoader 8 }

fsNetLoaderSectorTable OBJECT-TYPE
	SYNTAX  SEQUENCE OF FsNetLoaderSectorTableEntry
	ACCESS  not-accessible
	STATUS  mandatory
	DESCRIPTION  ""
	::= { fsNetworkLoader 9 }

	FsNetLoaderSectorTableEntry ::= SEQUENCE {
		fsNetLoaderSectorTableIndex   INTEGER,
		fsNetLoaderSectorState        INTEGER,
		fsNetLoaderSectorErase        INTEGER
		}

	fsNetLoaderSectorTableEntry OBJECT-TYPE	
		SYNTAX  FsNetLoaderSectorTableEntry
		ACCESS  not-accessible
		STATUS  mandatory
		DESCRIPTION ""
		INDEX { fsNetLoaderSectorTableIndex }
		::= { fsNetLoaderSectorTable 1 }

	fsNetLoaderSectorTableIndex OBJECT-TYPE
		SYNTAX  INTEGER
		ACCESS  read-only
		STATUS  mandatory
		DESCRIPTION ""
		::=  { fsNetLoaderSectorTableEntry 1 }

	fsNetLoaderSectorState OBJECT-TYPE
		SYNTAX  INTEGER {
			empty		(0),
			not-empty	(1)
			}
		ACCESS  read-only
		STATUS  mandatory
		DESCRIPTION ""
		::=  { fsNetLoaderSectorTableEntry 2 }

	fsNetLoaderSectorErase OBJECT-TYPE
		SYNTAX  INTEGER {
			view  	(1),
			erase 	(2)
			}
		ACCESS  read-write
		STATUS  mandatory
		DESCRIPTION ""
		::= { fsNetLoaderSectorTableEntry 3 }
  
fsCsuDsuSpeed OBJECT-TYPE
	SYNTAX  INTEGER {
		k56000		(0),
		k64000		(1),
		auto-detect		(2)
		}
	ACCESS  read-write
	STATUS  mandatory
	DESCRIPTION  "CSU/DSU speed."
	::= { fsGeneralParms 14 }

fsDistributedSystem OBJECT IDENTIFIER ::= { fsGeneralParms 15 }

fsFradRole OBJECT-TYPE
	SYNTAX  INTEGER {
		master	(1),
		slave		(2),
		none		(3)
		}
	ACCESS  read-write
	STATUS  mandatory
	DESCRIPTION  ""
	::= { fsDistributedSystem 1 }

fsFradBoardTable OBJECT-TYPE
	SYNTAX  SEQUENCE OF FsBoradTableEntry
	ACCESS  not-accessible
	STATUS  mandatory
	DESCRIPTION  ""
	::= { fsDistributedSystem 2 }

	FsBoradTableEntry ::= SEQUENCE {
		fsFradBoardIndex    INTEGER,
		fsFradBoardName     DisplayString,
		fsFradBoardMacAddr  DisplayString,
		fsFradBoardStatus   INTEGER
		}

	fsBoradTableEntry OBJECT-TYPE
		SYNTAX  FsBoradTableEntry
		ACCESS  not-accessible
		STATUS  mandatory
		DESCRIPTION  ""
		INDEX { fsFradBoardIndex }
		::= { fsFradBoardTable 1 }

	fsFradBoardIndex OBJECT-TYPE
		SYNTAX  INTEGER
		ACCESS  read-only
		STATUS  mandatory
		DESCRIPTION  ""
		::= { fsBoradTableEntry 1 }

	fsFradBoardName OBJECT-TYPE
		SYNTAX  DisplayString (SIZE (15))
		ACCESS  read-write
		STATUS  mandatory
		DESCRIPTION  ""
		::= { fsBoradTableEntry 2 }

	fsFradBoardMacAddr OBJECT-TYPE
		SYNTAX  DisplayString (SIZE (12))
		ACCESS  read-write
		STATUS  mandatory
		DESCRIPTION  ""
		::= { fsBoradTableEntry 3 }

	fsFradBoardStatus OBJECT-TYPE
		SYNTAX  INTEGER {
                  view    (1),
			delete  (3),
                  modify  (4)
			}
		ACCESS  read-write
		STATUS  mandatory
		DESCRIPTION  ""
		::= { fsBoradTableEntry 4 }

fsIpLogging OBJECT IDENTIFIER ::= { fsGeneralParms 16 }

fsIpLogStatus OBJECT-TYPE
	SYNTAX  INTEGER {
		enable       (1),
		disable      (2)
		}
	ACCESS  read-write
	STATUS  mandatory
	DESCRIPTION  ""
	::= { fsIpLogging 1 }

fsIpLogAddr OBJECT-TYPE
	SYNTAX  IpAddress
	ACCESS  read-write
	STATUS  mandatory
	DESCRIPTION  ""
	::= { fsIpLogging 2 }

fsIpLogFacility OBJECT-TYPE
	SYNTAX  INTEGER {
		syslog       (1),
		local0       (2),
            local1       (3),
            local2       (4),
            local3       (5),
            local4       (6),
            local5       (7),
            local6       (8),
            local7       (9),
            invalid      (10)
		}
	ACCESS  read-write
	STATUS  mandatory
	DESCRIPTION  ""
	::= { fsIpLogging 3 }

fsCopyConfig OBJECT IDENTIFIER ::= { fsGeneralParms 17 }

fsLocALocType OBJECT-TYPE
	SYNTAX  INTEGER {
		eeprom-database1  (1),
	      eeprom-database2  (2),
		sysram-database   (3),
		tftp-server       (4)
		}
	ACCESS  read-write
	STATUS  mandatory
	DESCRIPTION  ""
	::= { fsCopyConfig 1 }

fsLocALoadMethod OBJECT-TYPE
	SYNTAX  INTEGER {
		normal	(1),
		best-fit    (2)
		}
	ACCESS  read-write
	STATUS  mandatory
	DESCRIPTION  ""
	::= { fsCopyConfig 2 }

fsLocATFTPSerAddr OBJECT-TYPE
	SYNTAX  IpAddress
	ACCESS  read-write
	STATUS  mandatory
	DESCRIPTION  ""
	::= { fsCopyConfig 3 }

fsLocATFTPFileName OBJECT-TYPE
	SYNTAX  DisplayString (64)
	ACCESS  read-write
	STATUS  mandatory
	DESCRIPTION  ""
	::= { fsCopyConfig 4 }

fsLocBLocType OBJECT-TYPE
	SYNTAX  INTEGER {
		eeprom-database1  (1),
	      eeprom-database2  (2),
		sysram-database   (3),
		tftp-server       (4)
		}
	ACCESS  read-write
	STATUS  mandatory
	DESCRIPTION  ""
	::= { fsCopyConfig 5 }

fsLocBLoadMethod OBJECT-TYPE
	SYNTAX  INTEGER {
		normal	(1),
		best-fit    (2)
		}
	ACCESS  read-write
	STATUS  mandatory
	DESCRIPTION  ""
	::= { fsCopyConfig 6 }

fsLocBTFTPSerAddr OBJECT-TYPE
	SYNTAX  IpAddress
	ACCESS  read-write
	STATUS  mandatory
	DESCRIPTION  ""
	::= { fsCopyConfig 7 }

fsLocBTFTPFileName OBJECT-TYPE
	SYNTAX  DisplayString (64)
	ACCESS  read-write
	STATUS  mandatory
	DESCRIPTION  ""
	::= { fsCopyConfig 8 }

fsInitCopyAtoB OBJECT-TYPE
	SYNTAX  INTEGER {
		other		(0),
		initiate	(1)
		}
	ACCESS  read-write
	STATUS  mandatory
	DESCRIPTION  ""
	::= { fsCopyConfig 9 }

fsInitCopyBtoA OBJECT-TYPE
	SYNTAX  INTEGER {
		other		(0),
		initiate	(1)
		}
	ACCESS  read-write
	STATUS  mandatory
	DESCRIPTION  ""
	::= { fsCopyConfig 10 }

fsInitCopyActionStatus OBJECT-TYPE
	SYNTAX  DisplayString (SIZE (0..50))
	ACCESS  read-only
	STATUS  mandatory
	DESCRIPTION ""
	::= { fsCopyConfig 11 }

-- ***************************************************************************
-- Frad Model Id

fsFradModelId OBJECT-TYPE
	SYNTAX  INTEGER {
		-- MonoFRAD
		fastcomm-F9100-SN-NI    (1),
		fastcomm-F9100-SN-NE    (2),
		fastcomm-F9100-DN-NI    (3),
		fastcomm-F9100-DN-NE    (4),
		fastcomm-F9100-TN-NE    (5),
		fastcomm-F9100-EN-NE    (6),

		-- QuadFRAD
		fastcomm-F9100-SQ-NI    (7),
		fastcomm-F9100-SQ-NL    (8),
		fastcomm-F9100-DQ-NI    (9),
		fastcomm-F9100-DQ-NL    (10),
		fastcomm-F9100-SM-NI    (11),
		fastcomm-F9100-DM-NI    (12),

		-- EtherFRAD-5
		fastcomm-F9200-SR-NI    (13),
		fastcomm-F9200-SR-NL    (14),
		fastcomm-F9200-DR-NI    (15),
		fastcomm-F9200-DR-NL    (16),

		-- EtherFRAD-2
		fastcomm-F9200-SS-NI    (17),
		fastcomm-F9200-SS-NE    (18),
		fastcomm-F9200-DS-NI    (19),
		fastcomm-F9200-DS-NE    (20),

		-- EtherFRAD-1
		fastcomm-F9200-SN-NI    (21),
		fastcomm-F9200-SN-NE    (22),
		fastcomm-F9200-DN-NI    (23),
		fastcomm-F9200-DN-NE    (24),

		-- RingFRAD-4
		fastcomm-F9100-SW-NI    (25),
		fastcomm-F9100-SW-NL    (26),
		fastcomm-F9100-DW-NI    (27),
		fastcomm-F9100-DW-NL    (28),

		-- RingFRAD-2
		fastcomm-F9100-SV-NI    (29),
		fastcomm-F9100-SV-NE    (30),
		fastcomm-F9100-DV-NI    (31),
		fastcomm-F9100-DV-NE    (32),

		-- Web Router
		fastcomm-F9100-SN-NW    (33),
		fastcomm-F9100-DN-NW    (34),
		fastcomm-F9200-SN-NW    (35),
		fastcomm-F9200-DN-NW    (36),

		-- T1 DSU
		fastcomm-F9200-TN-NI    (37),
		fastcomm-F9200-TN-NE    (38),
		fastcomm-F9200-TS-NI    (39),
		fastcomm-F9200-TS-NE    (40),
		fastcomm-F9200-TR-NI    (41),
		fastcomm-F9200-TR-NL    (42),
		fastcomm-F9200-TN-NW    (43),
		fastcomm-F9200-TM-NI    (44),
		fastcomm-F9200-TM-NL    (45),

		-- E1 DSU
		fastcomm-F9200-EN-NI    (46),
		fastcomm-F9200-EN-NE    (47),
		fastcomm-F9200-ES-NI    (48),
		fastcomm-F9200-ES-NE    (50),
		fastcomm-F9200-ER-NI    (51),
		fastcomm-F9200-ER-NL    (52),
		fastcomm-F9200-EN-NW    (53),
		fastcomm-F9200-EM-NI    (54),
		fastcomm-F9200-EM-NL    (55),

		-- MetroLAN Serial/DSU
		fastcomm-F9200-SM-NI    (56),
		fastcomm-F9200-SM-NL    (57),
		fastcomm-F9200-DM-NI    (58),
		fastcomm-F9200-DM-NL    (59),
		-- Global Stack
                fastcomm-F9900-GlobalStack          (60)
                }
	ACCESS  read-write
	STATUS  mandatory
	DESCRIPTION
		"Setting this object to identify the frad."
	::= { fsGeneralParms 18 }

-- ***************************************************************************
-- System Usage parameters

fsSystemUsage OBJECT IDENTIFIER ::= { fsGeneralParms 19 }

fsBuffUtilization OBJECT-TYPE
	SYNTAX  INTEGER
	ACCESS  read-only
	STATUS  mandatory
	DESCRIPTION  ""
	::= { fsSystemUsage 1 }

fsRAMUtilization OBJECT-TYPE
	SYNTAX  INTEGER
	ACCESS  read-only
	STATUS  mandatory
	DESCRIPTION  ""
	::= { fsSystemUsage 2 }

fsEEPROMUtilization OBJECT-TYPE
	SYNTAX  INTEGER
	ACCESS  read-only
	STATUS  mandatory
	DESCRIPTION  ""
	::= { fsSystemUsage 3 }

fsCPUUtilization OBJECT-TYPE
	SYNTAX  INTEGER
	ACCESS  read-only
	STATUS  mandatory
	DESCRIPTION  ""
	::= { fsSystemUsage 4 }


-- ***************************************************************************
-- routing parameters

-- IP Routing Parameters

fsIpRouting OBJECT IDENTIFIER ::= { fsRouting 1 }

fsIpRoutingMode OBJECT-TYPE
	SYNTAX  INTEGER {
		static  (1),
		rip     (2)
		}
	ACCESS  read-write
	STATUS  mandatory
	DESCRIPTION  "IP routing mode (Static, RIP)."
	::= { fsIpRouting 1 }

-- IP Static Routing Parameters

fsIpStaticRouting OBJECT IDENTIFIER ::= { fsIpRouting 2 }

fsIpProxyARP OBJECT-TYPE
	SYNTAX  INTEGER {
		enabled     (1),
		disabled    (2)
		}
	ACCESS  read-write
	STATUS  mandatory
	DESCRIPTION  "Proxy ARP (enabled, disabled)."
	::= { fsIpStaticRouting 1 }

fsIpDefaultRouter OBJECT-TYPE
	SYNTAX  IpAddress
	ACCESS  read-write
	STATUS  mandatory
	DESCRIPTION  "Address of the IP default router."
	::= { fsIpStaticRouting 2 }

fsIpToDlciTable OBJECT-TYPE
	SYNTAX  SEQUENCE OF FsIpToDlciEntry
	ACCESS  not-accessible
	STATUS  mandatory
	DESCRIPTION  ""
	::= { fsIpStaticRouting 3 }

	FsIpToDlciEntry ::= SEQUENCE {
		fsIpIndex           INTEGER,
		fsIpLowIPaddr       IpAddress,
		fsIpHighIPaddr      IpAddress,
            fsIpGptName         DisplayString,
		fsIpPri             INTEGER,
	      fsIpNatConfigNum    INTEGER,
		fsIpStatus          INTEGER
		}

	fsIpToDlciEntry OBJECT-TYPE
		SYNTAX  FsIpToDlciEntry
		ACCESS  not-accessible
		STATUS  mandatory
		DESCRIPTION  ""
		INDEX { fsIpIndex }
		::= { fsIpToDlciTable 1 }

	fsIpIndex OBJECT-TYPE
		SYNTAX  INTEGER
		ACCESS  read-only
		STATUS  mandatory
		DESCRIPTION  ""
		::= { fsIpToDlciEntry 1 }

	fsIpLowIPaddr OBJECT-TYPE
		SYNTAX  IpAddress
		ACCESS  read-write
		STATUS  mandatory
		DESCRIPTION  "Low IP address in the range."
		::= { fsIpToDlciEntry 2 }

	fsIpHighIPaddr OBJECT-TYPE
		SYNTAX  IpAddress
		ACCESS  read-write
		STATUS  mandatory
		DESCRIPTION  "High IP address in the range."
		::= { fsIpToDlciEntry 3 }

	fsIpGptName OBJECT-TYPE
		SYNTAX  DisplayString (SIZE (11))
		ACCESS  read-write
		STATUS  mandatory
		DESCRIPTION  ""
		::= { fsIpToDlciEntry 4 }

	fsIpPri OBJECT-TYPE
		SYNTAX  INTEGER {
			immediate   (0),
			high        (1),
			medium	(2),
			low	      (3),
                  undefined   (4),
                  n-a         (222)
			}
		ACCESS  read-write
		STATUS  mandatory
		DESCRIPTION  "Priority for the IP address."
		::= { fsIpToDlciEntry 5 }

	fsIpNatConfigNum OBJECT-TYPE
		SYNTAX  INTEGER 
		ACCESS  read-write
		STATUS  mandatory
		DESCRIPTION  ""
		::= { fsIpToDlciEntry 6 }

	fsIpStatus OBJECT-TYPE
		SYNTAX  INTEGER {
                  view    (1),
			add     (2),
			delete  (3),
                  modify  (4)
			}
		ACCESS  read-write
		STATUS  mandatory
		DESCRIPTION  ""
		::= { fsIpToDlciEntry 7 }

-- IP RIP Routing Parameters

fsIpRipRouting OBJECT IDENTIFIER ::= { fsIpRouting 3 }

-- IP RIP Routing: Interface Table

--fsIpRipIPFramePri OBJECT-TYPE
--	SYNTAX  INTEGER {
--		immediate       (0),
--		high            (1),
--		medium          (2),
--		low             (3)
--		}
--	ACCESS  read-write
--	STATUS  mandatory
--	DESCRIPTION  ""
--	::= { fsIpRipRouting 1 }

fsIpRipIPV2Passwed OBJECT-TYPE
	SYNTAX  DisplayString
	ACCESS  read-write
	STATUS  mandatory
	DESCRIPTION  ""
	::= { fsIpRipRouting 2 }

fsIpRipIPDynLinkSupport OBJECT-TYPE
	SYNTAX  INTEGER {
		disable       (0),
		enable        (1)
		}
	ACCESS  read-write
	STATUS  mandatory
	DESCRIPTION  ""
	::= { fsIpRipRouting 3 }

fsIpRipAccList1Action OBJECT-TYPE
	SYNTAX  INTEGER {
		allow       (1),
		deny        (2)
		}
	ACCESS  read-write
	STATUS  mandatory
	DESCRIPTION  ""
	::= { fsIpRipRouting 4 }

fsIpRipAccList2Action OBJECT-TYPE
	SYNTAX  INTEGER {
		allow       (1),
		deny        (2)
		}
	ACCESS  read-write
	STATUS  mandatory
	DESCRIPTION  ""
	::= { fsIpRipRouting 5 }

fsIpRipAccList3Action OBJECT-TYPE
	SYNTAX  INTEGER {
		allow       (1),
		deny        (2)
		}
	ACCESS  read-write
	STATUS  mandatory
	DESCRIPTION  ""
	::= { fsIpRipRouting 6 }

fsIpRipAccList4Action OBJECT-TYPE
	SYNTAX  INTEGER {
		allow       (1),
		deny        (2)
		}
	ACCESS  read-write
	STATUS  mandatory
	DESCRIPTION  ""
	::= { fsIpRipRouting 7 }

fsIpRipAccList5Action OBJECT-TYPE
	SYNTAX  INTEGER {
		allow       (1),
		deny        (2)
		}
	ACCESS  read-write
	STATUS  mandatory
	DESCRIPTION  ""
	::= { fsIpRipRouting 8 }

fsIpRipAccList1Table OBJECT-TYPE
	SYNTAX  SEQUENCE OF FsIpRipAccList1TableEntry
	ACCESS  not-accessible
	STATUS  mandatory
	DESCRIPTION  ""
	::= { fsIpRipRouting 9 }

	FsIpRipAccList1TableEntry ::= SEQUENCE {
		fsIpRipAccList1Index           INTEGER,
		fsIpRipAccList1NetNum          IpAddress,
		fsIpRipAccList1NetMask         IpAddress,
		fsIpRipAccList1Status          INTEGER
		}

	fsIpRipAccList1TableEntry OBJECT-TYPE
		SYNTAX  FsIpRipAccList1TableEntry
		ACCESS  not-accessible
		STATUS  mandatory
		DESCRIPTION  ""
		INDEX { fsIpRipAccList1Index}
		::= { fsIpRipAccList1Table 1 }

	fsIpRipAccList1Index OBJECT-TYPE
		SYNTAX  INTEGER
		ACCESS  read-only
		STATUS  mandatory
		DESCRIPTION  ""
		::= { fsIpRipAccList1TableEntry 1 }

	fsIpRipAccList1NetNum OBJECT-TYPE
		SYNTAX  IpAddress
		ACCESS  read-write
		STATUS  mandatory
		DESCRIPTION  ""
		::= { fsIpRipAccList1TableEntry 2 }

	fsIpRipAccList1NetMask OBJECT-TYPE
		SYNTAX  IpAddress
		ACCESS  read-write
		STATUS  mandatory
		DESCRIPTION  ""
		::= { fsIpRipAccList1TableEntry 3 }

	fsIpRipAccList1Status OBJECT-TYPE
		SYNTAX  INTEGER {
                  view    (1),
			add     (2),
			delete  (3),
                  modify  (4)
			}
		ACCESS  read-write
		STATUS  mandatory
		DESCRIPTION  ""
		::= { fsIpRipAccList1TableEntry 4 }

fsIpRipAccList2Table OBJECT-TYPE
	SYNTAX  SEQUENCE OF FsIpRipAccList2TableEntry
	ACCESS  not-accessible
	STATUS  mandatory
	DESCRIPTION  ""
	::= { fsIpRipRouting 10 }

	FsIpRipAccList2TableEntry ::= SEQUENCE {
		fsIpRipAccList2Index           INTEGER,
		fsIpRipAccList2NetNum          IpAddress,
		fsIpRipAccList2NetMask         IpAddress,
		fsIpRipAccList2Status          INTEGER
		}

	fsIpRipAccList2TableEntry OBJECT-TYPE
		SYNTAX  FsIpRipAccList2TableEntry
		ACCESS  not-accessible
		STATUS  mandatory
		DESCRIPTION  ""
		INDEX { fsIpRipAccList2Index}
		::= { fsIpRipAccList2Table 1 }

	fsIpRipAccList2Index OBJECT-TYPE
		SYNTAX  INTEGER
		ACCESS  read-only
		STATUS  mandatory
		DESCRIPTION  ""
		::= { fsIpRipAccList2TableEntry 1 }

	fsIpRipAccList2NetNum OBJECT-TYPE
		SYNTAX  IpAddress
		ACCESS  read-write
		STATUS  mandatory
		DESCRIPTION  ""
		::= { fsIpRipAccList2TableEntry 2 }

	fsIpRipAccList2NetMask OBJECT-TYPE
		SYNTAX  IpAddress
		ACCESS  read-write
		STATUS  mandatory
		DESCRIPTION  ""
		::= { fsIpRipAccList2TableEntry 3 }

	fsIpRipAccList2Status OBJECT-TYPE
		SYNTAX  INTEGER {
                  view    (1),
			add     (2),
			delete  (3),
                  modify  (4)
			}
		ACCESS  read-write
		STATUS  mandatory
		DESCRIPTION  ""
		::= { fsIpRipAccList2TableEntry 4 }

fsIpRipAccList3Table OBJECT-TYPE
	SYNTAX  SEQUENCE OF FsIpRipAccList3TableEntry
	ACCESS  not-accessible
	STATUS  mandatory
	DESCRIPTION  ""
	::= { fsIpRipRouting 11 }

	FsIpRipAccList3TableEntry ::= SEQUENCE {
		fsIpRipAccList3Index           INTEGER,
		fsIpRipAccList3NetNum          IpAddress,
		fsIpRipAccList3NetMask         IpAddress,
		fsIpRipAccList3Status          INTEGER
		}

	fsIpRipAccList3TableEntry OBJECT-TYPE
		SYNTAX  FsIpRipAccList3TableEntry
		ACCESS  not-accessible
		STATUS  mandatory
		DESCRIPTION  ""
		INDEX { fsIpRipAccList3Index}
		::= { fsIpRipAccList3Table 1 }

	fsIpRipAccList3Index OBJECT-TYPE
		SYNTAX  INTEGER
		ACCESS  read-only
		STATUS  mandatory
		DESCRIPTION  ""
		::= { fsIpRipAccList3TableEntry 1 }

	fsIpRipAccList3NetNum OBJECT-TYPE
		SYNTAX  IpAddress
		ACCESS  read-write
		STATUS  mandatory
		DESCRIPTION  ""
		::= { fsIpRipAccList3TableEntry 2 }

	fsIpRipAccList3NetMask OBJECT-TYPE
		SYNTAX  IpAddress
		ACCESS  read-write
		STATUS  mandatory
		DESCRIPTION  ""
		::= { fsIpRipAccList3TableEntry 3 }

	fsIpRipAccList3Status OBJECT-TYPE
		SYNTAX  INTEGER {
                  view    (1),
			add     (2),
			delete  (3),
                  modify  (4)
			}
		ACCESS  read-write
		STATUS  mandatory
		DESCRIPTION  ""
		::= { fsIpRipAccList3TableEntry 4 }

fsIpRipAccList4Table OBJECT-TYPE
	SYNTAX  SEQUENCE OF FsIpRipAccList4TableEntry
	ACCESS  not-accessible
	STATUS  mandatory
	DESCRIPTION  ""
	::= { fsIpRipRouting 12 }

	FsIpRipAccList4TableEntry ::= SEQUENCE {
		fsIpRipAccList4Index           INTEGER,
		fsIpRipAccList4NetNum          IpAddress,
		fsIpRipAccList4NetMask         IpAddress,
		fsIpRipAccList4Status          INTEGER
		}

	fsIpRipAccList4TableEntry OBJECT-TYPE
		SYNTAX  FsIpRipAccList4TableEntry
		ACCESS  not-accessible
		STATUS  mandatory
		DESCRIPTION  ""
		INDEX { fsIpRipAccList4Index}
		::= { fsIpRipAccList4Table 1 }

	fsIpRipAccList4Index OBJECT-TYPE
		SYNTAX  INTEGER
		ACCESS  read-only
		STATUS  mandatory
		DESCRIPTION  ""
		::= { fsIpRipAccList4TableEntry 1 }

	fsIpRipAccList4NetNum OBJECT-TYPE
		SYNTAX  IpAddress
		ACCESS  read-write
		STATUS  mandatory
		DESCRIPTION  ""
		::= { fsIpRipAccList4TableEntry 2 }

	fsIpRipAccList4NetMask OBJECT-TYPE
		SYNTAX  IpAddress
		ACCESS  read-write
		STATUS  mandatory
		DESCRIPTION  ""
		::= { fsIpRipAccList4TableEntry 3 }

	fsIpRipAccList4Status OBJECT-TYPE
		SYNTAX  INTEGER {
                  view    (1),
			add     (2),
			delete  (3),
                  modify  (4)
			}
		ACCESS  read-write
		STATUS  mandatory
		DESCRIPTION  ""
		::= { fsIpRipAccList4TableEntry 4 }

fsIpRipAccList5Table OBJECT-TYPE
	SYNTAX  SEQUENCE OF FsIpRipAccList5TableEntry
	ACCESS  not-accessible
	STATUS  mandatory
	DESCRIPTION  ""
	::= { fsIpRipRouting 13 }

	FsIpRipAccList5TableEntry ::= SEQUENCE {
		fsIpRipAccList5Index           INTEGER,
		fsIpRipAccList5NetNum          IpAddress,
		fsIpRipAccList5NetMask         IpAddress,
		fsIpRipAccList5Status          INTEGER
		}

	fsIpRipAccList5TableEntry OBJECT-TYPE
		SYNTAX  FsIpRipAccList5TableEntry
		ACCESS  not-accessible
		STATUS  mandatory
		DESCRIPTION  ""
		INDEX { fsIpRipAccList5Index}
		::= { fsIpRipAccList5Table 1 }

	fsIpRipAccList5Index OBJECT-TYPE
		SYNTAX  INTEGER
		ACCESS  read-only
		STATUS  mandatory
		DESCRIPTION  ""
		::= { fsIpRipAccList5TableEntry 1 }

	fsIpRipAccList5NetNum OBJECT-TYPE
		SYNTAX  IpAddress
		ACCESS  read-write
		STATUS  mandatory
		DESCRIPTION  ""
		::= { fsIpRipAccList5TableEntry 2 }

	fsIpRipAccList5NetMask OBJECT-TYPE
		SYNTAX  IpAddress
		ACCESS  read-write
		STATUS  mandatory
		DESCRIPTION  ""
		::= { fsIpRipAccList5TableEntry 3 }

	fsIpRipAccList5Status OBJECT-TYPE
		SYNTAX  INTEGER {
                  view    (1),
			add     (2),
			delete  (3),
                  modify  (4)
			}
		ACCESS  read-write
		STATUS  mandatory
		DESCRIPTION  ""
		::= { fsIpRipAccList5TableEntry 4 }

fsIpRipInterfaceTable OBJECT-TYPE
	SYNTAX  SEQUENCE OF FsIpRipInterfaceTableEntry
	ACCESS  not-accessible
	STATUS  mandatory
	DESCRIPTION  ""
	::= { fsIpRipRouting 14 }

	FsIpRipInterfaceTableEntry ::= SEQUENCE {
		fsIpRipInterfaceIndex        INTEGER,
		fsIpRipInterfaceIPAddress    IpAddress,
		fsIpRipInterfaceNetMask      IpAddress,
            fsIpRipGptName               DisplayString,
            fsIpRipInterfaceNextHop      IpAddress,
            fsIpRipInterfaceMode         INTEGER,
            fsIpRipExtraRecHops          INTEGER,
            fsIpRipRouterProtocol        INTEGER,
            fsIpRipRouterRecMode         INTEGER,
            fsIpRipInAccListNo           INTEGER,
            fsIpRipOutAccListNo          INTEGER,
            fsIpRipNatConfigNum          INTEGER,
            fsIpRipBackupIpAddr          IpAddress,
		fsIpRipInterfaceStatus       INTEGER
		}

	fsIpRipInterfaceEntry OBJECT-TYPE
		SYNTAX  FsIpRipInterfaceTableEntry
		ACCESS  not-accessible
		STATUS  mandatory
		DESCRIPTION  ""
		INDEX { fsIpRipInterfaceIndex }
		::= { fsIpRipInterfaceTable 1 }

	fsIpRipInterfaceIndex OBJECT-TYPE
		SYNTAX  INTEGER
		ACCESS  read-only
		STATUS  mandatory
		DESCRIPTION  ""
		::= { fsIpRipInterfaceEntry 1 }

	fsIpRipInterfaceIPAddress OBJECT-TYPE
		SYNTAX  IpAddress
		ACCESS  read-write
		STATUS  mandatory
		DESCRIPTION  "Interface IP address for RIP routing."
		::= { fsIpRipInterfaceEntry 2 }

	fsIpRipInterfaceNetMask OBJECT-TYPE
		SYNTAX  IpAddress
		ACCESS  read-write
		STATUS  mandatory
		DESCRIPTION  "Network mask."
		::= { fsIpRipInterfaceEntry 3 }

	fsIpRipGptName OBJECT-TYPE
		SYNTAX  DisplayString (SIZE (11))
		ACCESS  read-write
		STATUS  mandatory
		DESCRIPTION  ""
		::= { fsIpRipInterfaceEntry 4 }

	fsIpRipInterfaceNextHop OBJECT-TYPE
		SYNTAX  IpAddress
		ACCESS  read-write
		STATUS  mandatory
		DESCRIPTION  "Network mask."
		::= { fsIpRipInterfaceEntry 5 }

	fsIpRipInterfaceMode OBJECT-TYPE
		SYNTAX  INTEGER {
			on      (1),
			send    (2),
			listen  (3),
			off     (4)
			}
		ACCESS  read-write
		STATUS  mandatory
		DESCRIPTION  "RIP mode (On, Send, Listen, Off)."
		::= { fsIpRipInterfaceEntry 6 }

	fsIpRipExtraRecHops OBJECT-TYPE
		SYNTAX  INTEGER (0..10)
		ACCESS  read-write
		STATUS  mandatory
		DESCRIPTION  "Number of hops."
		::= { fsIpRipInterfaceEntry 7 }

	fsIpRipRouterProtocol OBJECT-TYPE
		SYNTAX  INTEGER {
			ripv1-comp      (1),
			ripv1           (2),
			ripv2           (3)
			}
		ACCESS  read-write
		STATUS  mandatory
		DESCRIPTION  ""
		::= { fsIpRipInterfaceEntry 8 }

	fsIpRipRouterRecMode OBJECT-TYPE
		SYNTAX  INTEGER {
			both      	    (1),
			ripv1-only      (2),
			ripv2-only      (3)
			}
		ACCESS  read-write
		STATUS  mandatory
		DESCRIPTION  ""
		::= { fsIpRipInterfaceEntry 9 }

	fsIpRipInAccListNo OBJECT-TYPE
		SYNTAX  INTEGER (0..5)
		ACCESS  read-write
		STATUS  mandatory
		DESCRIPTION  ""
		::= { fsIpRipInterfaceEntry 10 }

	fsIpRipOutAccListNo OBJECT-TYPE
		SYNTAX  INTEGER (0..5)
		ACCESS  read-write
		STATUS  mandatory
		DESCRIPTION  ""
		::= { fsIpRipInterfaceEntry 11 }

	fsIpRipNatConfigNum OBJECT-TYPE
		SYNTAX  INTEGER 
		ACCESS  read-write
		STATUS  mandatory
		DESCRIPTION  ""
		::= { fsIpRipInterfaceEntry 12 }

	fsIpRipBackupIpAddr OBJECT-TYPE
		SYNTAX  IpAddress
		ACCESS  read-write
		STATUS  mandatory
		DESCRIPTION  ""
		::= { fsIpRipInterfaceEntry 13 }

	fsIpRipInterfaceStatus OBJECT-TYPE
		SYNTAX  INTEGER {
                  view    (1),
			add     (2),
			delete  (3),
                  modify  (4)
			}
		ACCESS  read-write
		STATUS  mandatory
		DESCRIPTION  ""
		::= { fsIpRipInterfaceEntry 14 }

-- IP RIP Routing: Static Table

fsIpRipStaticTable OBJECT-TYPE
	SYNTAX  SEQUENCE OF FsIpRipStaticTableEntry
	ACCESS  not-accessible
	STATUS  mandatory
	DESCRIPTION  ""
	::= { fsIpRipRouting 15 }

	FsIpRipStaticTableEntry ::= SEQUENCE {
		fsIpRipStaticIndex        INTEGER,
		fsIpRipStaticIPAddress    IpAddress,
            fsIpRipStaticNetMask      IpAddress,
            fsIpRipStaticGptName      DisplayString,
		fsIpRipStaticNextHop      IpAddress,
		fsIpRipStaticNumberOfHops INTEGER,
		fsIpRipStaticStatus       INTEGER
		}

	fsIpRipStaticEntry OBJECT-TYPE
		SYNTAX  FsIpRipStaticTableEntry
		ACCESS  not-accessible
		STATUS  mandatory
		DESCRIPTION  ""
		INDEX { fsIpRipStaticIndex }
		::= { fsIpRipStaticTable 1 }

	fsIpRipStaticIndex OBJECT-TYPE
		SYNTAX  INTEGER
		ACCESS  read-only
		STATUS  mandatory
		DESCRIPTION  ""
		::= { fsIpRipStaticEntry 1 }

	fsIpRipStaticIPAddress OBJECT-TYPE
		SYNTAX  IpAddress
		ACCESS  read-write
		STATUS  mandatory
		DESCRIPTION  "Static IP address."
		::= { fsIpRipStaticEntry 2 }

	fsIpRipStaticNetMask OBJECT-TYPE
		SYNTAX  IpAddress
		ACCESS  read-write
		STATUS  mandatory
		DESCRIPTION  "Network mask."
		::= { fsIpRipStaticEntry 3 }

	fsIpRipStaticGptName OBJECT-TYPE
		SYNTAX  DisplayString (SIZE (11))
		ACCESS  read-write
		STATUS  mandatory
		DESCRIPTION  ""
		::= { fsIpRipStaticEntry 4 }

	fsIpRipStaticNextHop OBJECT-TYPE
		SYNTAX  IpAddress
		ACCESS  read-write
		STATUS  mandatory
		DESCRIPTION  "Static routing next gateway."
		::= { fsIpRipStaticEntry 5 }

	fsIpRipStaticNumberOfHops OBJECT-TYPE
		SYNTAX  INTEGER (1..15)
		ACCESS  read-write
		STATUS  mandatory
		DESCRIPTION  "Number of hops."
		::= { fsIpRipStaticEntry 6 }

	fsIpRipStaticStatus OBJECT-TYPE
		SYNTAX  INTEGER {
			view    (1),
			add     (2),
                  delete  (3),
                  modify  (4)
			}
		ACCESS  read-write
		STATUS  mandatory
		DESCRIPTION  ""
		::= { fsIpRipStaticEntry 7 }

-- RIP Packet Priority

--fsIpRipPacketPri OBJECT-TYPE
--	SYNTAX  INTEGER {
--		immediate       (0),
--		high            (1),
--		medium          (2),
--		low             (3)
--		}
--	ACCESS  read-write
--	STATUS  mandatory
--	DESCRIPTION  "RIP packet priority (Immediate, High, Medium, Low)."
--	::= { fsIpRouting 4 }

-- IP Routing: BOOTP Address

--fsIpBOOTPAddress OBJECT-TYPE
--	SYNTAX  IpAddress
--	ACCESS  read-write
--	STATUS  mandatory
--	DESCRIPTION  "BootP address."
--	::= { fsIpRouting 5 }

-- IP Routing: IP Name Table

fsIpNameTable OBJECT-TYPE
	SYNTAX  SEQUENCE OF FsIpNameTableEntry
	ACCESS  not-accessible
	STATUS  mandatory
	DESCRIPTION  ""
	::= { fsIpRouting 6 }

	FsIpNameTableEntry ::= SEQUENCE {
		fsIpNameIndex       INTEGER,
		fsIpNameIPAddress   IpAddress,
		fsIpNameTcpPort     INTEGER,
		fsIpNameIPName      DisplayString,
		fsIpNameStatus      INTEGER
		}

	fsIpNameEntry OBJECT-TYPE
		SYNTAX  FsIpNameTableEntry
		ACCESS  not-accessible
		STATUS  mandatory
		DESCRIPTION  ""
		INDEX { fsIpNameIndex }
		::= { fsIpNameTable 1 }

	fsIpNameIndex OBJECT-TYPE
		SYNTAX  INTEGER
		ACCESS  read-only
		STATUS  mandatory
		DESCRIPTION  ""
		::= { fsIpNameEntry 1 }

	fsIpNameIPAddress OBJECT-TYPE
		SYNTAX  IpAddress
		ACCESS  read-write
		STATUS  mandatory
		DESCRIPTION  "IP address of the named FRAD."
		::= { fsIpNameEntry 2 }

	fsIpNameTcpPort OBJECT-TYPE
		SYNTAX  INTEGER (1..65535)
		ACCESS  read-write
		STATUS  mandatory
		DESCRIPTION  "TCP port number."
		::= { fsIpNameEntry 3 }

	fsIpNameIPName OBJECT-TYPE
		SYNTAX  DisplayString (SIZE (1..12))
		ACCESS  read-write
		STATUS  mandatory
		DESCRIPTION  ""
		::= { fsIpNameEntry 4 }

	fsIpNameStatus OBJECT-TYPE
		SYNTAX  INTEGER {
			view   (1),
                  add    (2),
			delete (3),
                  modify (4)
			}
		ACCESS  read-write
		STATUS  mandatory
		DESCRIPTION  ""
		::= { fsIpNameEntry 5 }

-- IP Filtering Parameters

fsIpFiltering OBJECT IDENTIFIER ::= { fsIpRouting 7 }

-- IP Filtering

fsIpFilteringEnable OBJECT-TYPE
	SYNTAX  INTEGER {
		enable       (1),
		disable      (2)
		}
	ACCESS  read-write
	STATUS  mandatory
	DESCRIPTION  ""
	::= { fsIpFiltering 1 }

fsIpFilteringLogging OBJECT-TYPE
	SYNTAX  INTEGER {
		enable       (1),
		disable      (2)
		}
	ACCESS  read-write
	STATUS  mandatory
	DESCRIPTION  ""
	::= { fsIpFiltering 2 }

fsIpFilteringFacility OBJECT-TYPE
	SYNTAX  INTEGER {
		syslog       (1),
		local0       (2),
            local1       (3),
            local2       (4),
            local3       (5),
            local4       (6),
            local5       (7),
            local6       (8),
            local7       (9),
            invalid      (10)
		}
	ACCESS  read-write
	STATUS  mandatory
	DESCRIPTION  ""
	::= { fsIpFiltering 3 }

fsIpFilteringAddr OBJECT-TYPE
	SYNTAX  IpAddress
	ACCESS  read-write
	STATUS  mandatory
	DESCRIPTION  ""
	::= { fsIpFiltering 4 }

fsIpFilteringTable OBJECT-TYPE
	SYNTAX  SEQUENCE OF FsIpFilteringTableEntry
	ACCESS  not-accessible
	STATUS  mandatory
	DESCRIPTION  ""
	::= { fsIpFiltering 5 }

	FsIpFilteringTableEntry ::= SEQUENCE {
		fsIpFilteringIndex                  INTEGER,
		fsIpFilteringSourceIPAddrLow		IpAddress,
		fsIpFilteringSourceIPAddrHigh		IpAddress,
		fsIpFilteringSourceIPPortLow		DisplayString,
		fsIpFilteringSourceIPPortHigh		DisplayString,
		fsIpFilteringDesIPAddrLow		IpAddress,
		fsIpFilteringDesIPAddrHigh		IpAddress,
		fsIpFilteringDesIPPortLow		DisplayString,
		fsIpFilteringDesIPPortHigh		DisplayString,
		fsIpFilteringProtocol			INTEGER,
            fsIpFilteringGptName                DisplayString,
		fsIpFilteringDirection			INTEGER,
		fsIpFilteringAction			INTEGER,
		fsIpFilteringDesc				DisplayString,
		fsIpFilteringStatus      		INTEGER
		}

	fsIpFilteringEntry OBJECT-TYPE
		SYNTAX  FsIpFilteringTableEntry
		ACCESS  not-accessible
		STATUS  mandatory
		DESCRIPTION  ""
		INDEX { fsIpFilteringIndex }
		::= { fsIpFilteringTable 1 }

	fsIpFilteringIndex OBJECT-TYPE
		SYNTAX  INTEGER
		ACCESS  read-only
		STATUS  mandatory
		DESCRIPTION  ""
		::= { fsIpFilteringEntry 1 }

	fsIpFilteringSourceIPAddrLow OBJECT-TYPE
		SYNTAX  IpAddress
		ACCESS  read-write
		STATUS  mandatory
		DESCRIPTION  ""
		::= { fsIpFilteringEntry 2 }

	fsIpFilteringSourceIPAddrHigh OBJECT-TYPE
		SYNTAX  IpAddress
		ACCESS  read-write
		STATUS  mandatory
		DESCRIPTION  ""
		::= { fsIpFilteringEntry 3 }

	fsIpFilteringSourceIPPortLow OBJECT-TYPE
		SYNTAX  DisplayString
		ACCESS  read-write
		STATUS  mandatory
		DESCRIPTION  ""
		::= { fsIpFilteringEntry 4 }

	fsIpFilteringSourceIPPortHigh OBJECT-TYPE
		SYNTAX  DisplayString
		ACCESS  read-write
		STATUS  mandatory
		DESCRIPTION  ""
		::= { fsIpFilteringEntry 5 }

	fsIpFilteringDesIPAddrLow OBJECT-TYPE
		SYNTAX  IpAddress
		ACCESS  read-write
		STATUS  mandatory
		DESCRIPTION  ""
		::= { fsIpFilteringEntry 6 }

	fsIpFilteringDesIPAddrHigh OBJECT-TYPE
		SYNTAX  IpAddress
		ACCESS  read-write
		STATUS  mandatory
		DESCRIPTION  ""
		::= { fsIpFilteringEntry 7 }

	fsIpFilteringDesIPPortLow OBJECT-TYPE
		SYNTAX  DisplayString
		ACCESS  read-write
		STATUS  mandatory
		DESCRIPTION  ""
		::= { fsIpFilteringEntry 8 }

	fsIpFilteringDesIPPortHigh OBJECT-TYPE
		SYNTAX  DisplayString
		ACCESS  read-write
		STATUS  mandatory
		DESCRIPTION  ""
		::= { fsIpFilteringEntry 9 }

	fsIpFilteringProtocol OBJECT-TYPE
		SYNTAX  INTEGER {
			any       (0),
			tcp       (1),
			udp       (2),
 			icmp      (3),
			ack       (4),
			tcp-ini   (5)
			}
		ACCESS  read-write
		STATUS  mandatory
		DESCRIPTION  ""
		::= { fsIpFilteringEntry 10 }

	fsIpFilteringGptName OBJECT-TYPE
		SYNTAX  DisplayString (SIZE (11))
		ACCESS  read-write
		STATUS  mandatory
		DESCRIPTION  ""
		::= { fsIpFilteringEntry 11 }

	fsIpFilteringDirection OBJECT-TYPE
		SYNTAX  INTEGER {
			incoming    (0),
			outgoing    (1),
			both        (2)
			}
		ACCESS  read-write
		STATUS  mandatory
		DESCRIPTION  ""
		::= { fsIpFilteringEntry 12 }

	fsIpFilteringAction OBJECT-TYPE
		SYNTAX  INTEGER {
			deny    (0),
			allow   (1)
			}
		ACCESS  read-write
		STATUS  mandatory
		DESCRIPTION  ""
		::= { fsIpFilteringEntry 13 }

	fsIpFilteringDesc OBJECT-TYPE
		SYNTAX  DisplayString (SIZE (1..40))
		ACCESS  read-write
		STATUS  mandatory
		DESCRIPTION  ""
		::= { fsIpFilteringEntry 14 }

	fsIpFilteringStatus OBJECT-TYPE
		SYNTAX  INTEGER {
			view   (1),
			add    (2),
                  delete (3),
                  modify (4)
			}
		ACCESS  read-write
		STATUS  mandatory
		DESCRIPTION  ""
		::= { fsIpFilteringEntry 15 }

-- IP Prioritization Parameters

fsIpPriority OBJECT IDENTIFIER ::= { fsIpRouting 8 }

-- IP RIP Routing: IP Priority Table

fsIpPriEnable OBJECT-TYPE
	SYNTAX  INTEGER {
		enable       (1),
		disable      (2)
		}
	ACCESS  read-write
	STATUS  mandatory
	DESCRIPTION  ""
	::= { fsIpPriority 1 }

fsIpPriDefPriority OBJECT-TYPE
	SYNTAX  INTEGER {
		immediate   (0),
		high        (1),
		medium	(2),
		low		(3)
		}
	ACCESS  read-write
	STATUS  mandatory
	DESCRIPTION  ""
	::= { fsIpPriority 2 }

fsIpPriServiceEnable OBJECT-TYPE
	SYNTAX  INTEGER {
		enable       (1),
		disable      (2)
		}
	ACCESS  read-write
	STATUS  mandatory
	DESCRIPTION  ""
	::= { fsIpPriority 3 }

fsIpPriServiceLow OBJECT-TYPE
	SYNTAX  DisplayString
	ACCESS  read-write
	STATUS  mandatory
	DESCRIPTION  ""
	::= { fsIpPriority 4 }

fsIpPriServiceMed OBJECT-TYPE
	SYNTAX  DisplayString
	ACCESS  read-write
	STATUS  mandatory
	DESCRIPTION  ""
	::= { fsIpPriority 5 }

fsIpPriServiceHigh OBJECT-TYPE
	SYNTAX  DisplayString
	ACCESS  read-write
	STATUS  mandatory
	DESCRIPTION  ""
	::= { fsIpPriority 6 }

fsIpPriServiceImmed OBJECT-TYPE
	SYNTAX  DisplayString
	ACCESS  read-write
	STATUS  mandatory
	DESCRIPTION  ""
	::= { fsIpPriority 7 }

fsIpPriTable OBJECT-TYPE
	SYNTAX  SEQUENCE OF FsIpPriTableEntry
	ACCESS  not-accessible
	STATUS  mandatory
	DESCRIPTION  ""
	::= { fsIpPriority 8 }

	FsIpPriTableEntry ::= SEQUENCE {
		fsIpPriIndex            	INTEGER,
		fsIpPriSourceIPAddrLow		IpAddress,
		fsIpPriSourceIPAddrHigh		IpAddress,
		fsIpPriSourceIPPortLow		DisplayString,
		fsIpPriSourceIPPortHigh		DisplayString,
		fsIpPriDesIPAddrLow		IpAddress,
		fsIpPriDesIPAddrHigh		IpAddress,
		fsIpPriDesIPPortLow		DisplayString,
		fsIpPriDesIPPortHigh		DisplayString,
		fsIpPriProtocol			INTEGER,
            fsIpPriGptName                DisplayString,
		fsIpPriPriority			INTEGER,
		fsIpPriStatus      		INTEGER
		}

	fsIpPriEntry OBJECT-TYPE
		SYNTAX  FsIpPriTableEntry
		ACCESS  not-accessible
		STATUS  mandatory
		DESCRIPTION  ""
		INDEX { fsIpPriIndex }
		::= { fsIpPriTable 1 }

	fsIpPriIndex OBJECT-TYPE
		SYNTAX  INTEGER
		ACCESS  read-only
		STATUS  mandatory
		DESCRIPTION  ""
		::= { fsIpPriEntry 1 }

	fsIpPriSourceIPAddrLow OBJECT-TYPE
		SYNTAX  IpAddress
		ACCESS  read-write
		STATUS  mandatory
		DESCRIPTION  ""
		::= { fsIpPriEntry 2 }

	fsIpPriSourceIPAddrHigh OBJECT-TYPE
		SYNTAX  IpAddress
		ACCESS  read-write
		STATUS  mandatory
		DESCRIPTION  ""
		::= { fsIpPriEntry 3 }

	fsIpPriSourceIPPortLow OBJECT-TYPE
		SYNTAX  DisplayString
		ACCESS  read-write
		STATUS  mandatory
		DESCRIPTION  ""
		::= { fsIpPriEntry 4 }

	fsIpPriSourceIPPortHigh OBJECT-TYPE
		SYNTAX  DisplayString
		ACCESS  read-write
		STATUS  mandatory
		DESCRIPTION  ""
		::= { fsIpPriEntry 5 }

	fsIpPriDesIPAddrLow OBJECT-TYPE
		SYNTAX  IpAddress
		ACCESS  read-write
		STATUS  mandatory
		DESCRIPTION  ""
		::= { fsIpPriEntry 6 }

	fsIpPriDesIPAddrHigh OBJECT-TYPE
		SYNTAX  IpAddress
		ACCESS  read-write
		STATUS  mandatory
		DESCRIPTION  ""
		::= { fsIpPriEntry 7 }

	fsIpPriDesIPPortLow OBJECT-TYPE
		SYNTAX  DisplayString
		ACCESS  read-write
		STATUS  mandatory
		DESCRIPTION  ""
		::= { fsIpPriEntry 8 }

	fsIpPriDesIPPortHigh OBJECT-TYPE
		SYNTAX  DisplayString
		ACCESS  read-write
		STATUS  mandatory
		DESCRIPTION  ""
		::= { fsIpPriEntry 9 }

	fsIpPriProtocol OBJECT-TYPE
		SYNTAX  INTEGER {
			any   (0),
			tcp   (1),
			udp   (2),
 			icmp  (3)
			}
		ACCESS  read-write
		STATUS  mandatory
		DESCRIPTION  ""
		::= { fsIpPriEntry 10 }

	fsIpPriGptName OBJECT-TYPE
		SYNTAX  DisplayString (SIZE (11))
		ACCESS  read-write
		STATUS  mandatory
		DESCRIPTION  ""
		::= { fsIpPriEntry 11 }

	fsIpPriPriority OBJECT-TYPE
		SYNTAX  INTEGER {
			immediate   (1),
			high        (2),
                  medium      (3),
			low         (4)
			}
		ACCESS  read-write
		STATUS  mandatory
		DESCRIPTION  ""
		::= { fsIpPriEntry 12 }

	fsIpPriStatus OBJECT-TYPE
		SYNTAX  INTEGER {
			view   (1),
			add    (2),
                  delete (3),
                  modify (4)
			}
		ACCESS  read-write
		STATUS  mandatory
		DESCRIPTION  ""
		::= { fsIpPriEntry 13 }

-- IP BOOTP/DHCP Parameters

fsIpDHCP OBJECT IDENTIFIER ::= { fsIpRouting 9 }

fsIpDHCPPrimaryAddr OBJECT-TYPE
	SYNTAX  IpAddress
	ACCESS  read-write
	STATUS  mandatory
	DESCRIPTION  ""
	::= { fsIpDHCP 1 }

fsIpDHCPSecondaryAddr OBJECT-TYPE
	SYNTAX  IpAddress
	ACCESS  read-write
	STATUS  mandatory
	DESCRIPTION  ""
	::= { fsIpDHCP 2 }

-- NAT Parameters

fsIpNAT OBJECT IDENTIFIER ::= { fsIpRouting 10 }

fsIpNATCfg1 OBJECT IDENTIFIER ::= { fsIpNAT 1 }
fsIpNATCfg2 OBJECT IDENTIFIER ::= { fsIpNAT 2 }

fsIpNatCfg1NATStatus OBJECT-TYPE
	SYNTAX  INTEGER {
		enable      (1),
		disable     (2),
            undefined   (3)
		}
	ACCESS  read-write
	STATUS  mandatory
	DESCRIPTION  ""
	::= { fsIpNATCfg1 1 }

fsIpNatCfg1IPMasMode OBJECT-TYPE
	SYNTAX  INTEGER {
		dynamic      (1),
		static       (2),
            undefined    (3)
		}
	ACCESS  read-write
	STATUS  mandatory
	DESCRIPTION  ""
	::= { fsIpNATCfg1 2 }

fsIpNatCfg1NATIPMasAddr OBJECT-TYPE
	SYNTAX  IpAddress
	ACCESS  read-write
	STATUS  mandatory
	DESCRIPTION  ""
	::= { fsIpNATCfg1 3 }

fsIpNatCfg1Logging OBJECT-TYPE
	SYNTAX  INTEGER {
		enable      (1),
		disable     (2),
            undefined   (3)
		}
	ACCESS  read-write
	STATUS  mandatory
	DESCRIPTION  ""
	::= { fsIpNATCfg1 4 }

fsIpNatCfg1NATLogAddr OBJECT-TYPE
	SYNTAX  IpAddress
	ACCESS  read-write
	STATUS  mandatory
	DESCRIPTION  ""
	::= { fsIpNATCfg1 5 }

fsIpNATCfg1Facility OBJECT-TYPE
	SYNTAX  INTEGER {
		syslog       (1),
		local0       (2),
            local1       (3),
            local2       (4),
            local3       (5),
            local4       (6),
            local5       (7),
            local6       (8),
            local7       (9),
            invalid      (10)
		}
	ACCESS  read-write
	STATUS  mandatory
	DESCRIPTION  ""
	::= { fsIpNATCfg1 6 }

fsIpNatCfg1StaticTable OBJECT-TYPE
	SYNTAX  SEQUENCE OF FsIpNatCfg1StaticEntry
	ACCESS  not-accessible
	STATUS  mandatory
	DESCRIPTION  ""
	::= { fsIpNATCfg1 7 }

	FsIpNatCfg1StaticEntry ::= SEQUENCE {
		fsIpNatCfg1StaticIndex           INTEGER,
		fsIpNatCfg1StaticPro		   INTEGER,
		fsIpNatCfg1StaticPriAddrLow	   IpAddress,
            fsIpNatCfg1StaticPriAddrHigh     IpAddress,
            fsIpNatCfg1StaticPriPortLow      INTEGER,
            fsIpNatCfg1StaticPriPortHigh     INTEGER,
		fsIpNatCfg1StaticPubAddrLow	   IpAddress,
            fsIpNatCfg1StaticPubAddrHigh     IpAddress,
            fsIpNatCfg1StaticPubPortLow      INTEGER,
            fsIpNatCfg1StaticPubPortHigh     INTEGER,
		fsIpNatCfg1StaticStatus      	   INTEGER
		}

	fsIpNatCfg1StaticEntry OBJECT-TYPE
		SYNTAX  FsIpNatCfg1StaticEntry
		ACCESS  not-accessible
		STATUS  mandatory
		DESCRIPTION  ""
		INDEX { fsIpNatCfg1StaticIndex }
		::= { fsIpNatCfg1StaticTable 1 }

	fsIpNatCfg1StaticIndex OBJECT-TYPE
		SYNTAX  INTEGER
		ACCESS  read-only
		STATUS  mandatory
		DESCRIPTION  ""
		::= { fsIpNatCfg1StaticEntry 1 }

	fsIpNatCfg1StaticPro OBJECT-TYPE
		SYNTAX  INTEGER {
			tcp   (1),
			udp   (2),
 			icmp  (3)
			}
		ACCESS  read-write
		STATUS  mandatory
		DESCRIPTION  ""
		::= { fsIpNatCfg1StaticEntry 2 }

	fsIpNatCfg1StaticPriAddrLow OBJECT-TYPE
		SYNTAX  IpAddress
		ACCESS  read-write
		STATUS  mandatory
		DESCRIPTION  ""
		::= { fsIpNatCfg1StaticEntry 3 }

	fsIpNatCfg1StaticPriAddrHigh OBJECT-TYPE
		SYNTAX  IpAddress
		ACCESS  read-write
		STATUS  mandatory
		DESCRIPTION  ""
		::= { fsIpNatCfg1StaticEntry 4 }

	fsIpNatCfg1StaticPriPortLow OBJECT-TYPE
		SYNTAX  INTEGER
		ACCESS  read-write
		STATUS  mandatory
		DESCRIPTION  ""
		::= { fsIpNatCfg1StaticEntry 5 }

	fsIpNatCfg1StaticPriPortHigh OBJECT-TYPE
		SYNTAX  INTEGER
		ACCESS  read-write
		STATUS  mandatory
		DESCRIPTION  ""
		::= { fsIpNatCfg1StaticEntry 6 }

	fsIpNatCfg1StaticPubAddrLow OBJECT-TYPE
		SYNTAX  IpAddress
		ACCESS  read-write
		STATUS  mandatory
		DESCRIPTION  ""
		::= { fsIpNatCfg1StaticEntry 7 }

	fsIpNatCfg1StaticPubAddrHigh OBJECT-TYPE
		SYNTAX  IpAddress
		ACCESS  read-write
		STATUS  mandatory
		DESCRIPTION  ""
		::= { fsIpNatCfg1StaticEntry 8 }

	fsIpNatCfg1StaticPubPortLow OBJECT-TYPE
		SYNTAX  INTEGER
		ACCESS  read-write
		STATUS  mandatory
		DESCRIPTION  ""
		::= { fsIpNatCfg1StaticEntry 9 }

	fsIpNatCfg1StaticPubPortHigh OBJECT-TYPE
		SYNTAX  INTEGER
		ACCESS  read-write
		STATUS  mandatory
		DESCRIPTION  ""
		::= { fsIpNatCfg1StaticEntry 10 }

	fsIpNatCfg1StaticStatus OBJECT-TYPE
		SYNTAX  INTEGER {
			view   (1),
			add    (2),
                  delete (3),
                  modify (4)
			}
		ACCESS  read-write
		STATUS  mandatory
		DESCRIPTION  ""
		::= { fsIpNatCfg1StaticEntry 11 }

fsIpNatCfg2NATStatus OBJECT-TYPE
	SYNTAX  INTEGER {
		enable      (1),
		disable     (2),
            undefined   (3)
		}
	ACCESS  read-write
	STATUS  mandatory
	DESCRIPTION  ""
	::= { fsIpNATCfg2 1 }

fsIpNatCfg2IPMasMode OBJECT-TYPE
	SYNTAX  INTEGER {
		dynamic      (1),
		static       (2),
            undefined    (3)
		}
	ACCESS  read-write
	STATUS  mandatory
	DESCRIPTION  ""
	::= { fsIpNATCfg2 2 }

fsIpNatCfg2NATIPMasAddr OBJECT-TYPE
	SYNTAX  IpAddress
	ACCESS  read-write
	STATUS  mandatory
	DESCRIPTION  ""
	::= { fsIpNATCfg2 3 }

fsIpNatCfg2Logging OBJECT-TYPE
	SYNTAX  INTEGER {
		enable      (1),
		disable     (2),
            undefined   (3)
		}
	ACCESS  read-write
	STATUS  mandatory
	DESCRIPTION  ""
	::= { fsIpNATCfg2 4 }

fsIpNatCfg2NATLogAddr OBJECT-TYPE
	SYNTAX  IpAddress
	ACCESS  read-write
	STATUS  mandatory
	DESCRIPTION  ""
	::= { fsIpNATCfg2 5 }

fsIpNATCfg2Facility OBJECT-TYPE
	SYNTAX  INTEGER {
		syslog       (1),
		local0       (2),
            local1       (3),
            local2       (4),
            local3       (5),
            local4       (6),
            local5       (7),
            local6       (8),
            local7       (9),
            invalid      (10)
		}
	ACCESS  read-write
	STATUS  mandatory
	DESCRIPTION  ""
	::= { fsIpNATCfg2 6 }

fsIpNatCfg2StaticTable OBJECT-TYPE
	SYNTAX  SEQUENCE OF FsIpNatCfg2StaticEntry
	ACCESS  not-accessible
	STATUS  mandatory
	DESCRIPTION  ""
	::= { fsIpNATCfg2 7 }

	FsIpNatCfg2StaticEntry ::= SEQUENCE {
		fsIpNatCfg2StaticIndex           INTEGER,
		fsIpNatCfg2StaticPro		   INTEGER,
		fsIpNatCfg2StaticPriAddrLow	   IpAddress,
            fsIpNatCfg2StaticPriAddrHigh     IpAddress,
            fsIpNatCfg2StaticPriPortLow      INTEGER,
            fsIpNatCfg2StaticPriPortHigh     INTEGER,
		fsIpNatCfg2StaticPubAddrLow	   IpAddress,
            fsIpNatCfg2StaticPubAddrHigh     IpAddress,
            fsIpNatCfg2StaticPubPortLow      INTEGER,
            fsIpNatCfg2StaticPubPortHigh     INTEGER,
		fsIpNatCfg2StaticStatus      	   INTEGER
		}

	fsIpNatCfg2StaticEntry OBJECT-TYPE
		SYNTAX  FsIpNatCfg2StaticEntry
		ACCESS  not-accessible
		STATUS  mandatory
		DESCRIPTION  ""
		INDEX { fsIpNatCfg2StaticIndex }
		::= { fsIpNatCfg2StaticTable 1 }

	fsIpNatCfg2StaticIndex OBJECT-TYPE
		SYNTAX  INTEGER
		ACCESS  read-only
		STATUS  mandatory
		DESCRIPTION  ""
		::= { fsIpNatCfg2StaticEntry 1 }

	fsIpNatCfg2StaticPro OBJECT-TYPE
		SYNTAX  INTEGER {
			tcp   (1),
			udp   (2),
 			icmp  (3)
			}
		ACCESS  read-write
		STATUS  mandatory
		DESCRIPTION  ""
		::= { fsIpNatCfg2StaticEntry 2 }

	fsIpNatCfg2StaticPriAddrLow OBJECT-TYPE
		SYNTAX  IpAddress
		ACCESS  read-write
		STATUS  mandatory
		DESCRIPTION  ""
		::= { fsIpNatCfg2StaticEntry 3 }

	fsIpNatCfg2StaticPriAddrHigh OBJECT-TYPE
		SYNTAX  IpAddress
		ACCESS  read-write
		STATUS  mandatory
		DESCRIPTION  ""
		::= { fsIpNatCfg2StaticEntry 4 }

	fsIpNatCfg2StaticPriPortLow OBJECT-TYPE
		SYNTAX  INTEGER
		ACCESS  read-write
		STATUS  mandatory
		DESCRIPTION  ""
		::= { fsIpNatCfg2StaticEntry 5 }

	fsIpNatCfg2StaticPriPortHigh OBJECT-TYPE
		SYNTAX  INTEGER
		ACCESS  read-write
		STATUS  mandatory
		DESCRIPTION  ""
		::= { fsIpNatCfg2StaticEntry 6 }

	fsIpNatCfg2StaticPubAddrLow OBJECT-TYPE
		SYNTAX  IpAddress
		ACCESS  read-write
		STATUS  mandatory
		DESCRIPTION  ""
		::= { fsIpNatCfg2StaticEntry 7 }

	fsIpNatCfg2StaticPubAddrHigh OBJECT-TYPE
		SYNTAX  IpAddress
		ACCESS  read-write
		STATUS  mandatory
		DESCRIPTION  ""
		::= { fsIpNatCfg2StaticEntry 8 }

	fsIpNatCfg2StaticPubPortLow OBJECT-TYPE
		SYNTAX  INTEGER
		ACCESS  read-write
		STATUS  mandatory
		DESCRIPTION  ""
		::= { fsIpNatCfg2StaticEntry 9 }

	fsIpNatCfg2StaticPubPortHigh OBJECT-TYPE
		SYNTAX  INTEGER
		ACCESS  read-write
		STATUS  mandatory
		DESCRIPTION  ""
		::= { fsIpNatCfg2StaticEntry 10 }

	fsIpNatCfg2StaticStatus OBJECT-TYPE
		SYNTAX  INTEGER {
			view   (1),
			add    (2),
                  delete (3),
                  modify (4)
			}
		ACCESS  read-write
		STATUS  mandatory
		DESCRIPTION  ""
		::= { fsIpNatCfg2StaticEntry 11 }

-- ***************************************************************************
--  frad IPX routing parameters

fsIpxRouting OBJECT IDENTIFIER ::= { fsRouting 2 }

fsIpxRoutingMethod OBJECT-TYPE
	SYNTAX  INTEGER {
		ipx-router      (1),
		ipx-passthru    (2),
            undefined       (3)
		}
	ACCESS  read-write
	STATUS  mandatory
	DESCRIPTION  "IPX routing or IPX passthru (via serial port only)."
	::= { fsIpxRouting 1 }

fsIpxEncapsulationMethod OBJECT-TYPE
	SYNTAX  INTEGER {
		ietf    (1),
		cisco   (2)
		}
	ACCESS  read-write
	STATUS  mandatory
	DESCRIPTION  "IPX compatibility mode (IETF or CISCO)."
	::= { fsIpxRouting 2 }

fsIpxPassThruGPTName OBJECT-TYPE
	SYNTAX  DisplayString (SIZE (11))
	ACCESS  read-write
	STATUS  mandatory
	DESCRIPTION  ""
	::= { fsIpxRouting 3 }

fsIpxFrameRelayPri OBJECT-TYPE
	SYNTAX  INTEGER {
		immediate   (0),
		high        (1),
		medium	(2),
		low		(3),
		not-apply	(4)
		}
	ACCESS  read-write
	STATUS  mandatory
	DESCRIPTION  "Priority for the DLCI selected."
	::= { fsIpxRouting 4 }

fsIpxRipPacketPri OBJECT-TYPE
	SYNTAX  INTEGER {
		immediate   (0),
		high        (1),
		medium	(2),
		low		(3)
		}
	ACCESS  read-write
	STATUS  mandatory
	DESCRIPTION  "IPX RIP packet priority."
	::= { fsIpxRouting 5 }

fsIpxSapPacketPri OBJECT-TYPE
	SYNTAX  INTEGER {
		immediate   (0),
		high        (1),
		medium	(2),
		low		(3)
		}
	ACCESS  read-write
	STATUS  mandatory
	DESCRIPTION  "IPX SAP packet priority."
	::= { fsIpxRouting 6 }

fsIpxWANFlag OBJECT-TYPE
	SYNTAX  INTEGER {
		active      (1),
		inactive    (2)
		}
	ACCESS  read-write
	STATUS  mandatory
	DESCRIPTION  ""
	::= { fsIpxRouting 7 }

fsIpxPrimaryNetwork OBJECT-TYPE
	SYNTAX  DisplayString (SIZE (0..8))
	ACCESS  read-write
	STATUS  mandatory
	DESCRIPTION  ""
	::= { fsIpxRouting 8 }

fsIpxRouterName OBJECT-TYPE
	SYNTAX  DisplayString (SIZE (0..48))
	ACCESS  read-write
	STATUS  mandatory
	DESCRIPTION  ""
	::= { fsIpxRouting 9 }

fsIpxNetworkSize OBJECT-TYPE
	SYNTAX  INTEGER {
		small       (1),
		medium      (2),
		large		(3)
		}
	ACCESS  read-write
	STATUS  mandatory
	DESCRIPTION  ""
	::= { fsIpxRouting 10 }

-- IPX routing table

fsIpxRouteTable OBJECT-TYPE
	SYNTAX  SEQUENCE OF FsIpxTableEntry
	ACCESS  not-accessible
	STATUS  mandatory
	DESCRIPTION  ""
	::= { fsIpxRouting 11 }

	FsIpxTableEntry ::= SEQUENCE {
		fsIpxIndex        INTEGER,
		fsIpxNetNum       DisplayString,
		fsIpxPri	      INTEGER,
            fsIpxGptName      DisplayString,
                fsIpxSapMode	  INTEGER,
		fsIpxStatus       INTEGER
		}

	fsIpxTableEntry OBJECT-TYPE
		SYNTAX  FsIpxTableEntry
		ACCESS  not-accessible
		STATUS  mandatory
		DESCRIPTION  ""
		INDEX { fsIpxIndex }
		::= { fsIpxRouteTable 1 }

	fsIpxIndex OBJECT-TYPE
		SYNTAX  INTEGER
		ACCESS  read-only
		STATUS  mandatory
		DESCRIPTION  ""
		::= { fsIpxTableEntry 1 }

	fsIpxNetNum OBJECT-TYPE
		SYNTAX  DisplayString (SIZE (0..8))
		ACCESS  read-write
		STATUS  mandatory
		DESCRIPTION  "IPX network number."
		::= { fsIpxTableEntry 2 }

	fsIpxPri OBJECT-TYPE
		SYNTAX  INTEGER {
			immediate   (0),
			high        (1),
			medium	(2),
			low		(3)
			}
		ACCESS  read-write
		STATUS  mandatory
		DESCRIPTION  "Priority for IPX (Immediate, High, Medium, Low)."
		::= { fsIpxTableEntry 3 }

	fsIpxGptName OBJECT-TYPE
		SYNTAX  DisplayString (SIZE (11))
		ACCESS  read-write
		STATUS  mandatory
		DESCRIPTION  ""
		::= { fsIpxTableEntry 4 }

	fsIpxSapMode OBJECT-TYPE
		SYNTAX  INTEGER {
			on      (0),
			send    (1),
			listen	(2),
			off	(3)
			}
		ACCESS  read-write
		STATUS  mandatory
		DESCRIPTION  ""
		::= { fsIpxTableEntry 5 }

	fsIpxStatus OBJECT-TYPE
		SYNTAX  INTEGER {
			view   (1),
			add    (2),
                  delete (3),
                  modify (4)
			}
		ACCESS  read-write
		STATUS  mandatory
		DESCRIPTION  ""
		::= { fsIpxTableEntry 6 }


-- ***************************************************************************
-- frad frame relay routing table

fsFrameRelayRouting OBJECT IDENTIFIER ::= { fsRouting 3 }

fsFrameRelayRoutingTable OBJECT-TYPE
	SYNTAX  SEQUENCE OF FsFrameRelayRoutingEntry
	ACCESS  not-accessible
	STATUS  mandatory
	DESCRIPTION  ""
	::= { fsFrameRelayRouting 1 }

	FsFrameRelayRoutingEntry ::= SEQUENCE {
		fsFRRouteIndex            INTEGER,
            fsFRFirstGptName          DisplayString,
		fsFRFirstPri              INTEGER,
            fsFRSecondGptName         DisplayString,
		fsFRSecondPri             INTEGER,
		fsFRStatus                INTEGER
		}

	fsFrameRelayRoutingEntry OBJECT-TYPE
		SYNTAX  FsFrameRelayRoutingEntry
		ACCESS  not-accessible
		STATUS  mandatory
		DESCRIPTION  ""
		INDEX { fsFRRouteIndex }
		::= { fsFrameRelayRoutingTable 1 }

	fsFRRouteIndex OBJECT-TYPE
		SYNTAX  INTEGER
		ACCESS  read-only
		STATUS  mandatory
		DESCRIPTION  ""
		::= { fsFrameRelayRoutingEntry 1 }

	fsFRFirstGptName OBJECT-TYPE
		SYNTAX  DisplayString (SIZE (11))
		ACCESS  read-write
		STATUS  mandatory
		DESCRIPTION  ""
		::= { fsFrameRelayRoutingEntry 2 }

	fsFRFirstPri OBJECT-TYPE
		SYNTAX  INTEGER {
			immediate   (0),
			high        (1),
			medium	(2),
			low		(3)
			}
		ACCESS  read-write
		STATUS  mandatory
		DESCRIPTION  "Priority for Frame Relay routing."
		::= { fsFrameRelayRoutingEntry 3 }

	fsFRSecondGptName OBJECT-TYPE
		SYNTAX  DisplayString (SIZE (11))
		ACCESS  read-write
		STATUS  mandatory
		DESCRIPTION  ""
		::= { fsFrameRelayRoutingEntry 4 }

	fsFRSecondPri OBJECT-TYPE
		SYNTAX  INTEGER {
			immediate   (0),
			high        (1),
			medium	(2),
			low		(3)
			}
		ACCESS  read-write
		STATUS  mandatory
		DESCRIPTION  "Priority for Frame Relay routing."
		::= { fsFrameRelayRoutingEntry 5 }

	fsFRStatus OBJECT-TYPE
		SYNTAX  INTEGER {
			view   (1),
			add    (2),
                  delete (3),
                  modify (4)
			}
		ACCESS  read-write
		STATUS  mandatory
		DESCRIPTION  ""
		::= { fsFrameRelayRoutingEntry 6 }

-- ***************************************************************************
-- frad frame relay routing table

fsVoiceRouting OBJECT IDENTIFIER ::= { fsRouting 4 }

fsVoiceRoutingATPTable OBJECT-TYPE
	SYNTAX  SEQUENCE OF FsVoiceRoutingATPEntry
	ACCESS  not-accessible
	STATUS  mandatory
	DESCRIPTION  ""
	::= { fsVoiceRouting 1 }

	FsVoiceRoutingATPEntry ::= SEQUENCE {
		fsATPIndex			INTEGER,
            fsATPPhoneAddr          DisplayString,
		fsATPMinDigitReq        INTEGER,
            fsATPMaxDigitReq        INTEGER,
		fsATPDigitStrip         INTEGER,
            fsATPPrefixStr          DisplayString,
            fsATPHuntGrpId          DisplayString,
            fsATPGPTName            DisplayString,
		fsATPStatus             INTEGER
		}

	fsVoiceRoutingATPEntry OBJECT-TYPE
		SYNTAX  FsVoiceRoutingATPEntry
		ACCESS  not-accessible
		STATUS  mandatory
		DESCRIPTION  ""
		INDEX { fsATPIndex }
		::= { fsVoiceRoutingATPTable 1 }

	fsATPIndex OBJECT-TYPE
		SYNTAX  INTEGER
		ACCESS  read-only
		STATUS  mandatory
		DESCRIPTION  ""
		::= { fsVoiceRoutingATPEntry 1 }

	fsATPPhoneAddr OBJECT-TYPE
		SYNTAX  DisplayString
		ACCESS  read-write
		STATUS  mandatory
		DESCRIPTION  ""
		::= { fsVoiceRoutingATPEntry 2 }

	fsATPMinDigitReq OBJECT-TYPE
		SYNTAX  INTEGER (0..20)
		ACCESS  read-write
		STATUS  mandatory
		DESCRIPTION  ""
		::= { fsVoiceRoutingATPEntry 3 }

	fsATPMaxDigitReq OBJECT-TYPE
		SYNTAX  INTEGER (0..20)
		ACCESS  read-write
		STATUS  mandatory
		DESCRIPTION  ""
		::= { fsVoiceRoutingATPEntry 4 }

	fsATPDigitStrip OBJECT-TYPE
		SYNTAX  INTEGER (0..20)
		ACCESS  read-write
		STATUS  mandatory
		DESCRIPTION  ""
		::= { fsVoiceRoutingATPEntry 5 }

	fsATPPrefixStr OBJECT-TYPE
		SYNTAX  DisplayString
		ACCESS  read-write
		STATUS  mandatory
		DESCRIPTION  ""
		::= { fsVoiceRoutingATPEntry 6 }

	fsATPHuntGrpId OBJECT-TYPE
		SYNTAX  DisplayString
		ACCESS  read-write
		STATUS  mandatory
		DESCRIPTION  ""
		::= { fsVoiceRoutingATPEntry 7 }

	fsATPGPTName OBJECT-TYPE
		SYNTAX  DisplayString
		ACCESS  read-write
		STATUS  mandatory
		DESCRIPTION  ""
		::= { fsVoiceRoutingATPEntry 8 }

	fsATPStatus OBJECT-TYPE
		SYNTAX  INTEGER {
			view   (1),
			add    (2),
                  delete (3),
                  modify (4)
			}
		ACCESS  read-write
		STATUS  mandatory
		DESCRIPTION  ""
		::= { fsVoiceRoutingATPEntry 9 }

fsVoiceRoutingHuntTable OBJECT-TYPE
	SYNTAX  SEQUENCE OF FsVoiceRoutingHuntEntry
	ACCESS  not-accessible
	STATUS  mandatory
	DESCRIPTION  ""
	::= { fsVoiceRouting 2 }

    FsVoiceRoutingHuntEntry ::= SEQUENCE {
            fsHuntIndex			INTEGER,
            fsHuntGroupId           INTEGER,
            fsHuntGPTName           DisplayString,
            fsMappedToHuntId        DisplayString,
            fsHuntMode              INTEGER,
            fsHuntStatus            INTEGER
    }

	fsVoiceRoutingHuntEntry OBJECT-TYPE
		SYNTAX  FsVoiceRoutingHuntEntry
		ACCESS  not-accessible
		STATUS  mandatory
		DESCRIPTION  ""
		INDEX { fsHuntIndex }
		::= { fsVoiceRoutingHuntTable 1 }

	fsHuntIndex OBJECT-TYPE
		SYNTAX  INTEGER
		ACCESS  read-only
		STATUS  mandatory
		DESCRIPTION  ""
		::= { fsVoiceRoutingHuntEntry 1 }

	fsHuntGroupId OBJECT-TYPE
		SYNTAX  INTEGER (0..10)
		ACCESS  read-write
		STATUS  mandatory
		DESCRIPTION  ""
		::= { fsVoiceRoutingHuntEntry 2 }

	fsHuntGPTName OBJECT-TYPE
		SYNTAX  DisplayString
		ACCESS  read-write
		STATUS  mandatory
		DESCRIPTION  ""
		::= { fsVoiceRoutingHuntEntry 3 }

	fsMappedToHuntId OBJECT-TYPE
		SYNTAX  DisplayString
		ACCESS  read-write
		STATUS  mandatory
		DESCRIPTION  "Hunt Group can be mapped to previously configured
			      Hunt group. Mapped to Hunt Group cannot be mapped 			      again"
		::= { fsVoiceRoutingHuntEntry 4 }

	fsHuntMode OBJECT-TYPE
		SYNTAX  INTEGER (1..2)
		ACCESS  read-write
		STATUS  mandatory
		DESCRIPTION  "There are two types of modes - Terminal, Circular
			      Terminal - call is always established with the 
			      first available  path mentioned in the hunt grp
			      Circular - Every call proceeds in a round robin
			      fashion within that hunt group"
		::= { fsVoiceRoutingHuntEntry 5 }

	fsHuntStatus OBJECT-TYPE
		SYNTAX  INTEGER {
			view   (1),
			add    (2),
                  delete (3),
                  modify (4)
			}
		ACCESS  read-write
		STATUS  mandatory
		DESCRIPTION  ""
		::= { fsVoiceRoutingHuntEntry 6 }
-- ***************************************************************************
-- frad SNA Configuration

fsSna OBJECT IDENTIFIER ::= { fsRouting 7 }

	fsSnaAdminStatus OBJECT-TYPE
		SYNTAX  INTEGER {
			down  (1),
			up    (2)
		      }
	      ACCESS  read-write
	      STATUS  mandatory
	      DESCRIPTION
		      "This object reflects the desired status of the SNA
		       Switching module. If this value is set to 'down',
		       SNA Switching is disabled. If this value is set to
		       'up', SNA Switching is enabled."
	      ::= { fsSna 1 }

	fsSnaSwTstXidRetries OBJECT-TYPE
	      SYNTAX  INTEGER (1..20)
	      ACCESS  read-write
	      STATUS  mandatory
	      DESCRIPTION
		      "This object reflects the maximum number of retries
		       permitted for TEST and XID pdus."
	      ::= { fsSna 2 }

	fsSnaSwTstXidTmr OBJECT-TYPE
	      SYNTAX  INTEGER (1..60)
	      ACCESS  read-write
	      STATUS  mandatory
	      DESCRIPTION
		      "This object reflects the value of the XID-TEST timer
		       in seconds."
	      ::= { fsSna 3 }

	fsSnaSessRestartTmr OBJECT-TYPE
	      SYNTAX  INTEGER (1..180)
	      ACCESS  read-write
	      STATUS  mandatory
	      DESCRIPTION
		      "This object reflects the value of the Session-Restart
		       timer in seconds."
	      ::= { fsSna 4 }

--        fsSnaCallRetryTimer OBJECT-TYPE
--              SYNTAX  INTEGER
--              ACCESS  read-write
--              STATUS  mandatory
--              DESCRIPTION
--                      "This object reflects the value of the Call-Retry timer
--                      in 1/10ths of a second."
--              ::= { fsSna 5 }

--        fsSnaQllcQueryTimer OBJECT-TYPE
--              SYNTAX  INTEGER
--              ACCESS  read-write
--              STATUS  mandatory
--              DESCRIPTION
--                      "This object reflects the value of the QLLC Query timer
--                      in 1/10ths of a second."
--              ::= { fsSna 6 }

--        fsSnaQllcMaxRetries OBJECT-TYPE
--              SYNTAX  INTEGER
--              ACCESS  read-write
--              STATUS  mandatory
--              DESCRIPTION
--                      "This object reflects the maximum number of retries
--                       permitted for QLLC QSM and QDISC pdus."
--              ::= { fsSna 7 }

	fsSnaPseudoBridgeNumber OBJECT-TYPE
	      SYNTAX  INTEGER
	      ACCESS  read-write
	      STATUS  mandatory
	      DESCRIPTION
		      "The pseudo-bridge number for the FRAD"
	      ::= { fsSna 8 }

	fsSnaPseudoRingNumber OBJECT-TYPE
	      SYNTAX  INTEGER
	      ACCESS  read-write
	      STATUS  mandatory
	      DESCRIPTION
		      "The pseudo-ring number for the FRAD"
	      ::= { fsSna 9 }

-- ***************************************************************************
-- frad SNA SWITCHING SDLC-FR CONFIGURATION TABLE

	fsSnaSdlcFrCfgTable OBJECT-TYPE
	      SYNTAX  SEQUENCE OF FsSnaSdlcFrCfgEntry
	      ACCESS  not-accessible
	      STATUS  mandatory
	      DESCRIPTION
		      "Configuration Table for SDLC-FR Switching. This table
		      would contain the SDLC-FR switching entries, indexed by
		      the table index 'fsSnaSdlcFrIndex'."
	      ::= { fsSna 10 }
	  
	FsSnaSdlcFrCfgEntry ::= SEQUENCE {
		fsSnaSdlcFrIndex              INTEGER,
		fsSnaSdlcFrSdlcPortNum        INTEGER,
		fsSnaSdlcFrSdlcStnAddr        DisplayString,
		fsSnaSdlcFrLocalMAC           DisplayString,
		fsSnaSdlcFrLocalSAP           DisplayString,
		fsSnaSdlcFrRemoteMAC          DisplayString,
		fsSnaSdlcFrRemoteSAP          DisplayString,
            fsSnaSdlcFrFRGPTName          DisplayString,
            fsSnaSdlcFrPriority           INTEGER,
		fsSnaSdlcFrXidProcessing      INTEGER,
		fsSnaSdlcFrPUType             INTEGER,
		fsSnaSdlcFrXidValue           DisplayString,
		fsSnaSdlcFrAdminStatus        INTEGER
	      }

	fsSnaSdlcFrCfgEntry OBJECT-TYPE
	      SYNTAX  FsSnaSdlcFrCfgEntry
	      ACCESS  not-accessible
	      STATUS  mandatory
	      DESCRIPTION
		      "Config Table Entry for SDLC-FR switching scenario."
	      INDEX   { fsSnaSdlcFrIndex }
	      ::= { fsSnaSdlcFrCfgTable 1 }

	fsSnaSdlcFrIndex OBJECT-TYPE
	      SYNTAX  INTEGER
	      ACCESS  read-only
	      STATUS  mandatory
	      DESCRIPTION
		      "The index value which uniquely identifies this
		      SDLC-FR switching configuration table entry."
	      ::= { fsSnaSdlcFrCfgEntry 1 }

	fsSnaSdlcFrSdlcPortNum OBJECT-TYPE
		  SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
	      ACCESS  read-write
	      STATUS  mandatory
	      DESCRIPTION
		      "The SDLC Port for this switching entry."
	      ::= { fsSnaSdlcFrCfgEntry 2 }
 
	fsSnaSdlcFrSdlcStnAddr OBJECT-TYPE
	      SYNTAX  DisplayString (SIZE(2))
	      ACCESS  read-write
	      STATUS  mandatory
	      DESCRIPTION
		      "The SDLC Station Address for this switching entry."
	      ::= { fsSnaSdlcFrCfgEntry 3 }

	fsSnaSdlcFrLocalMAC OBJECT-TYPE
	      SYNTAX  DisplayString (SIZE (12))
	      ACCESS  read-write
	      STATUS  mandatory
	      DESCRIPTION
		      "The Pseudo-MAC address for this switching entry."
	      ::= { fsSnaSdlcFrCfgEntry 4 }

	fsSnaSdlcFrLocalSAP OBJECT-TYPE
	      SYNTAX  DisplayString (SIZE (2))
	      ACCESS  read-write
	      STATUS  mandatory
	      DESCRIPTION
		      "The Pseudo-SAP for this switching entry."
	      ::= { fsSnaSdlcFrCfgEntry 5 }

	fsSnaSdlcFrRemoteMAC OBJECT-TYPE
	      SYNTAX  DisplayString (SIZE (12))
	      ACCESS  read-write
	      STATUS  mandatory
	      DESCRIPTION
		      "The Remote MAC address for this switching entry."
	      ::= { fsSnaSdlcFrCfgEntry 6 }

	fsSnaSdlcFrRemoteSAP OBJECT-TYPE
	      SYNTAX  DisplayString (SIZE (2))
	      ACCESS  read-write
	      STATUS  mandatory
	      DESCRIPTION
		      "The Remote SAP for this switching entry."
	      ::= { fsSnaSdlcFrCfgEntry 7 }

      fsSnaSdlcFrFRGPTName OBJECT-TYPE
            SYNTAX  DisplayString (SIZE (10))
            ACCESS  read-write
            STATUS  mandatory
            DESCRIPTION
                  "The GPT name for this switching entry."
            ::= { fsSnaSdlcFrCfgEntry 8 }

	fsSnaSdlcFrPriority OBJECT-TYPE
	      SYNTAX  INTEGER {
			immediate   (0),
			high        (1),
			medium	(2),
			low		(3)
			}
	      ACCESS  read-write
	      STATUS  mandatory
	      DESCRIPTION
		      "The priority of messages for this session, when
		       tranporting over FR."
	      ::= { fsSnaSdlcFrCfgEntry 9 }

	fsSnaSdlcFrXidProcessing OBJECT-TYPE
	      SYNTAX  INTEGER {
			end-to-end-xid          (1),
			poll-llc-with-xid       (2),
			respond-to-sdlc-xid     (3),
			respond-to-llc-xid      (4)
		      }
	      ACCESS  read-write
	      STATUS  mandatory
	      DESCRIPTION
		      "This object reflects the type of XID processing desired.
		      A value of 'END-TO-END-XID' indicates that end-nodes will 
		      respond to XID requests. A value of 'POLL-LLC-WITH-XID'
		      indicates that Switching will send a XID request when it
		      receives a TEST request from the LLC across FR network.
		      A value of 'RESPOND-TO-SDLC-XID' indicates that Switching
		      will respond to a XID request from an SDLC end-node.
		      A value of 'RESPOND-TO-LLC-XID' indicates that Switching
		      will respond to the XID request received across the FR
		      network."
	      ::= { fsSnaSdlcFrCfgEntry 10 }

	fsSnaSdlcFrPUType OBJECT-TYPE
	      SYNTAX  INTEGER {
			pu1-0	(1),
			pu2-0   (2),
			pu4-0   (4)
		      }
	      ACCESS  read-write
	      STATUS  mandatory
	      DESCRIPTION
		      "The Physical Unit Type for Xid Processing."
	      ::= { fsSnaSdlcFrCfgEntry 11 }

	fsSnaSdlcFrXidValue OBJECT-TYPE
	      SYNTAX  DisplayString (SIZE (8))
	      ACCESS  read-write
	      STATUS  mandatory
	      DESCRIPTION     
		      "The XID string to be used for XID responses."
	      ::= { fsSnaSdlcFrCfgEntry 12 }

	fsSnaSdlcFrAdminStatus OBJECT-TYPE
		SYNTAX  INTEGER {
			view   (1),
			add    (2),
                  delete (3),
                  modify (4)
			}
	      ACCESS  read-write
	      STATUS  mandatory
	      DESCRIPTION ""
	      ::= { fsSnaSdlcFrCfgEntry 13 }

-- ***************************************************************************
-- frad SNA SWITCHING LLC-FR CONFIGURATION TABLE

	fsSnaLlcFrCfgTable OBJECT-TYPE
	      SYNTAX  SEQUENCE OF FsSnaLlcFrCfgEntry
	      ACCESS  not-accessible
	      STATUS  mandatory
	      DESCRIPTION
		      "Configuration Table for LLC-FR Switching. This table
		      would contain the LLC-FR switching entries, indexed by the
		      table index 'fsSnaLlcFrIndex'."
	      ::= { fsSna 11 }
	  
	FsSnaLlcFrCfgEntry ::= SEQUENCE {
		fsSnaLlcFrIndex               INTEGER,
            fsSnaLlcFrLLCGptName          DisplayString,
		fsSnaLlcFrLocalMAC            DisplayString,
		fsSnaLlcFrLocalSAP            DisplayString,
		fsSnaLlcFrLocalMapSAP         DisplayString,
            fsSnaLlcFrFRGptName           DisplayString,
		fsSnaLlcFrRemoteMAC           DisplayString,
		fsSnaLlcFrRemoteSAP           DisplayString,
		fsSnaLlcFrRemoteMapSAP        DisplayString,
		fsSnaLlcFrPriority            INTEGER,
            fsSnaLlcFrXidProcessing       INTEGER,
		fsSnaLlcFrAdminStatus         INTEGER
	      }

	fsSnaLlcFrCfgEntry OBJECT-TYPE
	      SYNTAX  FsSnaLlcFrCfgEntry
	      ACCESS  not-accessible
	      STATUS  mandatory
	      DESCRIPTION
		      "Configuration Table Entry for LLC-FR switching scenario."
	      INDEX   { fsSnaLlcFrIndex }
	      ::= { fsSnaLlcFrCfgTable 1 }

	fsSnaLlcFrIndex OBJECT-TYPE
	      SYNTAX  INTEGER
	      ACCESS  read-only
	      STATUS  mandatory
	      DESCRIPTION
		      "The index value which uniquely identifies this
		      LLC-FR switching configuration table entry."
	      ::= { fsSnaLlcFrCfgEntry 1 }

	fsSnaLlcFrLLCGptName OBJECT-TYPE
		SYNTAX  DisplayString (SIZE (1..12))
		ACCESS  read-write
		STATUS  mandatory
		DESCRIPTION  ""
		::= { fsSnaLlcFrCfgEntry 2 }
 
	fsSnaLlcFrLocalMAC OBJECT-TYPE
	      SYNTAX  DisplayString (SIZE (12))
	      ACCESS  read-write
	      STATUS  mandatory
	      DESCRIPTION
		      "The Local MAC address for this switching entry."
	      ::= { fsSnaLlcFrCfgEntry 3 }

	fsSnaLlcFrLocalSAP OBJECT-TYPE
	      SYNTAX  DisplayString (SIZE (2))
	      ACCESS  read-write
	      STATUS  mandatory
	      DESCRIPTION
		      "The Local SAP for this switching entry."
	      ::= { fsSnaLlcFrCfgEntry 4 }

	fsSnaLlcFrLocalMapSAP OBJECT-TYPE
	      SYNTAX  DisplayString (SIZE (2))
	      ACCESS  read-write
	      STATUS  mandatory
	      DESCRIPTION
		      "The Local Mapped SAP for this switching entry.
		       This is used only in the case of RFC1490BNN
		       encapsulation, since multiplexed connections
		       will be distinguished by SAP, so a unique SAP is 
		       required for each source and destination end-node.
		       This entry must be unique for each MAC-SAP pair in
		       the configuration table.
		       This entry may be left blank for RFC1490BAN
		       encapsulation."
	      ::= { fsSnaLlcFrCfgEntry 5 }

	fsSnaLlcFrFRGptName OBJECT-TYPE
		SYNTAX  DisplayString (SIZE (1..12))
		ACCESS  read-write
		STATUS  mandatory
		DESCRIPTION  ""
		::= { fsSnaLlcFrCfgEntry 6 }

	fsSnaLlcFrRemoteMAC OBJECT-TYPE
	      SYNTAX  DisplayString (SIZE (12))
	      ACCESS  read-write
	      STATUS  mandatory
	      DESCRIPTION
		      "The Remote MAC address for this switching entry."
	      ::= { fsSnaLlcFrCfgEntry 7 }

	fsSnaLlcFrRemoteSAP OBJECT-TYPE
	      SYNTAX  DisplayString (SIZE (2))
	      ACCESS  read-write
	      STATUS  mandatory
	      DESCRIPTION
		      "The Remote SAP for this switching entry."
	      ::= { fsSnaLlcFrCfgEntry 8 }

	fsSnaLlcFrRemoteMapSAP OBJECT-TYPE
	      SYNTAX  DisplayString (SIZE (2))
	      ACCESS  read-write
	      STATUS  mandatory
	      DESCRIPTION
		      "The Remote Mapped SAP for this switching entry.
		       This is used only in the case of RFC1490BNN
		       encapsulation, since multiplexed connections will
		       be distinguished by SAP, so a unique SAP is required
		       for each source and destination end-node. This entry
		       must be unique for each MAC-SAP pair in the
		       configuration table.
		       This entry may be left blank for RFC1490BAN
		       encapsulation."
	      ::= { fsSnaLlcFrCfgEntry 9 }

	fsSnaLlcFrPriority OBJECT-TYPE
	      SYNTAX  INTEGER {
			immediate   (0),
			high        (1),
			medium	(2),
			low		(3)
			}
	      ACCESS  read-write
	      STATUS  mandatory
	      DESCRIPTION ""
	      ::= { fsSnaLlcFrCfgEntry 10 }

	fsSnaLlcFrXidProcessing OBJECT-TYPE
	      SYNTAX  INTEGER {
			  end-to-end-xid       (1),
			  respond-to-llc-xid   (4)
		      }
	      ACCESS  read-write
	      STATUS  mandatory
	      DESCRIPTION
		      "This object reflects the type of XID processing desired.
		      A value of 'END-TO-END-XID' indicates that end-nodes will 
		      respond to XID requests. A value of 'RESPOND-TO-LLC-XID'
		      indicates that Switching will respond to the XID request
		      received across the FR network or from an end-node."
	      ::= { fsSnaLlcFrCfgEntry 11 }

	fsSnaLlcFrAdminStatus OBJECT-TYPE
		SYNTAX  INTEGER {
			view   (1),
			add    (2),
                  delete (3),
                  modify (4)
			}
	      ACCESS  read-write
	      STATUS  mandatory
	      DESCRIPTION ""
	      ::= { fsSnaLlcFrCfgEntry 12}


-- ***************************************************************************
-- frad SNA SWITCHING SDLC-LLC CONFIGURATION TABLE

	fsSnaSdlcLlcCfgTable OBJECT-TYPE
	      SYNTAX  SEQUENCE OF FsSnaSdlcLlcCfgEntry
	      ACCESS  not-accessible
	      STATUS  mandatory
	      DESCRIPTION
		      "Configuration Table for SDLC-LLC Switching. This table
		      would contain the SDLC-LLC switching entries, indexed
		      by the table index 'fsSnaSdlcLlcIndex'."
	      ::= { fsSna 12 }

	FsSnaSdlcLlcCfgEntry ::= SEQUENCE {
		fsSnaSdlcLlcIndex             INTEGER,
		fsSnaSdlcLlcSdlcPortNum       INTEGER,
            fsSnaSdlcLlcCUAddr            DisplayString,
		fsSnaSdlcLlcEmuMAC            DisplayString,
		fsSnaSdlcLlcEmuSAP            DisplayString,
		fsSnaSdlcLlcRemoteMAC         DisplayString,
		fsSnaSdlcLlcRemoteSAP         DisplayString,
            fsSnaSdlcLlcFRGptName         DisplayString,
		fsSnaSdlcLlcXidProcessing     INTEGER,
		fsSnaSdlcLlcPUType            INTEGER,
		fsSnaSdlcLlcXidValue          DisplayString,
		fsSnaSdlcLlcAdminStatus       INTEGER
	      }

	fsSnaSdlcLlcCfgEntry OBJECT-TYPE
	      SYNTAX  FsSnaSdlcLlcCfgEntry
	      ACCESS  not-accessible
	      STATUS  mandatory
	      DESCRIPTION
		      "Config Table Entry for SDLC-LLC switching scenario."
	      INDEX   { fsSnaSdlcLlcIndex }
	      ::= { fsSnaSdlcLlcCfgTable 1 }

	fsSnaSdlcLlcIndex OBJECT-TYPE
	      SYNTAX  INTEGER
	      ACCESS  read-only
	      STATUS  mandatory
	      DESCRIPTION
		      "The index value which uniquely identifies this
		      SDLC-LLC switching configuration table entry."
	      ::= { fsSnaSdlcLlcCfgEntry 1 }

	fsSnaSdlcLlcSdlcPortNum OBJECT-TYPE
	      SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
	      ACCESS  read-write
	      STATUS  mandatory
	      DESCRIPTION
		      "The SDLC Port for this switching entry."
	      ::= { fsSnaSdlcLlcCfgEntry 2 }
	  
	fsSnaSdlcLlcCUAddr OBJECT-TYPE
	      SYNTAX  DisplayString (SIZE(2))
	      ACCESS  read-write
	      STATUS  mandatory
	      DESCRIPTION
		      "The SDLC Station Address for this switching entry."
	      ::= { fsSnaSdlcLlcCfgEntry 3 }
	  
	fsSnaSdlcLlcEmuMAC OBJECT-TYPE
	      SYNTAX  DisplayString (SIZE (12))
	      ACCESS  read-write
	      STATUS  mandatory
	      DESCRIPTION
		      "The Pseudo-MAC address for this switching entry, which
		      identifies the SDLC Station."
	      ::= { fsSnaSdlcLlcCfgEntry 4 }

	fsSnaSdlcLlcEmuSAP OBJECT-TYPE
	      SYNTAX  DisplayString (SIZE (2))
	      ACCESS  read-write
	      STATUS  mandatory
	      DESCRIPTION
		      "The Pseudo-SAP for this switching entry, which identifies
		      the SDLC Station."
	      ::= { fsSnaSdlcLlcCfgEntry 5 }

	fsSnaSdlcLlcRemoteMAC OBJECT-TYPE
	      SYNTAX  DisplayString (SIZE (12))
	      ACCESS  read-write
	      STATUS  mandatory
	      DESCRIPTION
		      "The Remote MAC address for this switching entry,
		      which identifies the LLC end-node."
	      ::= { fsSnaSdlcLlcCfgEntry 6 }

	fsSnaSdlcLlcRemoteSAP OBJECT-TYPE
	      SYNTAX  DisplayString (SIZE (2))
	      ACCESS  read-write
	      STATUS  mandatory
	      DESCRIPTION
		      "The Remote SAP for this switching entry, which identifies
		      the LLC end-node."
	      ::= { fsSnaSdlcLlcCfgEntry 7 }

	fsSnaSdlcLlcFRGptName OBJECT-TYPE
		SYNTAX  DisplayString (SIZE (1..12))
		ACCESS  read-write
		STATUS  mandatory
		DESCRIPTION  ""
		::= { fsSnaSdlcLlcCfgEntry 8 }

	fsSnaSdlcLlcXidProcessing OBJECT-TYPE
	      SYNTAX  INTEGER {
			end-to-end-xid          (1),
			poll-llc-with-xid       (2),
			respond-to-sdlc-xid     (4),
			respond-to-llc-xid      (8)
		      }
	      ACCESS  read-write
	      STATUS  mandatory
	      DESCRIPTION
		      "This object reflects the type of XID processing desired.
		      A value of 'END-TO-END-XID' indicates that end-nodes will 
		      respond to XID requests. A value of 'POLL-LLC-WITH-XID'
		      indicates that Switching will send a XID request when it
		      receives a TEST request from the LLC. A value of 
		      'RESPOND-TO-SDLC-XID' indicates that Switching will
		      respond to a XID request from an SDLC end-node. A value
		      of 'RESPOND-TO-LLC-XID' indicates that Switching will
		      respond to the LLC XID request."
	      ::= { fsSnaSdlcLlcCfgEntry 9 }

	fsSnaSdlcLlcPUType OBJECT-TYPE
	      SYNTAX  INTEGER {
			pu1-0	(1),
			pu2-0   (2),
			pu4-0   (4)
		      }
	      ACCESS  read-write
	      STATUS  optional
	      DESCRIPTION
		      "The Physical Unit Type for Xid Processing."
	      ::= { fsSnaSdlcLlcCfgEntry 10 }

	fsSnaSdlcLlcXidValue OBJECT-TYPE
	      SYNTAX  DisplayString (SIZE (8))
	      ACCESS  read-write
	      STATUS  optional
	      DESCRIPTION     
		      "The XID string that may be used in XID, when
		      Switching responds to XID requests."
	      ::= { fsSnaSdlcLlcCfgEntry 11 }

	fsSnaSdlcLlcAdminStatus OBJECT-TYPE
		SYNTAX  INTEGER {
			view   (1),
			add    (2),
                  delete (3),
                  modify (4)
			}
	      ACCESS  read-write
	      STATUS  mandatory
	      DESCRIPTION ""
	      ::= { fsSnaSdlcLlcCfgEntry 12 }


-- ***************************************************************************
-- frad SNA SWITCHING SDLC-QLLC CONFIGURATION TABLE

--          fsSnaSdlcQllcCfgTable OBJECT-TYPE
--              SYNTAX  SEQUENCE OF SwSdlcQllcCfgEntry
--              ACCESS  not-accessible
--              STATUS  mandatory
--              DESCRIPTION
--                      "Configuration Table for SDLC-QLLC Switching. This table
--                      would contain the SDLC-QLLC switching entries, indexed by
--                      the table index 'fsSnaSdlcQllcIndex'."
--              ::= { fsSna 13 }

--          FsSnaSdlcQllcCfgEntry ::= SEQUENCE {
--              fsSnaSdlcQllcIndex         INTEGER,    
--              fsSnaSdlcQllcSdlcPortNum   INTEGER,    
--              fsSnaSdlcQllcSdlcStnAddr   DisplayString,    
--              fsSnaSdlcQllcGPTName       DisplayString,
--              fsSnaSdlcQllcSubAddress    DisplayString,
--              fsSnaSdlcQllcCallInit      INTEGER,
--              fsSnaSdlcQllcXidProcessing INTEGER,
--              fsSnaSdlcQllcPUType        INTEGER,
--              fsSnaSdlcQllcXidValue      DisplayString,
--              fsSnaSdlcQllcAdminStatus   INTEGER
--              }

--          fsSnaSdlcQllcCfgEntry OBJECT-TYPE
--              SYNTAX  FsSnaSdlcQllcCfgEntry
--              ACCESS  not-accessible
--              STATUS  mandatory
--              DESCRIPTION
--                      "Configuration Table Entry for SDLC-QLLC
--                       switching scenario."
--              INDEX   { fsSnaSdlcQllcIndex }
--              ::= { fsSnaSdlcQllcCfgTable 1 }

--          fsSnaSdlcQllcIndex OBJECT-TYPE
--              SYNTAX  INTEGER
--              ACCESS  read-only
--              STATUS  mandatory
--              DESCRIPTION
--                      "The index value which uniquely identifies this
--                      SDLC-QLLC switching configuration table entry."
--              ::= { fsSnaSdlcQllcCfgEntry 1 }

--          fsSnaSdlcQllcSdlcPortNum OBJECT-TYPE
--		  SYNTAX  INTEGER {
--			port1		(1),
--			port2       (2),
--			port3       (3),
--			port4       (4),
--			port5       (5),
--			port6		(6),
--			port7       (7),
--			port8       (8),
--			port9       (9),
--			portA      	(10),
--			portB		(11),
--			portC      	(12),
--			portD      	(13),
--			portE      	(14),
--			portF      	(15),
--			portG		(16),
--			portH      	(17),
--			portI      	(18),
--			portJ      	(19)
--			}
--              ACCESS  read-write
--              STATUS  mandatory
--              DESCRIPTION
--                      "The SDLC Port for this switching entry."
--              ::= { fsSnaSdlcQllcCfgEntry 2 }
 
--          fsSnaSdlcQllcSdlcStnAddr OBJECT-TYPE
--              SYNTAX  DisplayString (SIZE(2)) 
--              ACCESS  read-write
--              STATUS  mandatory
--              DESCRIPTION
--                      "The SDLC Station Address for this switching entry."
--              ::= { fsSnaSdlcQllcCfgEntry 3 }

--          fsSnaSdlcQllcGPTName OBJECT-TYPE
--              SYNTAX  DisplayString (SIZE (10))
--              ACCESS  read-write
--             STATUS  mandatory
--              DESCRIPTION
--                      "The GPT name for this switching entry."
--              ::= { fsSnaSdlcQllcCfgEntry 4 }

--          fsSnaSdlcQllcSubAddress OBJECT-TYPE
--              SYNTAX  DisplayString (SIZE (4))
--              ACCESS  read-write
--              STATUS  mandatory
--              DESCRIPTION
--                      "The QLLC sub-address for this switching entry."
--              ::= { fsSnaSdlcQllcCfgEntry 5 }

--          fsSnaSdlcQllcCallInit OBJECT-TYPE
--              SYNTAX  INTEGER {
--                          call-acceptor        (0),
--                          call-initiator       (1)
--                      }
--              ACCESS  read-write
--              STATUS  mandatory
--              DESCRIPTION
--                      "This variable indicates whether this session will
--                       initiate the X.25 call or wait for the other end
--                       to establish the call."
--              ::= { fsSnaSdlcQllcCfgEntry 6 }

--          fsSnaSdlcQllcXidProcessing OBJECT-TYPE
--              SYNTAX  INTEGER {
--                          end-to-end-xid       (1),
--                          respond-to-sdlc-xid  (4),
--                          poll-qllc-with-xid   (16),
--                          respond-to-qllc-xid  (32)
--                      }
--              ACCESS  read-write
--              STATUS  mandatory
--              DESCRIPTION
--                      "This object reflects the type of XID processing desired."
--              ::= { fsSnaSdlcQllcCfgEntry 7 }

--          fsSnaSdlcQllcPUType OBJECT-TYPE
--              SYNTAX  INTEGER {
--                              none  (0),  
--                              pu1-0 (1),
--                              pu2-0 (2),
--                              pu4-0 (4)
--                      }   
--              ACCESS  read-write
--              STATUS  optional
--              DESCRIPTION
--                      "The Physical Unit Type for Xid Processing."
--              ::= { fsSnaSdlcQllcCfgEntry 8 }

--          fsSnaSdlcQllcXidValue OBJECT-TYPE
--              SYNTAX  DisplayString (SIZE (0..8))
--              ACCESS  read-write
--              STATUS  optional
--              DESCRIPTION     
--                      "The XID string to be used in XID for 'POLL-QLLC-WITH-XID'
--                       'RESPOND-TO-SDLC-XID' and 'RESPOND-TO-QLLC-XID'."
--              ::= { fsSnaSdlcQllcCfgEntry 9 }

--          fsSnaSdlcQllcAdminStatus OBJECT-TYPE
--              SYNTAX  INTEGER {
--                          up      (2),
--                        invalid (3)
--                    }
--            ACCESS  read-write
--            STATUS  mandatory
--            DESCRIPTION
--                    "This object reflects the desired status of this
--                     switching entry. If the value of this object is
--                     set to 'down', then the session associated with
--                     this switching entry is released. If the value of
--                     this object is set to 'up' then a session is created
--                     for this switching entry and the SDLC module is
--                     notified of this. If the value of this object is
--                     set to 'invalid' then the session associated with
--                     this switching entry is released and the switching
--                     entry is deleted."
--            ::= { fsSnaSdlcQllcCfgEntry 10 }


-- ***************************************************************************
-- frad SNA SWITCHING LLC-QLLC CONFIGURATION TABLE

--        fsSnaLlcQllcCfgTable OBJECT-TYPE
--            SYNTAX  SEQUENCE OF SwLlcQllcCfgEntry
--            ACCESS  not-accessible
--            STATUS  mandatory
--            DESCRIPTION
--                    "Configuration Table for LLC-QLLC Switching. This table
--                    would contain the LLC-QLLC switching entries, indexed by
--                    the table index 'fsSnaLlcQllcIndex'."
--            ::= { fsSna 14 }

--        fsSnaLlcQllcCfgEntry OBJECT-TYPE
--            SYNTAX  SwLlcQllcCfgEntry
--            ACCESS  not-accessible
--            STATUS  mandatory
--            DESCRIPTION
--                    "Configuration Table Entry for LLC-QLLC switching scenario."
--            INDEX   { fsSnaLlcQllcIndex }
--            ::= { fsSnaLlcQllcCfgTable 1 }

--        SwLlcQllcCfgEntry ::= SEQUENCE {
--            fsSnaLlcQllcIndex          INTEGER,
--            fsSnaLlcQllcLocalMAC       DisplayString, 
--            fsSnaLlcQllcRemoteMAC      DisplayString,
--            fsSnaLlcQllcLocalSAP       DisplayString,
--            fsSnaLlcQllcRemoteSAP      DisplayString,
--            fsSnaLlcQllcGPTName        DisplayString,
--            fsSnaLlcQllcSubAddress     DisplayString,
--            fsSnaLlcQllcCallInit       INTEGER,
--            fsSnaLlcQllcXidProcessing  INTEGER,
--            fsSnaLlcQllcPUType         INTEGER,
--            fsSnaLlcQllcXidValue       DisplayString,
--            fsSnaLlcQllcAdminStatus    INTEGER
--            }

--        fsSnaLlcQllcIndex OBJECT-TYPE
--            SYNTAX  INTEGER
--           ACCESS  read-only
--            STATUS  mandatory
--            DESCRIPTION
--                    "The index value which uniquely identifies this
--                    LLC-QLLC switching configuration table entry."
--            ::= { fsSnaLlcQllcCfgEntry 1 }

--        fsSnaLlcQllcLocalMAC OBJECT-TYPE
--            SYNTAX  DisplayString (SIZE (6))
--            ACCESS  read-write
--            STATUS  mandatory
--            DESCRIPTION
--                    "The Local MAC address for this switching entry."
--            ::= { fsSnaLlcQllcCfgEntry 2 }

--        fsSnaLlcQllcRemoteMAC OBJECT-TYPE
--            SYNTAX  DisplayString (SIZE (6))
--            ACCESS  read-write
--            STATUS  mandatory
--            DESCRIPTION
--                    "The Remote MAC address for this switching entry."
--            ::= { fsSnaLlcQllcCfgEntry 3 }

--        fsSnaLlcQllcLocalSAP OBJECT-TYPE
--            SYNTAX  DisplayString (SIZE (1))
--            ACCESS  read-write
--            STATUS  mandatory
--            DESCRIPTION
--                    "The Local SAP for this switching entry."
--            ::= { fsSnaLlcQllcCfgEntry 4 }

--        fsSnaLlcQllcRemoteSAP OBJECT-TYPE
--            SYNTAX  DisplayString (SIZE (1))
--            ACCESS  read-write
--            STATUS  mandatory
--            DESCRIPTION
--                    "The Remote SAP for this switching entry."
--            ::= { fsSnaLlcQllcCfgEntry 5 }
 
--        fsSnaLlcQllcGPTName OBJECT-TYPE
--            SYNTAX  DisplayString (SIZE (10))
--            ACCESS  read-write
--            STATUS  mandatory
--            DESCRIPTION
--                    "The GPT name for this switching entry."
--            ::= { fsSnaLlcQllcCfgEntry 8 }

--        fsSnaLlcQllcSubAddress OBJECT-TYPE
--            SYNTAX  DisplayString (SIZE (4))
--            ACCESS  read-write
--            STATUS  mandatory
--            DESCRIPTION
--                    "The QLLC sub-address for this switching entry."
--            ::= { fsSnaLlcQllcCfgEntry 9 }

--        fsSnaLlcQllcCallInit OBJECT-TYPE
--            SYNTAX  INTEGER {
--                        call-acceptor        (0),
--                        call-initiator       (1)
--                    }
--            ACCESS  read-write
--            STATUS  mandatory
--            DESCRIPTION
--                    "This variable indicates whether this session will
--                     initiate the X.25 call or wait for the other end
--                     to establish the call."
--            ::= { fsSnaLlcQllcCfgEntry 10 }

--        fsSnaLlcQllcXidProcessing OBJECT-TYPE
--            SYNTAX  INTEGER {
--                        end-to-end-xid       (1),
--                        poll-llc-with-xid    (2),
--                        respond-to-llc-xid   (8),
--                        poll-llc-with-learn-xid  (64)
--                    }
--            ACCESS  read-write
--            STATUS  mandatory
--            DESCRIPTION
--                    "This object reflects the type of XID processing desired."
--            ::= { fsSnaLlcQllcCfgEntry 11 }

--        fsSnaLlcQllcPUType OBJECT-TYPE
--            SYNTAX  INTEGER {
--                            none  (0),  
--                            pu1-0 (1),
--                            pu2-0 (2),
--                            pu4-0 (4)
--                    }   
--            ACCESS  read-write
--            STATUS  optional
--            DESCRIPTION
--                    "The Physical Unit Type for Xid Processing."
--            ::= { fsSnaLlcQllcCfgEntry 12 }

--        fsSnaLlcQllcXidValue OBJECT-TYPE
--            SYNTAX  DisplayString (SIZE (0..8))
--            ACCESS  read-write
--            STATUS  optional
--            DESCRIPTION     
--                    "The XID string to be used in XID for 'POLL-LLC-WITH-XID'
--                     'RESPOND-TO-LLC-XID'."
--            ::= { fsSnaLlcQllcCfgEntry 13 }

--        fsSnaLlcQllcAdminStatus OBJECT-TYPE
--            SYNTAX  INTEGER {
--                        up      (2),
--                        invalid (3)
--                    }
--            ACCESS  read-write
--            STATUS  mandatory
--            DESCRIPTION
--                    "This object reflects the desired status of this
--                     switching entry. If the value of this object is
--                     set to 'down', then the session associated with
--                     this switching entry is released. If the value of
--                     this object is set to 'up' then a session is created
--                     for this switching entry and the LLC module is
--                     notified of this. If the value of this object is
--                     set to 'invalid' then the session associated with
--                     this switching entry is released and the switching
--                     entry is deleted."
--            ::= { fsSnaLlcQllcCfgEntry 14 }

-- ***************************************************************************
-- frad New X.25 Global Parameters & X.25 Switching Table

fsX25NewGlob OBJECT IDENTIFIER ::= { fsRouting 8 }

	fsX25NewGlobPropIdleVCTimer OBJECT-TYPE
	      SYNTAX  INTEGER (0..600)
	      ACCESS  read-write
	      STATUS  mandatory
	      DESCRIPTION ""
	      ::= { fsX25NewGlob 1 }

	fsX25NewGlobSNAIdleVCTimer OBJECT-TYPE
	      SYNTAX  INTEGER (0..600)
	      ACCESS  read-write
	      STATUS  mandatory
	      DESCRIPTION ""
	      ::= { fsX25NewGlob 2 }

	fsX25NewGlobIPIdleVCTimer OBJECT-TYPE
	      SYNTAX  INTEGER (0..600)
	      ACCESS  read-write
	      STATUS  mandatory
	      DESCRIPTION
		      "This object reflects the IP/IPX Idle VC Timer in
                       seconds."
	      ::= { fsX25NewGlob 3 }

	fsX25NewGlobTCHRecallTimer OBJECT-TYPE
	      SYNTAX  INTEGER (0..600)
	      ACCESS  read-write
	      STATUS  mandatory
	      DESCRIPTION
		      "This object reflects the TCh Recall Timer in seconds."
	      DEFVAL  { 60 }
	      ::= { fsX25NewGlob 4 }

	fsX25NewGlobTCHRecallCount OBJECT-TYPE
	      SYNTAX  INTEGER (0..10)
	      ACCESS  read-write
	      STATUS  mandatory
	      DESCRIPTION
		      "This object reflects the maximum TCH call retries."
	      DEFVAL  { 3 }
	      ::= { fsX25NewGlob 5 }

	fsX25NewGlobSubAddressLength OBJECT-TYPE
	      SYNTAX  INTEGER (1..5)
	      ACCESS  read-write
	      STATUS  mandatory
	      DESCRIPTION
		      ""
	      DEFVAL  { 2 }
	      ::= { fsX25NewGlob 6 }

        fsX25NewGlobSwTable OBJECT-TYPE
	        SYNTAX  SEQUENCE OF FsX25NewGlobSwEntry
	        ACCESS  not-accessible
	        STATUS  mandatory
	        ::= { fsX25NewGlob 7 }

FsX25NewGlobSwEntry ::= SEQUENCE {
	fsX25NewGlobSwIndex         INTEGER,
	fsX25NewGlobSwDestAddr      DisplayString,
	fsX25NewGlobSwPort          INTEGER,
	fsX25NewGlobSwStatus        INTEGER
	}

	fsX25NewGlobSwEntry OBJECT-TYPE
            SYNTAX  FsX25NewGlobSwEntry
	      ACCESS  not-accessible
	      STATUS  mandatory
	      DESCRIPTION
			"Configuration Table Entry for X.25 Switching Table"
	      INDEX { fsX25NewGlobSwIndex }
	      ::= { fsX25NewGlobSwTable 1 }

	fsX25NewGlobSwIndex OBJECT-TYPE
	      SYNTAX  INTEGER
	      ACCESS  read-only
	      STATUS  mandatory
	      DESCRIPTION
		      "The index value if X.25 Switching Table."
	      ::= { fsX25NewGlobSwEntry 1 }

	fsX25NewGlobSwDestAddr OBJECT-TYPE
	      SYNTAX  DisplayString (SIZE (15))
	      ACCESS  read-write
	      STATUS  mandatory
	      DESCRIPTION
		      "The Destination address for X.25 Switching."
	      ::= { fsX25NewGlobSwEntry 2 }

	fsX25NewGlobSwPort OBJECT-TYPE
		SYNTAX  INTEGER {
			portN		(1),
			port1       (2),
			port2       (3),
			port3       (4),
			port4       (5),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29)
			}
	      ACCESS  read-write
	      STATUS  mandatory
	      DESCRIPTION
		      "The output port for X.25 Switching, i.e. the port
                       through which the Destination Address can be reached."
	      ::= { fsX25NewGlobSwEntry 3 }

	fsX25NewGlobSwStatus OBJECT-TYPE
	      SYNTAX  INTEGER {
            	view    (1),
                  add     (2),
                  delete  (3),
                  modify  (4)
                  }
	      ACCESS  read-write
	      STATUS  mandatory
	      DESCRIPTION
		      "The index value if X.25 Switching Table."
	      ::= { fsX25NewGlobSwEntry 4 }

-- ***************************************************************************
-- frad GPT Parameters

	fsGPTTable OBJECT-TYPE
		SYNTAX  SEQUENCE OF FsGPTEntry
	      ACCESS  not-accessible
	      STATUS  mandatory
	      ::= { fsGpt 1 }

	FsGPTEntry ::= SEQUENCE {
		fsGPTIndex             INTEGER,
		fsGPTPathName          DisplayString,
		fsGPTPathType          INTEGER,
		fsGPTPort              INTEGER,
            fsGPTDLCINum           DisplayString,
		fsGPTX121SrcAddress    DisplayString,
		fsGPTX121DestAddress   DisplayString,
            fsGPTBackupPathName    DisplayString,
		fsGPTSVCSrcAddress     DisplayString,
		fsGPTSVCDestAddress    DisplayString,
		fsGPTPVCNumber         DisplayString,
            fsGPTIPDestAddress     DisplayString,
            fsGPTUDPPort           DisplayString,
            fsGPTChan              INTEGER,
		fsGPTAdminStatus       INTEGER
	      }

	fsGPTEntry OBJECT-TYPE
            SYNTAX  FsGPTEntry
	      ACCESS  not-accessible
	      STATUS  mandatory
	      DESCRIPTION ""
	      INDEX { fsGPTIndex }
	      ::= { fsGPTTable 1 }

	fsGPTIndex OBJECT-TYPE
	      SYNTAX  INTEGER
	      ACCESS  read-only
	      STATUS  mandatory
	      DESCRIPTION ""
	      ::= { fsGPTEntry 1 }

	fsGPTPathName OBJECT-TYPE
            SYNTAX  DisplayString (SIZE (10))
	      ACCESS  read-write
	      STATUS  mandatory
	      DESCRIPTION ""
	      ::= { fsGPTEntry 2 }

	fsGPTPathType OBJECT-TYPE
	      SYNTAX  INTEGER {
            	x25-svc     	(0),
                  x25-pvc     	(1),
                  fr-svc      	(2),
                  fr-pvc      	(3),
                  ser-port    	(4),
                  ip-udp      	(5),
                  voice       	(6),
                  fr-multicasting   (7)                
                  }
	      ACCESS  read-write
	      STATUS  mandatory
	      DESCRIPTION ""
	      ::= { fsGPTEntry 3 }

	fsGPTPort OBJECT-TYPE
	      SYNTAX  INTEGER {
			portN		(1),
			port1       (2),
			port2       (3),
			port3       (4),
			port4       (5),
			port5		(6),
			port10      (10),
			port11	(11),
			port12      (12),
			port13      (13),
			port14      (14),
			port15      (15),
			port16	(16),
			port17      (17),
			port18      (18),
			port19      (19),
                  port20      (20),
                  port21      (21),
                  port22      (22),
                  port23      (23),
                  port24      (24),
                  port25      (25),
                  port26      (26),
                  port27      (27),
                  port28      (28),
                  port29      (29),
                  n-a          (222)
                  }
	      ACCESS  read-write
	      STATUS  mandatory
	      DESCRIPTION ""
	      ::= { fsGPTEntry 4 }

	fsGPTDLCINum OBJECT-TYPE
            SYNTAX  DisplayString (SIZE (4))
	      ACCESS  read-write
	      STATUS  mandatory
	      DESCRIPTION ""
	      ::= { fsGPTEntry 5 }

	fsGPTX121SrcAddress OBJECT-TYPE
	      SYNTAX  DisplayString (SIZE (15))
	      ACCESS  read-write
	      STATUS  mandatory
	      DESCRIPTION ""
	      ::= { fsGPTEntry 6 }

	fsGPTX121DestAddress OBJECT-TYPE
	      SYNTAX  DisplayString (SIZE (15))
	      ACCESS  read-write
	      STATUS  mandatory
	      DESCRIPTION ""
	      ::= { fsGPTEntry 7 }

	fsGPTBackupPathName OBJECT-TYPE
            SYNTAX  DisplayString (SIZE (10))
	      ACCESS  read-write
	      STATUS  mandatory
	      DESCRIPTION ""
	      ::= { fsGPTEntry 8 }

	fsGPTSVCSrcAddress OBJECT-TYPE
	      SYNTAX  DisplayString (SIZE (15))
	      ACCESS  read-write
	      STATUS  mandatory
	      DESCRIPTION ""
	      ::= { fsGPTEntry 9 }

	fsGPTSVCDestAddress OBJECT-TYPE
	      SYNTAX  DisplayString (SIZE (15))
	      ACCESS  read-write
	      STATUS  mandatory
	      DESCRIPTION ""
	      ::= { fsGPTEntry 10 }

	fsGPTPVCNumber OBJECT-TYPE
            SYNTAX  DisplayString (SIZE (4))
	      ACCESS  read-write
	      STATUS  mandatory
	      DESCRIPTION ""
	      ::= { fsGPTEntry 11 }

	fsGPTIPDestAddress OBJECT-TYPE
	      SYNTAX  DisplayString (SIZE (15))
	      ACCESS  read-write
	      STATUS  mandatory
	      DESCRIPTION ""
	      ::= { fsGPTEntry 12 }

	fsGPTUDPPort OBJECT-TYPE
            SYNTAX  DisplayString (SIZE (5))
	      ACCESS  read-write
	      STATUS  mandatory
	      DESCRIPTION ""
	      ::= { fsGPTEntry 13 }

	fsGPTChan OBJECT-TYPE
		SYNTAX  INTEGER {
			chan1		(1),
			chan2       (2),
			chan3       (3),
			chan4       (4),
			chan5       (5),
			chan6		(6),
			chan7       (7),
			chan8       (8),
			chan9       (9),
			chan10	(10),
                  chan11	(11),
			chan12	(12),
			chan13	(13),
			chan14	(14),
			chan15	(15),
			chan16	(16),
			chan17	(17),
			chan18	(18),
			chan19	(19),
			chan20	(20),
			chan21	(21),
                  chan22	(22),
			chan23	(23),
			chan24	(24),
			chan25	(25),
			chan26	(26),
			chan27	(27),
			chan28	(28),
			chan29	(29),
			chan30	(30),
                  n-a          (222)
			}
	      ACCESS  read-write
	      STATUS  mandatory
	      DESCRIPTION ""
	      ::= { fsGPTEntry 14 }

   	fsGPTAdminStatus OBJECT-TYPE
      	SYNTAX  INTEGER {
			view   (1),
			add    (2),
			delete (3),
			modify (4)		
                  }
            ACCESS  read-write
            STATUS  mandatory
            DESCRIPTION ""
            ::= { fsGPTEntry 15 }

-- ***************************************************************************
-- frad GPT FR Multicasting Table

	fsFRMTable OBJECT-TYPE
		SYNTAX  SEQUENCE OF FsFRMEntry
	      ACCESS  not-accessible
	      STATUS  mandatory
	      ::= { fsGpt 2 }

	FsFRMEntry ::= SEQUENCE {
		fsFRMIndex             INTEGER,
		fsFRMPathName          DisplayString,
            fsFRMMemberPathName    DisplayString,
		fsFRMStatus            INTEGER
	      }

	fsFRMEntry OBJECT-TYPE
            SYNTAX  FsFRMEntry
	      ACCESS  not-accessible
	      STATUS  mandatory
	      DESCRIPTION ""
	      INDEX { fsFRMIndex }
	      ::= { fsFRMTable 1 }

	fsFRMIndex OBJECT-TYPE
	      SYNTAX  INTEGER
	      ACCESS  read-only
	      STATUS  mandatory
	      DESCRIPTION ""
	      ::= { fsFRMEntry 1 }

	fsFRMPathName OBJECT-TYPE
            SYNTAX  DisplayString (SIZE (10))
	      ACCESS  read-write
	      STATUS  mandatory
	      DESCRIPTION ""
	      ::= { fsFRMEntry 2 }

	fsFRMMemberPathName OBJECT-TYPE
            SYNTAX  DisplayString (SIZE (10))
	      ACCESS  read-write
	      STATUS  mandatory
	      DESCRIPTION ""
	      ::= { fsFRMEntry 3 }

   	fsFRMStatus OBJECT-TYPE
      	SYNTAX  INTEGER {
			view   (1),
			add    (2),
			delete (3)	
                  }
            ACCESS  read-write
            STATUS  mandatory
            DESCRIPTION ""
            ::= { fsFRMEntry 4 }

-- ***************************************************************************
-- T-1 CSU/DSC Configuration

fsT1DsuFrameFormat OBJECT-TYPE
	SYNTAX  INTEGER {
		d4          (1),
		esf         (2),
		unframed    (3)
	      } 
	ACCESS  read-write
      STATUS  mandatory
      DESCRIPTION  ""
      ::= { fsT1DsuConfig 1 }

fsT1DsuLineCode OBJECT-TYPE
	SYNTAX  INTEGER {
		ami         (1),
		b8zs        (2)
	      } 
	ACCESS  read-write
      STATUS  mandatory
      DESCRIPTION  ""
      ::= { fsT1DsuConfig 2 }

fsT1DsuBitStuffing OBJECT-TYPE
	SYNTAX  INTEGER {
		enable      (1),
		disable     (2)
	      } 
	ACCESS  read-write
      STATUS  mandatory
      DESCRIPTION  ""
      ::= { fsT1DsuConfig 3 }

fsT1DsuLineBuildOut OBJECT-TYPE
	SYNTAX  INTEGER {
		db0         (0),
		db-7-5      (1),
		db-15       (2),
     		db-22-5     (3),
    		ft133       (4),
		ft266       (5),
	  	ft399       (6),
		ft533       (7),
		ft655       (8)
	      } 
	ACCESS  read-write
      STATUS  mandatory
      DESCRIPTION  ""
      ::= { fsT1DsuConfig 4 }

fsT1DsuClock OBJECT-TYPE
	SYNTAX  INTEGER {
		line        (1),
		internal    (2)
	      } 
	ACCESS  read-write
      STATUS  mandatory
      DESCRIPTION  ""
      ::= { fsT1DsuConfig 5 }

fsT1DsuLineLoopBack OBJECT-TYPE
	SYNTAX  INTEGER {
		enable      (1),
		disable     (2)
	      } 
	ACCESS  read-write
      STATUS  mandatory
      DESCRIPTION  ""
      ::= { fsT1DsuConfig 6 }

fsT1DsuTimeSlotDataRate OBJECT-TYPE
	SYNTAX  INTEGER {
		k48         (1),
		k56         (2),
		k64         (3)
	      } 
	ACCESS  read-write
      STATUS  mandatory
      DESCRIPTION  ""
      ::= { fsT1DsuConfig 7 }

fsT1DsuTimeSlots OBJECT-TYPE
	SYNTAX  DisplayString (SIZE (24))
	ACCESS  read-write
      STATUS  mandatory
      DESCRIPTION  ""
      ::= { fsT1DsuConfig 8 }

fsT1DsuTimeSlotDataType OBJECT-TYPE
	SYNTAX  INTEGER {
		normal      (1),
		invert      (2)
	      } 
	ACCESS  read-write
      STATUS  mandatory
      DESCRIPTION  ""
      ::= { fsT1DsuConfig 9 }

fsT1DsuYellowAlarm OBJECT-TYPE
	SYNTAX  INTEGER {
		enable      (1),
		disable     (2)
	      } 
	ACCESS  read-write
      STATUS  mandatory
      DESCRIPTION  ""
      ::= { fsT1DsuConfig 10 }

fsT1DsuLoopbackLocalAnalog OBJECT-TYPE
	SYNTAX  INTEGER {
		up       (1),
		down     (2)
	      } 
	ACCESS  read-write
      STATUS  mandatory
      DESCRIPTION  ""
      ::= { fsT1DsuConfig 11 }

fsT1DsuLoopbackLocalDigit OBJECT-TYPE
	SYNTAX  INTEGER {
		up       (1),
		down     (2)
	      } 
	ACCESS  read-write
      STATUS  mandatory
      DESCRIPTION  ""
      ::= { fsT1DsuConfig 12 }

fsT1DsuLoopbackRemoteAnalog OBJECT-TYPE
	SYNTAX  INTEGER {
		up       (1),
		down     (2)
	      } 
	ACCESS  read-write
      STATUS  mandatory
      DESCRIPTION  ""
      ::= { fsT1DsuConfig 13 }

fsT1DsuLoopbackRemoteDigit OBJECT-TYPE
	SYNTAX  INTEGER {
		up       (1),
		down     (2)
	      } 
	ACCESS  read-write
      STATUS  mandatory
      DESCRIPTION  ""
      ::= { fsT1DsuConfig 14 }


-- ***************************************************************************
-- E-1 CSU/DSC Configuration

fsE1DsuFrameFormat OBJECT-TYPE
	SYNTAX  INTEGER {
		framed      (1),
		unframed    (2)
	      } 
	ACCESS  read-write
      STATUS  mandatory
      DESCRIPTION  ""
      ::= { fsE1DsuConfig 1 }

fsE1DsuCRC OBJECT-TYPE
	SYNTAX  INTEGER {
		enable      (1),
		disable     (2)
	      } 
	ACCESS  read-write
      STATUS  mandatory
      DESCRIPTION  ""
      ::= { fsE1DsuConfig 2 }

fsE1DsuClock OBJECT-TYPE
	SYNTAX  INTEGER {
		line        (1),
		internal    (2)
	      } 
	ACCESS  read-write
      STATUS  mandatory
      DESCRIPTION  ""
      ::= { fsE1DsuConfig 3 }

fsE1DsuLineLoop OBJECT-TYPE
	SYNTAX  INTEGER {
		activateloopback  (1),
		removeloopback    (2)
	      } 
	ACCESS  read-write
      STATUS  mandatory
      DESCRIPTION  ""
      ::= { fsE1DsuConfig 4 }

fsE1DsuTimeSlots OBJECT-TYPE
	SYNTAX  DisplayString (SIZE (24))
	ACCESS  read-write
      STATUS  mandatory
      DESCRIPTION  ""
      ::= { fsE1DsuConfig 5 }

fsE1DsuDataType OBJECT-TYPE
	SYNTAX  INTEGER {
		normal      (1),
		invert      (2)
	      } 
	ACCESS  read-write
      STATUS  mandatory
      DESCRIPTION  ""
      ::= { fsE1DsuConfig 6 }

fsE1DsuDisFrame OBJECT-TYPE
	SYNTAX  INTEGER {
		enable      (1),
		disable     (2)
	      } 
	ACCESS  read-write
      STATUS  mandatory
      DESCRIPTION  ""
      ::= { fsE1DsuConfig 7 }

fsE1DsuAISTrans OBJECT-TYPE
	SYNTAX  INTEGER {
		enable      (1),
		disable     (2)
	      } 
	ACCESS  read-write
      STATUS  mandatory
      DESCRIPTION  ""
      ::= { fsE1DsuConfig 8 }

-- ***************************************************************************
-- ISDN Configuration

fsIsdnEnable OBJECT-TYPE
	SYNTAX  INTEGER {
		enable      (1),
		disable     (2)
	      } 
	ACCESS  read-write
      STATUS  mandatory
      DESCRIPTION  ""
      ::= { fsIsdnConfig 1 }

fsIsdnLocalPhe1 OBJECT-TYPE
	SYNTAX  DisplayString (SIZE (32))
	ACCESS  read-write
      STATUS  mandatory
      DESCRIPTION  ""
      ::= { fsIsdnConfig 2 }

fsIsdnSPID1 OBJECT-TYPE
	SYNTAX  DisplayString (SIZE (32))
	ACCESS  read-write
      STATUS  mandatory
      DESCRIPTION  ""
      ::= { fsIsdnConfig 3 }

fsIsdnLocalPhe2 OBJECT-TYPE
	SYNTAX  DisplayString (SIZE (32))
	ACCESS  read-write
      STATUS  mandatory
      DESCRIPTION  ""
      ::= { fsIsdnConfig 4 }

fsIsdnSPID2 OBJECT-TYPE
	SYNTAX  DisplayString (SIZE (32))
	ACCESS  read-write
      STATUS  mandatory
      DESCRIPTION  ""
      ::= { fsIsdnConfig 5 }

fsIsdnSwitchSel OBJECT-TYPE
	SYNTAX  INTEGER {
		not-defined			(0),
  		att-5ess-sym		(1),
  		bri-5esssym-stype		(2),
  		nt-dms100			(3),
  		nt-dms-100s			(4),
  		national-isdn-1		(5),
  		national-isdn-2 		(6)
	      } 
	ACCESS  read-write
      STATUS  mandatory
      DESCRIPTION  ""
      ::= { fsIsdnConfig 6 }

-- ***************************************************************************
-- External Dialup Devices

	fsExtDialupDevTable OBJECT-TYPE
		SYNTAX  SEQUENCE OF FsExtDialupDevEntry
	      ACCESS  not-accessible
	      STATUS  mandatory
	      ::= { fsExtDialupDev 1 }

	FsExtDialupDevEntry ::= SEQUENCE {
		fsExtDevIndex          INTEGER,
		fsExtDevPort           INTEGER,
		fsExtDevModemType      INTEGER,
		fsExtDevStatus         INTEGER
	      }

	fsExtDialupDevEntry OBJECT-TYPE
            SYNTAX  FsExtDialupDevEntry
	      ACCESS  not-accessible
	      STATUS  mandatory
	      DESCRIPTION ""
	      INDEX { fsExtDevIndex }
	      ::= { fsExtDialupDevTable 1 }

	fsExtDevIndex OBJECT-TYPE
	      SYNTAX  INTEGER
	      ACCESS  read-only
	      STATUS  mandatory
	      DESCRIPTION ""
	      ::= { fsExtDialupDevEntry 1 }

	fsExtDevPort OBJECT-TYPE
	      SYNTAX  INTEGER {
			portN  	(1),
			port1     	(2),
			port2      	(3),
			port3      	(4),
			port4		(5),
			undefined	(100)
			}
	      ACCESS  read-write
	      STATUS  mandatory
	      DESCRIPTION ""
	      ::= { fsExtDialupDevEntry 2 }

	fsExtDevModemType OBJECT-TYPE
	      SYNTAX  INTEGER {
            	us-robotics (1),
                  rockwell    (2)
                  }
	      ACCESS  read-write
	      STATUS  mandatory
	      DESCRIPTION ""
      ::= { fsExtDialupDevEntry 3 }

   	fsExtDevStatus OBJECT-TYPE
      	SYNTAX  INTEGER {
			view   (1),
			add    (2),
			delete (3),
			modify (4)		
                  }
            ACCESS  read-write
            STATUS  mandatory
            DESCRIPTION ""
            ::= { fsExtDialupDevEntry 4}


-- ***************************************************************************
-- Fastcomm Voice Frad Configuration

fsChannelConfig OBJECT IDENTIFIER ::= { fsVoiceConfig 1 }

fsChanMainConfigTable OBJECT-TYPE
	SYNTAX  SEQUENCE OF FsChanMainConfigEntry
	ACCESS  not-accessible
	STATUS  mandatory
	DESCRIPTION  ""
	::= { fsChannelConfig 1 }

	FsChanMainConfigEntry ::= SEQUENCE {
		fsChanConfigChanNo			INTEGER,
            fsChanConfigAdminStatus             INTEGER,
		fsChanConfigVoiceProIx			INTEGER,
		fsChanConfigFaxProIx         		INTEGER,
		fsChanConfigModemProIx			INTEGER,
		fsChanConfigDataProIx			INTEGER,
            fsChanConfigFTMUPathName            DisplayString,
		fsChanConfigProBit			INTEGER,
		fsChanConfigCompandLaws			INTEGER,
		fsChanConfigTeleSigMode			INTEGER,
		fsChanConfigDialOutMode			INTEGER,
		fsChanConfigTeleSigProtocol		INTEGER,
		fsChanConfigRxGain			DisplayString,
		fsChanConfigTxGain         		DisplayString,
		fsChanConfigMainStatus			INTEGER
		}

	fsChanMainConfigEntry OBJECT-TYPE
		SYNTAX  FsChanMainConfigEntry
		ACCESS  not-accessible
		STATUS  mandatory
		DESCRIPTION  ""
		INDEX { fsChanConfigChanNo }
		::= { fsChanMainConfigTable 1 }

	fsChanConfigChanNo OBJECT-TYPE
		SYNTAX  INTEGER {
			chan1		(1),
			chan2       (2),
			chan3       (3),
			chan4       (4),
			chan5       (5),
			chan6		(6),
			chan7       (7),
			chan8       (8),
			chan9       (9),
			chan10	(10),
                  chan11	(11),
			chan12	(12),
			chan13	(13),
			chan14	(14),
			chan15	(15),
			chan16	(16),
			chan17	(17),
			chan18	(18),
			chan19	(19),
			chan20	(20),
			chan21	(21),
                  chan22	(22),
			chan23	(23),
			chan24	(24),
			chan25	(25),
			chan26	(26),
			chan27	(27),
			chan28	(28),
			chan29	(29),
			chan30	(30)
			}
		ACCESS  read-only
		STATUS  mandatory
		DESCRIPTION  ""
		::= { fsChanMainConfigEntry 1 }

	fsChanConfigAdminStatus OBJECT-TYPE
		SYNTAX  INTEGER {
			disabled      (1),
			enabled       (2)
			}
		ACCESS  read-write
		STATUS  mandatory
		DESCRIPTION ""
		::= { fsChanMainConfigEntry 2 }

	fsChanConfigVoiceProIx OBJECT-TYPE
		SYNTAX  INTEGER (0..10)
		ACCESS  read-write
		STATUS  mandatory
		DESCRIPTION ""
		::= { fsChanMainConfigEntry 3 }

	fsChanConfigFaxProIx OBJECT-TYPE
		SYNTAX  INTEGER (0..10)
		ACCESS  read-write
		STATUS  mandatory
		DESCRIPTION ""
		::= { fsChanMainConfigEntry 4 }

	fsChanConfigModemProIx OBJECT-TYPE
		SYNTAX  INTEGER (0..10)
		ACCESS  read-write
		STATUS  mandatory
		DESCRIPTION ""
		::= { fsChanMainConfigEntry 5 }

	fsChanConfigDataProIx OBJECT-TYPE
		SYNTAX  INTEGER (0..10)
		ACCESS  read-write
		STATUS  mandatory
		DESCRIPTION ""
		::= { fsChanMainConfigEntry 6 }

	fsChanConfigFTMUPathName OBJECT-TYPE
		SYNTAX  DisplayString
		ACCESS  read-write
		STATUS  mandatory
		DESCRIPTION ""
		::= { fsChanMainConfigEntry 7 }

	fsChanConfigProBit OBJECT-TYPE
		SYNTAX  INTEGER
		ACCESS  read-write
		STATUS  mandatory
		DESCRIPTION ""
		::= { fsChanMainConfigEntry 8 }

	fsChanConfigCompandLaws OBJECT-TYPE
		SYNTAX  INTEGER {
			u-law		(1),
			a-law       (2)
			}
		ACCESS  read-write
		STATUS  mandatory
		DESCRIPTION ""
		::= { fsChanMainConfigEntry 9 }

	fsChanConfigTeleSigMode OBJECT-TYPE
		SYNTAX  INTEGER {
			switch-cas		(1),
			switch-ccs       	(2),
                  tran-cas		(3),
			tran-ccs		(4)
			}
		ACCESS  read-write
		STATUS  mandatory
		DESCRIPTION ""
		::= { fsChanMainConfigEntry 10 }

	fsChanConfigDialOutMode OBJECT-TYPE
		SYNTAX  INTEGER {
			tone		(1),
			pulse       (2)
			}
		ACCESS  read-write
		STATUS  mandatory
		DESCRIPTION ""
		::= { fsChanMainConfigEntry 11 }

	fsChanConfigTeleSigProtocol OBJECT-TYPE
		SYNTAX  INTEGER {
			undefined			(1),
                  em-immediate		(2),
                  em-wink-start		(3),
                  em-delay-start		(4),
			fxs-loop-start       	(5),
                  fxs-ground-start		(6),
                  fxo-loop-start		(7),
			fxo-ground-start		(8)
			}
		ACCESS  read-write
		STATUS  mandatory
		DESCRIPTION ""
		::= { fsChanMainConfigEntry 12 }

	fsChanConfigRxGain OBJECT-TYPE
		SYNTAX  DisplayString
		ACCESS  read-write
		STATUS  mandatory
		DESCRIPTION ""
		::= { fsChanMainConfigEntry 13 }

	fsChanConfigTxGain OBJECT-TYPE
		SYNTAX  DisplayString
		ACCESS  read-write
		STATUS  mandatory
		DESCRIPTION ""
		::= { fsChanMainConfigEntry 14 }

	fsChanConfigMainStatus OBJECT-TYPE
		SYNTAX  INTEGER {
			view   (1),
			modify (2)
			}
		ACCESS  read-write
		STATUS  mandatory
		DESCRIPTION  ""
		::= { fsChanMainConfigEntry 15 }

fsChanMoreConfigTable OBJECT-TYPE
	SYNTAX  SEQUENCE OF FsChanMoreConfigEntry
	ACCESS  not-accessible
	STATUS  mandatory
	DESCRIPTION  ""
	::= { fsChannelConfig 2 }

	FsChanMoreConfigEntry ::= SEQUENCE {
		fsChanConfigMoreChanNo			INTEGER,
		fsChanConfigIdleNoiseLevel		DisplayString,
		fsChanConfigCallLimit			DisplayString,
		fsChanConfigWaitForAnswer		DisplayString,
		fsChanConfigWaitForHangup		DisplayString,
		fsChanConfigFaxHoldoverDelay		INTEGER,
		fsChanConfigOffHookDelay		INTEGER,
		fsChanConfigToneOnTime			INTEGER,
		fsChanConfigToneOffTime			INTEGER,
		fsChanConfigPriLineAutoRingdown	DisplayString,
		fsChanConfigTranDestChan		INTEGER,
		fsChanConfigTranSubChan			INTEGER,
		fsChanConfigMoreStatus			INTEGER
		}

	fsChanMoreConfigEntry OBJECT-TYPE
		SYNTAX  FsChanMoreConfigEntry
		ACCESS  not-accessible
		STATUS  mandatory
		DESCRIPTION  ""
		INDEX { fsChanConfigMoreChanNo }
		::= { fsChanMoreConfigTable 1 }

	fsChanConfigMoreChanNo OBJECT-TYPE
		SYNTAX  INTEGER {
			chan1		(1),
			chan2       (2),
			chan3       (3),
			chan4       (4),
			chan5       (5),
			chan6		(6),
			chan7       (7),
			chan8       (8),
			chan9       (9),
			chan10	(10),
                  chan11	(11),
			chan12	(12),
			chan13	(13),
			chan14	(14),
			chan15	(15),
			chan16	(16),
			chan17	(17),
			chan18	(18),
			chan19	(19),
			chan20	(20),
			chan21	(21),
                  chan22	(22),
			chan23	(23),
			chan24	(24),
			chan25	(25),
			chan26	(26),
			chan27	(27),
			chan28	(28),
			chan29	(29),
			chan30	(30)
			}
		ACCESS  read-only
		STATUS  mandatory
		DESCRIPTION  ""
		::= { fsChanMoreConfigEntry 1 }

	fsChanConfigIdleNoiseLevel OBJECT-TYPE
		SYNTAX  DisplayString
		ACCESS  read-write
		STATUS  mandatory
		DESCRIPTION ""
		::= { fsChanMoreConfigEntry 2 }

	fsChanConfigCallLimit OBJECT-TYPE
		SYNTAX  DisplayString
		ACCESS  read-write
		STATUS  mandatory
		DESCRIPTION ""
		::= { fsChanMoreConfigEntry 3 }

	fsChanConfigWaitForAnswer OBJECT-TYPE
		SYNTAX  DisplayString
		ACCESS  read-write
		STATUS  mandatory
		DESCRIPTION ""
		::= { fsChanMoreConfigEntry 4 }

	fsChanConfigWaitForHangup OBJECT-TYPE
		SYNTAX  DisplayString
		ACCESS  read-write
		STATUS  mandatory
		DESCRIPTION ""
		::= { fsChanMoreConfigEntry 5 }

	fsChanConfigFaxHoldoverDelay OBJECT-TYPE
		SYNTAX  INTEGER (0..5000)
		ACCESS  read-write
		STATUS  mandatory
		DESCRIPTION ""
		::= { fsChanMoreConfigEntry 6 }

	fsChanConfigOffHookDelay OBJECT-TYPE
		SYNTAX  INTEGER (0..5000)
		ACCESS  read-write
		STATUS  mandatory
		DESCRIPTION ""
		::= { fsChanMoreConfigEntry 7 }

	fsChanConfigToneOnTime OBJECT-TYPE
		SYNTAX  INTEGER (0..5000)
		ACCESS  read-write
		STATUS  mandatory
		DESCRIPTION ""
		::= { fsChanMoreConfigEntry 8 }

	fsChanConfigToneOffTime OBJECT-TYPE
		SYNTAX  INTEGER (0..5000)
		ACCESS  read-write
		STATUS  mandatory
		DESCRIPTION ""
		::= { fsChanMoreConfigEntry 9 }

	fsChanConfigPriLineAutoRingdown OBJECT-TYPE
		SYNTAX  DisplayString
		ACCESS  read-write
		STATUS  mandatory
		DESCRIPTION ""
		::= { fsChanMoreConfigEntry 10 }

	fsChanConfigTranDestChan OBJECT-TYPE
		SYNTAX  INTEGER 
		ACCESS  read-write
		STATUS  mandatory
		DESCRIPTION ""
		::= { fsChanMoreConfigEntry 11 }

	fsChanConfigTranSubChan OBJECT-TYPE
		SYNTAX  INTEGER 
		ACCESS  read-write
		STATUS  mandatory
		DESCRIPTION ""
		::= { fsChanMoreConfigEntry 12 }

	fsChanConfigMoreStatus OBJECT-TYPE
		SYNTAX  INTEGER {
			view   (1),
			modify (2)
			}
		ACCESS  read-write
		STATUS  mandatory
		DESCRIPTION  ""
		::= { fsChanMoreConfigEntry 13 }

fsFXSLoopStartConfigTable OBJECT-TYPE
	SYNTAX  SEQUENCE OF FsFXSLoopStartConfigEntry
	ACCESS  not-accessible
	STATUS  mandatory
	DESCRIPTION  ""
	::= { fsChannelConfig 3 }

	FsFXSLoopStartConfigEntry ::= SEQUENCE {
		fsFXSLoopChanNo			INTEGER,
		fsFXSLoopOffhookDebouInter    INTEGER,
            fsFXSLoopOnhookDebouInter	INTEGER,
		fsFXSLoopOffhookCondDecTime   INTEGER,
            fsFXSLoopOrgOnhookDecTime	INTEGER,
		fsFXSLoopRecOnhookDecTime	INTEGER,
            fsFXSLoopSupDisWaitTime		INTEGER,
		fsFXSLoopSupDisDurTime    	INTEGER,
            fsFXSLoopStatus			INTEGER
		}

	fsFXSLoopStartConfigEntry OBJECT-TYPE
		SYNTAX  FsFXSLoopStartConfigEntry
		ACCESS  not-accessible
		STATUS  mandatory
		DESCRIPTION  ""
		INDEX { fsFXSLoopChanNo }
		::= { fsFXSLoopStartConfigTable 1 }

	fsFXSLoopChanNo OBJECT-TYPE
		SYNTAX  INTEGER {
			chan1		(1),
			chan2       (2),
			chan3       (3),
			chan4       (4),
			chan5       (5),
			chan6		(6),
			chan7       (7),
			chan8       (8),
			chan9       (9),
			chan10	(10),
                  chan11	(11),
			chan12	(12),
			chan13	(13),
			chan14	(14),
			chan15	(15),
			chan16	(16),
			chan17	(17),
			chan18	(18),
			chan19	(19),
			chan20	(20),
			chan21	(21),
                  chan22	(22),
			chan23	(23),
			chan24	(24),
			chan25	(25),
			chan26	(26),
			chan27	(27),
			chan28	(28),
			chan29	(29),
			chan30	(30)
			}
		ACCESS  read-only
		STATUS  mandatory
		DESCRIPTION  ""
		::= { fsFXSLoopStartConfigEntry 1 }

	fsFXSLoopOffhookDebouInter OBJECT-TYPE
		SYNTAX  INTEGER (1..1000)
		ACCESS  read-write
		STATUS  mandatory
		DESCRIPTION ""
		::= { fsFXSLoopStartConfigEntry 2 }

	fsFXSLoopOnhookDebouInter OBJECT-TYPE
		SYNTAX  INTEGER (1..1000)
		ACCESS  read-write
		STATUS  mandatory
		DESCRIPTION ""
		::= { fsFXSLoopStartConfigEntry 3 }

	fsFXSLoopOffhookCondDecTime OBJECT-TYPE
		SYNTAX  INTEGER (1..1000)
		ACCESS  read-write
		STATUS  mandatory
		DESCRIPTION ""
		::= { fsFXSLoopStartConfigEntry 4 }

	fsFXSLoopOrgOnhookDecTime OBJECT-TYPE
		SYNTAX  INTEGER (1..60000)
		ACCESS  read-write
		STATUS  mandatory
		DESCRIPTION ""
		::= { fsFXSLoopStartConfigEntry 5 }

	fsFXSLoopRecOnhookDecTime OBJECT-TYPE
		SYNTAX  INTEGER (1..60000)
		ACCESS  read-write
		STATUS  mandatory
		DESCRIPTION ""
		::= { fsFXSLoopStartConfigEntry 6 }

	fsFXSLoopSupDisWaitTime OBJECT-TYPE
		SYNTAX  INTEGER (1..60000)
		ACCESS  read-write
		STATUS  mandatory
		DESCRIPTION ""
		::= { fsFXSLoopStartConfigEntry 7 }

	fsFXSLoopSupDisDurTime OBJECT-TYPE
		SYNTAX  INTEGER (1..60000)
		ACCESS  read-write
		STATUS  mandatory
		DESCRIPTION ""
		::= { fsFXSLoopStartConfigEntry 8 }

	fsFXSLoopStatus OBJECT-TYPE
		SYNTAX  INTEGER {
			view   (1),
			modify (2)
			}
		ACCESS  read-write
		STATUS  mandatory
		DESCRIPTION  ""
		::= { fsFXSLoopStartConfigEntry 9 }

fsFXOLoopStartConfigTable OBJECT-TYPE
	SYNTAX  SEQUENCE OF FsFXOLoopStartConfigEntry
	ACCESS  not-accessible
	STATUS  mandatory
	DESCRIPTION  ""
	::= { fsChannelConfig 4 }

	FsFXOLoopStartConfigEntry ::= SEQUENCE {
		fsFXOLoopChanNo			INTEGER,
		fsFXOLoopRingDebouInter    	INTEGER,
            fsFXOLoopRingInterPulseTime	INTEGER,
		fsFXOLoopRingInterCycleTime   INTEGER,
            fsFXOLoopDisDurTime		INTEGER,
		fsFXOLoopGuardOutTime		INTEGER,
            fsFXOLoopPortTimeout		INTEGER,
            fsFXOLoopStatus			INTEGER
		}

	fsFXOLoopStartConfigEntry OBJECT-TYPE
		SYNTAX  FsFXOLoopStartConfigEntry
		ACCESS  not-accessible
		STATUS  mandatory
		DESCRIPTION  ""
		INDEX { fsFXOLoopChanNo }
		::= { fsFXOLoopStartConfigTable 1 }

	fsFXOLoopChanNo OBJECT-TYPE
		SYNTAX  INTEGER {
			chan1		(1),
			chan2       (2),
			chan3       (3),
			chan4       (4),
			chan5       (5),
			chan6		(6),
			chan7       (7),
			chan8       (8),
			chan9       (9),
			chan10	(10),
                  chan11	(11),
			chan12	(12),
			chan13	(13),
			chan14	(14),
			chan15	(15),
			chan16	(16),
			chan17	(17),
			chan18	(18),
			chan19	(19),
			chan20	(20),
			chan21	(21),
                  chan22	(22),
			chan23	(23),
			chan24	(24),
			chan25	(25),
			chan26	(26),
			chan27	(27),
			chan28	(28),
			chan29	(29),
			chan30	(30)
			}
		ACCESS  read-only
		STATUS  mandatory
		DESCRIPTION  ""
		::= { fsFXOLoopStartConfigEntry 1 }

	fsFXOLoopRingDebouInter OBJECT-TYPE
		SYNTAX  INTEGER (1..1000)
		ACCESS  read-write
		STATUS  mandatory
		DESCRIPTION ""
		::= { fsFXOLoopStartConfigEntry 2 }

	fsFXOLoopRingInterPulseTime OBJECT-TYPE
		SYNTAX  INTEGER (1..60000)
		ACCESS  read-write
		STATUS  mandatory
		DESCRIPTION ""
		::= { fsFXOLoopStartConfigEntry 3 }

	fsFXOLoopRingInterCycleTime OBJECT-TYPE
		SYNTAX  INTEGER (1..60000)
		ACCESS  read-write
		STATUS  mandatory
		DESCRIPTION ""
		::= { fsFXOLoopStartConfigEntry 4 }

	fsFXOLoopDisDurTime OBJECT-TYPE
		SYNTAX  INTEGER (1..60000)
		ACCESS  read-write
		STATUS  mandatory
		DESCRIPTION ""
		::= { fsFXOLoopStartConfigEntry 5 }

	fsFXOLoopGuardOutTime OBJECT-TYPE
		SYNTAX  INTEGER (1..60000)
		ACCESS  read-write
		STATUS  mandatory
		DESCRIPTION ""
		::= { fsFXOLoopStartConfigEntry 6 }

	fsFXOLoopPortTimeout OBJECT-TYPE
		SYNTAX  INTEGER (1..60000)
		ACCESS  read-write
		STATUS  mandatory
		DESCRIPTION ""
		::= { fsFXOLoopStartConfigEntry 7 }

	fsFXOLoopStatus OBJECT-TYPE
		SYNTAX  INTEGER {
			view   (1),
			modify (2)
			}
		ACCESS  read-write
		STATUS  mandatory
		DESCRIPTION  ""
		::= { fsFXOLoopStartConfigEntry 8 }

fsFXSGroundStartConfigTable OBJECT-TYPE
	SYNTAX  SEQUENCE OF FsFXSGroundStartConfigEntry
	ACCESS  not-accessible
	STATUS  mandatory
	DESCRIPTION  ""
	::= { fsChannelConfig 5 }

	FsFXSGroundStartConfigEntry ::= SEQUENCE {
		fsFXSGroundChanNo				INTEGER,
		fsFXSGroundOffhookDebouInter    	INTEGER,
            fsFXSGroundOnhookDebouInter		INTEGER,
		fsFXSGroundOrgOnhookDecTime   	INTEGER,
            fsFXSGroundRecOnhookDecTime		INTEGER,
		fsFXSGroundMinRingGroundTime		INTEGER,
            fsFXSGroundMaxWaitCloseTime		INTEGER,
		fsFXSGroundMinWaitOpenTime		INTEGER,
            fsFXSGroundStatus				INTEGER
		}

	fsFXSGroundStartConfigEntry OBJECT-TYPE
		SYNTAX  FsFXSGroundStartConfigEntry
		ACCESS  not-accessible
		STATUS  mandatory
		DESCRIPTION  ""
		INDEX { fsFXSGroundChanNo }
		::= { fsFXSGroundStartConfigTable 1 }

	fsFXSGroundChanNo OBJECT-TYPE
		SYNTAX  INTEGER {
			chan1		(1),
			chan2       (2),
			chan3       (3),
			chan4       (4),
			chan5       (5),
			chan6		(6),
			chan7       (7),
			chan8       (8),
			chan9       (9),
			chan10	(10),
                  chan11	(11),
			chan12	(12),
			chan13	(13),
			chan14	(14),
			chan15	(15),
			chan16	(16),
			chan17	(17),
			chan18	(18),
			chan19	(19),
			chan20	(20),
			chan21	(21),
                  chan22	(22),
			chan23	(23),
			chan24	(24),
			chan25	(25),
			chan26	(26),
			chan27	(27),
			chan28	(28),
			chan29	(29),
			chan30	(30)
			}
		ACCESS  read-only
		STATUS  mandatory
		DESCRIPTION  ""
		::= { fsFXSGroundStartConfigEntry 1 }

	fsFXSGroundOffhookDebouInter OBJECT-TYPE
		SYNTAX  INTEGER (1..1000)
		ACCESS  read-write
		STATUS  mandatory
		DESCRIPTION ""
		::= { fsFXSGroundStartConfigEntry 2 }

	fsFXSGroundOnhookDebouInter OBJECT-TYPE
		SYNTAX  INTEGER (1..1000)
		ACCESS  read-write
		STATUS  mandatory
		DESCRIPTION ""
		::= { fsFXSGroundStartConfigEntry 3 }

	fsFXSGroundOrgOnhookDecTime OBJECT-TYPE
		SYNTAX  INTEGER (1..1000)
		ACCESS  read-write
		STATUS  mandatory
		DESCRIPTION ""
		::= { fsFXSGroundStartConfigEntry 4 }

	fsFXSGroundRecOnhookDecTime OBJECT-TYPE
		SYNTAX  INTEGER (1..1000)
		ACCESS  read-write
		STATUS  mandatory
		DESCRIPTION ""
		::= { fsFXSGroundStartConfigEntry 5 }

	fsFXSGroundMinRingGroundTime OBJECT-TYPE
		SYNTAX  INTEGER (1..1000)
		ACCESS  read-write
		STATUS  mandatory
		DESCRIPTION ""
		::= { fsFXSGroundStartConfigEntry 6 }

	fsFXSGroundMaxWaitCloseTime OBJECT-TYPE
		SYNTAX  INTEGER (1..1000)
		ACCESS  read-write
		STATUS  mandatory
		DESCRIPTION ""
		::= { fsFXSGroundStartConfigEntry 7 }

	fsFXSGroundMinWaitOpenTime OBJECT-TYPE
		SYNTAX  INTEGER (1..1000)
		ACCESS  read-write
		STATUS  mandatory
		DESCRIPTION ""
		::= { fsFXSGroundStartConfigEntry 8 }

	fsFXSGroundStatus OBJECT-TYPE
		SYNTAX  INTEGER {
			view   (1),
			modify (2)
			}
		ACCESS  read-write
		STATUS  mandatory
		DESCRIPTION  ""
		::= { fsFXSGroundStartConfigEntry 9 }

fsFXOGroundStartConfigTable OBJECT-TYPE
	SYNTAX  SEQUENCE OF FsFXOGroundStartConfigEntry
	ACCESS  not-accessible
	STATUS  mandatory
	DESCRIPTION  ""
	::= { fsChannelConfig 6 }

	FsFXOGroundStartConfigEntry ::= SEQUENCE {
		fsFXOGroundChanNo				INTEGER,
		fsFXOGroundLoopOpenDebouInter    	INTEGER,
            fsFXOGroundMaxGroundWaitTime		INTEGER,
            fsFXOGroundStatus				INTEGER
		}

	fsFXOGroundStartConfigEntry OBJECT-TYPE
		SYNTAX  FsFXOGroundStartConfigEntry
		ACCESS  not-accessible
		STATUS  mandatory
		DESCRIPTION  ""
		INDEX { fsFXOGroundChanNo }
		::= { fsFXOGroundStartConfigTable 1 }

	fsFXOGroundChanNo OBJECT-TYPE
		SYNTAX  INTEGER {
			chan1		(1),
			chan2       (2),
			chan3       (3),
			chan4       (4),
			chan5       (5),
			chan6		(6),
			chan7       (7),
			chan8       (8),
			chan9       (9),
			chan10	(10),
                  chan11	(11),
			chan12	(12),
			chan13	(13),
			chan14	(14),
			chan15	(15),
			chan16	(16),
			chan17	(17),
			chan18	(18),
			chan19	(19),
			chan20	(20),
			chan21	(21),
                  chan22	(22),
			chan23	(23),
			chan24	(24),
			chan25	(25),
			chan26	(26),
			chan27	(27),
			chan28	(28),
			chan29	(29),
			chan30	(30)
			}
		ACCESS  read-only
		STATUS  mandatory
		DESCRIPTION  ""
		::= { fsFXOGroundStartConfigEntry 1 }

	fsFXOGroundLoopOpenDebouInter OBJECT-TYPE
		SYNTAX  INTEGER (1..1000)
		ACCESS  read-write
		STATUS  mandatory
		DESCRIPTION ""
		::= { fsFXOGroundStartConfigEntry 2 }

	fsFXOGroundMaxGroundWaitTime OBJECT-TYPE
		SYNTAX  INTEGER (1..1000)
		ACCESS  read-write
		STATUS  mandatory
		DESCRIPTION ""
		::= { fsFXOGroundStartConfigEntry 3 }

	fsFXOGroundStatus OBJECT-TYPE
		SYNTAX  INTEGER {
			view   (1),
			modify (2)
			}
		ACCESS  read-write
		STATUS  mandatory
		DESCRIPTION  ""
		::= { fsFXOGroundStartConfigEntry 4 }

fsEMImmeConfigTable OBJECT-TYPE
	SYNTAX  SEQUENCE OF FsEMImmeConfigEntry
	ACCESS  not-accessible
	STATUS  mandatory
	DESCRIPTION  ""
	::= { fsChannelConfig 7 }

	FsEMImmeConfigEntry ::= SEQUENCE {
		fsEMImmeChanNo				INTEGER,
		fsEMImmeOffhookDebouInter    		INTEGER,
            fsEMImmeOnhookDebouInter		INTEGER,
		fsEMImmeOffhookIncomeCallTime    	INTEGER,
            fsEMImmeOnhookCallDisTime		INTEGER,
		fsEMImmeClearConfDetectTime    	INTEGER,
            fsEMImmeClearConfMaxWaitTime		INTEGER,
		fsEMImmeGuardAllTime    		INTEGER,
            fsEMImmeGuardOutTime			INTEGER,
		fsEMImmeOffhookCongToneTime		INTEGER,
            fsEMImmeStatus				INTEGER
		}

	fsEMImmeConfigEntry OBJECT-TYPE
		SYNTAX  FsEMImmeConfigEntry
		ACCESS  not-accessible
		STATUS  mandatory
		DESCRIPTION  ""
		INDEX { fsEMImmeChanNo }
		::= { fsEMImmeConfigTable 1 }

	fsEMImmeChanNo OBJECT-TYPE
		SYNTAX  INTEGER {
			chan1		(1),
			chan2       (2),
			chan3       (3),
			chan4       (4),
			chan5       (5),
			chan6		(6),
			chan7       (7),
			chan8       (8),
			chan9       (9),
			chan10	(10),
                  chan11	(11),
			chan12	(12),
			chan13	(13),
			chan14	(14),
			chan15	(15),
			chan16	(16),
			chan17	(17),
			chan18	(18),
			chan19	(19),
			chan20	(20),
			chan21	(21),
                  chan22	(22),
			chan23	(23),
			chan24	(24),
			chan25	(25),
			chan26	(26),
			chan27	(27),
			chan28	(28),
			chan29	(29),
			chan30	(30)
			}
		ACCESS  read-only
		STATUS  mandatory
		DESCRIPTION  ""
		::= { fsEMImmeConfigEntry 1 }

	fsEMImmeOffhookDebouInter OBJECT-TYPE
		SYNTAX  INTEGER (5..1000)
		ACCESS  read-write
		STATUS  mandatory
		DESCRIPTION ""
		::= { fsEMImmeConfigEntry 2 }

	fsEMImmeOnhookDebouInter OBJECT-TYPE
		SYNTAX  INTEGER (5..1000)
		ACCESS  read-write
		STATUS  mandatory
		DESCRIPTION ""
		::= { fsEMImmeConfigEntry 3 }

	fsEMImmeOffhookIncomeCallTime OBJECT-TYPE
		SYNTAX  INTEGER (5..5000)
		ACCESS  read-write
		STATUS  mandatory
		DESCRIPTION ""
		::= { fsEMImmeConfigEntry 4 }

	fsEMImmeOnhookCallDisTime OBJECT-TYPE
		SYNTAX  INTEGER (5..5000)
		ACCESS  read-write
		STATUS  mandatory
		DESCRIPTION ""
		::= { fsEMImmeConfigEntry 5 }

	fsEMImmeClearConfDetectTime OBJECT-TYPE
		SYNTAX  INTEGER (5..5000)
		ACCESS  read-write
		STATUS  mandatory
		DESCRIPTION ""
		::= { fsEMImmeConfigEntry 6 }

	fsEMImmeClearConfMaxWaitTime OBJECT-TYPE
		SYNTAX  INTEGER (5..60000)
		ACCESS  read-write
		STATUS  mandatory
		DESCRIPTION ""
		::= { fsEMImmeConfigEntry 7 }

	fsEMImmeGuardAllTime OBJECT-TYPE
		SYNTAX  INTEGER (0..60000)
		ACCESS  read-write
		STATUS  mandatory
		DESCRIPTION ""
		::= { fsEMImmeConfigEntry 8 }

	fsEMImmeGuardOutTime OBJECT-TYPE
		SYNTAX  INTEGER (5..60000)
		ACCESS  read-write
		STATUS  mandatory
		DESCRIPTION ""
		::= { fsEMImmeConfigEntry 9 }

	fsEMImmeOffhookCongToneTime OBJECT-TYPE
		SYNTAX  INTEGER (0..65535)
		ACCESS  read-write
		STATUS  mandatory
		DESCRIPTION ""
		::= { fsEMImmeConfigEntry 10 }

	fsEMImmeStatus OBJECT-TYPE
		SYNTAX  INTEGER {
			view   (1),
			modify (2)
			}
		ACCESS  read-write
		STATUS  mandatory
		DESCRIPTION  ""
		::= { fsEMImmeConfigEntry 11 }

fsEMDelayStartConfigTable OBJECT-TYPE
	SYNTAX  SEQUENCE OF FsEMDelayStartConfigEntry
	ACCESS  not-accessible
	STATUS  mandatory
	DESCRIPTION  ""
	::= { fsChannelConfig 8 }

	FsEMDelayStartConfigEntry ::= SEQUENCE {
		fsEMDelayChanNo				INTEGER,
		fsEMDelayOffhookDebouInter    	INTEGER,
            fsEMDelayOnhookDebouInter		INTEGER,
		fsEMDelayOffhookIncomeCallTime    	INTEGER,
            fsEMDelayOnhookCallDisTime		INTEGER,
		fsEMDelayClearConfDetectTime    	INTEGER,
            fsEMDelayClearConfMaxWaitTime		INTEGER,
		fsEMDelayGuardAllTime    		INTEGER,
            fsEMDelayGuardOutTime			INTEGER,
		fsEMDelayMinIncallDelayTime    	INTEGER,
            fsEMDelayMaxIncallDelayTime		INTEGER,
		fsEMDelayInDigitIgnoreTime    	INTEGER,
            fsEMDelayIntegCheckMode			INTEGER,
		fsEMDelayMinOutcallDelayTime    	INTEGER,
            fsEMDelayMaxOutcallDelayTime		INTEGER,
		fsEMDelayOutcallDelayCheckTime    	INTEGER,
            fsEMDelayStatus				INTEGER
		}

	fsEMDelayStartConfigEntry OBJECT-TYPE
		SYNTAX  FsEMDelayStartConfigEntry
		ACCESS  not-accessible
		STATUS  mandatory
		DESCRIPTION  ""
		INDEX { fsEMDelayChanNo }
		::= { fsEMDelayStartConfigTable 1 }

	fsEMDelayChanNo OBJECT-TYPE
		SYNTAX  INTEGER {
			chan1		(1),
			chan2       (2),
			chan3       (3),
			chan4       (4),
			chan5       (5),
			chan6		(6),
			chan7       (7),
			chan8       (8),
			chan9       (9),
			chan10	(10),
                  chan11	(11),
			chan12	(12),
			chan13	(13),
			chan14	(14),
			chan15	(15),
			chan16	(16),
			chan17	(17),
			chan18	(18),
			chan19	(19),
			chan20	(20),
			chan21	(21),
                  chan22	(22),
			chan23	(23),
			chan24	(24),
			chan25	(25),
			chan26	(26),
			chan27	(27),
			chan28	(28),
			chan29	(29),
			chan30	(30)
			}
		ACCESS  read-only
		STATUS  mandatory
		DESCRIPTION  ""
		::= { fsEMDelayStartConfigEntry 1 }

	fsEMDelayOffhookDebouInter OBJECT-TYPE
		SYNTAX  INTEGER (5..1000)
		ACCESS  read-write
		STATUS  mandatory
		DESCRIPTION ""
		::= { fsEMDelayStartConfigEntry 2 }

	fsEMDelayOnhookDebouInter OBJECT-TYPE
		SYNTAX  INTEGER (5..1000)
		ACCESS  read-write
		STATUS  mandatory
		DESCRIPTION ""
		::= { fsEMDelayStartConfigEntry 3 }

	fsEMDelayOffhookIncomeCallTime OBJECT-TYPE
		SYNTAX  INTEGER (5..5000)
		ACCESS  read-write
		STATUS  mandatory
		DESCRIPTION ""
		::= { fsEMDelayStartConfigEntry 4 }

	fsEMDelayOnhookCallDisTime OBJECT-TYPE
		SYNTAX  INTEGER (5..5000)
		ACCESS  read-write
		STATUS  mandatory
		DESCRIPTION ""
		::= { fsEMDelayStartConfigEntry 5 }

	fsEMDelayClearConfDetectTime OBJECT-TYPE
		SYNTAX  INTEGER (5..5000)
		ACCESS  read-write
		STATUS  mandatory
		DESCRIPTION ""
		::= { fsEMDelayStartConfigEntry 6 }

	fsEMDelayClearConfMaxWaitTime OBJECT-TYPE
		SYNTAX  INTEGER (5..60000)
		ACCESS  read-write
		STATUS  mandatory
		DESCRIPTION ""
		::= { fsEMDelayStartConfigEntry 7 }

	fsEMDelayGuardAllTime OBJECT-TYPE
		SYNTAX  INTEGER (0..60000)
		ACCESS  read-write
		STATUS  mandatory
		DESCRIPTION ""
		::= { fsEMDelayStartConfigEntry 8 }

	fsEMDelayGuardOutTime OBJECT-TYPE
		SYNTAX  INTEGER (5..60000)
		ACCESS  read-write
		STATUS  mandatory
		DESCRIPTION ""
		::= { fsEMDelayStartConfigEntry 9 }

	fsEMDelayMinIncallDelayTime OBJECT-TYPE
		SYNTAX  INTEGER (5..60000)
		ACCESS  read-write
		STATUS  mandatory
		DESCRIPTION ""
		::= { fsEMDelayStartConfigEntry 10 }

	fsEMDelayMaxIncallDelayTime OBJECT-TYPE
		SYNTAX  INTEGER (5..60000)
		ACCESS  read-write
		STATUS  mandatory
		DESCRIPTION ""
		::= { fsEMDelayStartConfigEntry 11 }

	fsEMDelayInDigitIgnoreTime OBJECT-TYPE
		SYNTAX  INTEGER (5..1000)
		ACCESS  read-write
		STATUS  mandatory
		DESCRIPTION ""
		::= { fsEMDelayStartConfigEntry 12 }

	fsEMDelayIntegCheckMode OBJECT-TYPE
		SYNTAX  INTEGER {
			off	(1),
			on	(2)
			}
		ACCESS  read-write
		STATUS  mandatory
		DESCRIPTION ""
		::= { fsEMDelayStartConfigEntry 13 }

	fsEMDelayMinOutcallDelayTime OBJECT-TYPE
		SYNTAX  INTEGER (5..60000)
		ACCESS  read-write
		STATUS  mandatory
		DESCRIPTION ""
		::= { fsEMDelayStartConfigEntry 14 }

	fsEMDelayMaxOutcallDelayTime OBJECT-TYPE
		SYNTAX  INTEGER (5..60000)
		ACCESS  read-write
		STATUS  mandatory
		DESCRIPTION ""
		::= { fsEMDelayStartConfigEntry 15 }

	fsEMDelayOutcallDelayCheckTime OBJECT-TYPE
		SYNTAX  INTEGER (0..60000)
		ACCESS  read-write
		STATUS  mandatory
		DESCRIPTION ""
		::= { fsEMDelayStartConfigEntry 16 }

	fsEMDelayStatus OBJECT-TYPE
		SYNTAX  INTEGER {
			view   (1),
			modify (2)
			}
		ACCESS  read-write
		STATUS  mandatory
		DESCRIPTION  ""
		::= { fsEMDelayStartConfigEntry 17 }

fsEMWinkStartConfigTable OBJECT-TYPE
	SYNTAX  SEQUENCE OF FsEMWinkStartConfigEntry
	ACCESS  not-accessible
	STATUS  mandatory
	DESCRIPTION  ""
	::= { fsChannelConfig 9 }

	FsEMWinkStartConfigEntry ::= SEQUENCE {
		fsEMWinkChanNo				INTEGER,
		fsEMWinkOffhookDebouInter    		INTEGER,
            fsEMWinkOnhookDebouInter		INTEGER,
		fsEMWinkOffhookIncomeCallTime    	INTEGER,
            fsEMWinkOnhookCallDisTime		INTEGER,
		fsEMWinkClearConfDetectTime    	INTEGER,
            fsEMWinkClearConfMaxWaitTime		INTEGER,
		fsEMWinkGuardAllTime    		INTEGER,
            fsEMWinkGuardOutTime			INTEGER,
		fsEMWinkMinIncallDelayTime    	INTEGER,
            fsEMWinkMaxIncallDelayTime		INTEGER,
		fsEMWinkIncallDurTime    		INTEGER,
            fsEMWinkIncallDigitIgnoreTime		INTEGER,
		fsEMWinkMaxOutcallDelayTime    	INTEGER,
            fsEMWinkMinOutcallDurTime		INTEGER,
		fsEMWinkMaxOutcallDurTime    		INTEGER,
            fsEMWinkStatus				INTEGER
		}

	fsEMWinkStartConfigEntry OBJECT-TYPE
		SYNTAX  FsEMWinkStartConfigEntry
		ACCESS  not-accessible
		STATUS  mandatory
		DESCRIPTION  ""
		INDEX { fsEMWinkChanNo }
		::= { fsEMWinkStartConfigTable 1 }

	fsEMWinkChanNo OBJECT-TYPE
		SYNTAX  INTEGER {
			chan1		(1),
			chan2       (2),
			chan3       (3),
			chan4       (4),
			chan5       (5),
			chan6		(6),
			chan7       (7),
			chan8       (8),
			chan9       (9),
			chan10	(10),
                  chan11	(11),
			chan12	(12),
			chan13	(13),
			chan14	(14),
			chan15	(15),
			chan16	(16),
			chan17	(17),
			chan18	(18),
			chan19	(19),
			chan20	(20),
			chan21	(21),
                  chan22	(22),
			chan23	(23),
			chan24	(24),
			chan25	(25),
			chan26	(26),
			chan27	(27),
			chan28	(28),
			chan29	(29),
			chan30	(30)
			}
		ACCESS  read-only
		STATUS  mandatory
		DESCRIPTION  ""
		::= { fsEMWinkStartConfigEntry 1 }

	fsEMWinkOffhookDebouInter OBJECT-TYPE
		SYNTAX  INTEGER (5..1000)
		ACCESS  read-write
		STATUS  mandatory
		DESCRIPTION ""
		::= { fsEMWinkStartConfigEntry 2 }

	fsEMWinkOnhookDebouInter OBJECT-TYPE
		SYNTAX  INTEGER (5..1000)
		ACCESS  read-write
		STATUS  mandatory
		DESCRIPTION ""
		::= { fsEMWinkStartConfigEntry 3 }

	fsEMWinkOffhookIncomeCallTime OBJECT-TYPE
		SYNTAX  INTEGER (5..5000)
		ACCESS  read-write
		STATUS  mandatory
		DESCRIPTION ""
		::= { fsEMWinkStartConfigEntry 4 }

	fsEMWinkOnhookCallDisTime OBJECT-TYPE
		SYNTAX  INTEGER (5..5000)
		ACCESS  read-write
		STATUS  mandatory
		DESCRIPTION ""
		::= { fsEMWinkStartConfigEntry 5 }

	fsEMWinkClearConfDetectTime OBJECT-TYPE
		SYNTAX  INTEGER (5..5000)
		ACCESS  read-write
		STATUS  mandatory
		DESCRIPTION ""
		::= { fsEMWinkStartConfigEntry 6 }

	fsEMWinkClearConfMaxWaitTime OBJECT-TYPE
		SYNTAX  INTEGER (5..60000)
		ACCESS  read-write
		STATUS  mandatory
		DESCRIPTION ""
		::= { fsEMWinkStartConfigEntry 7 }

	fsEMWinkGuardAllTime OBJECT-TYPE
		SYNTAX  INTEGER (0..60000)
		ACCESS  read-write
		STATUS  mandatory
		DESCRIPTION ""
		::= { fsEMWinkStartConfigEntry 8 }

	fsEMWinkGuardOutTime OBJECT-TYPE
		SYNTAX  INTEGER (5..60000)
		ACCESS  read-write
		STATUS  mandatory
		DESCRIPTION ""
		::= { fsEMWinkStartConfigEntry 9 }

	fsEMWinkMinIncallDelayTime OBJECT-TYPE
		SYNTAX  INTEGER (5..60000)
		ACCESS  read-write
		STATUS  mandatory
		DESCRIPTION ""
		::= { fsEMWinkStartConfigEntry 10 }

	fsEMWinkMaxIncallDelayTime OBJECT-TYPE
		SYNTAX  INTEGER (5..60000)
		ACCESS  read-write
		STATUS  mandatory
		DESCRIPTION ""
		::= { fsEMWinkStartConfigEntry 11 }

	fsEMWinkIncallDurTime OBJECT-TYPE
		SYNTAX  INTEGER (5..60000)
		ACCESS  read-write
		STATUS  mandatory
		DESCRIPTION ""
		::= { fsEMWinkStartConfigEntry 12 }

	fsEMWinkIncallDigitIgnoreTime OBJECT-TYPE
		SYNTAX  INTEGER (5..60000)
		ACCESS  read-write
		STATUS  mandatory
		DESCRIPTION ""
		::= { fsEMWinkStartConfigEntry 13 }

	fsEMWinkMaxOutcallDelayTime OBJECT-TYPE
		SYNTAX  INTEGER (5..60000)
		ACCESS  read-write
		STATUS  mandatory
		DESCRIPTION ""
		::= { fsEMWinkStartConfigEntry 14 }

	fsEMWinkMinOutcallDurTime OBJECT-TYPE
		SYNTAX  INTEGER (5..60000)
		ACCESS  read-write
		STATUS  mandatory
		DESCRIPTION ""
		::= { fsEMWinkStartConfigEntry 15 }

	fsEMWinkMaxOutcallDurTime OBJECT-TYPE
		SYNTAX  INTEGER (5..60000)
		ACCESS  read-write
		STATUS  mandatory
		DESCRIPTION ""
		::= { fsEMWinkStartConfigEntry 16 }

	fsEMWinkStatus OBJECT-TYPE
		SYNTAX  INTEGER {
			view   (1),
			modify (2)
			}
		ACCESS  read-write
		STATUS  mandatory
		DESCRIPTION  ""
		::= { fsEMWinkStartConfigEntry 17 }

fsChannelProfile OBJECT IDENTIFIER ::= { fsVoiceConfig 2 }

fsChanProfileTable OBJECT-TYPE
	SYNTAX  SEQUENCE OF FsChanProfileTableEntry
	ACCESS  not-accessible
	STATUS  mandatory
	DESCRIPTION  ""
	::= { fsChannelProfile 1 }

	FsChanProfileTableEntry ::= SEQUENCE {
		fsChanProfileIndex    		INTEGER,
            fsChanUsage				INTEGER,
		fsChanCodecCodeType     	INTEGER,
		fsChanVoiceInfoField		INTEGER,
            fsChanNetworkJitter		INTEGER,
            fsChanNetworkDelay		INTEGER,
            fsChanVoiceActDetector		INTEGER,
            fsChanDTMFRelayMode		INTEGER,
            fsChanEchoCancelMode     	INTEGER,
            fsChanEchoCancelTailLength   	INTEGER,
            fsChanFaxRate     		INTEGER,
            fsChanFaxInactTimeout     	INTEGER,
            fsChanNonLinProceMode		INTEGER,
		fsChanEncapType     		INTEGER,
		fsChanVADThreshold     		DisplayString,
		fsChanBlockSplitOptMode     	INTEGER,
		fsChanEnhanceBits			INTEGER,
		fsChanProfileStatus   		INTEGER
		}

	fsChanProfileTableEntry OBJECT-TYPE
		SYNTAX  FsChanProfileTableEntry
		ACCESS  not-accessible
		STATUS  mandatory
		DESCRIPTION  ""
		INDEX { fsChanProfileIndex }
		::= { fsChanProfileTable 1 }

	fsChanProfileIndex OBJECT-TYPE
		SYNTAX  INTEGER {
			entry1	(1),
			entry2      (2)
			}
		ACCESS  read-only
		STATUS  mandatory
		DESCRIPTION  ""
		::= { fsChanProfileTableEntry 1 }

	fsChanUsage OBJECT-TYPE
		SYNTAX  INTEGER {
			undefined	(0),
			voice      	(1),
			fax		(2),
			modem      	(3),
			data		(4)
			}
		ACCESS  read-write
		STATUS  mandatory
		DESCRIPTION  ""
		::= { fsChanProfileTableEntry 2 }

	fsChanCodecCodeType OBJECT-TYPE
		SYNTAX  INTEGER {
			undefined		(1),
			pcm-a-law   	(2),
			pcm-mu-law		(3),
			g-711      		(4),
			g-723-1-5-3k	(5),
			g-723-1-6-3k   	(6),
			g-726-adpcm-16k	(7),
			g-726-adpcm-24k   (8),
			g-726-adpcm-32k	(9),
			g-726-adpcm-40k   (10),
			g-727-eadpcm-16k	(11),
			g-727-eadpcm-24k	(12),
			g-727-eadpcm-32k	(13),
			g-727-eadpcm-40k	(14),
			g-729-8k		(15),
			g-729-annx-a8k	(16),
			fax-relay		(17),
			packetsignal	(18)
			}
		ACCESS  read-write
		STATUS  mandatory
		DESCRIPTION  ""
		::= { fsChanProfileTableEntry 3 }

	fsChanVoiceInfoField OBJECT-TYPE
		SYNTAX  INTEGER 
		ACCESS  read-write
		STATUS  mandatory
		DESCRIPTION  ""
		::= { fsChanProfileTableEntry 4 }

	fsChanNetworkJitter OBJECT-TYPE
		SYNTAX  INTEGER (0..240)
		ACCESS  read-write
		STATUS  mandatory
		DESCRIPTION  ""
		::= { fsChanProfileTableEntry 5 }

	fsChanNetworkDelay OBJECT-TYPE
		SYNTAX  INTEGER (60..500)
		ACCESS  read-write
		STATUS  mandatory
		DESCRIPTION  ""
		::= { fsChanProfileTableEntry 6 }

	fsChanVoiceActDetector OBJECT-TYPE
		SYNTAX  INTEGER {
			off	(1),
			on	(2)
			}
		ACCESS  read-write
		STATUS  mandatory
		DESCRIPTION  ""
		::= { fsChanProfileTableEntry 7 }

	fsChanDTMFRelayMode OBJECT-TYPE
		SYNTAX  INTEGER {
			off		(1),
			on		(2)
			}
		ACCESS  read-write
		STATUS  mandatory
		DESCRIPTION  ""
		::= { fsChanProfileTableEntry 8 }

	fsChanEchoCancelMode OBJECT-TYPE
		SYNTAX  INTEGER {
			off		(1),
			on		(2)
			}
		ACCESS  read-write
		STATUS  mandatory
		DESCRIPTION  ""
		::= { fsChanProfileTableEntry 9 }

	fsChanEchoCancelTailLength OBJECT-TYPE
		SYNTAX  INTEGER (0..32)
		ACCESS  read-write
		STATUS  mandatory
		DESCRIPTION  ""
		::= { fsChanProfileTableEntry 10 }

	fsChanFaxRate OBJECT-TYPE
		SYNTAX  INTEGER {
			b2400		(1),
			b4800		(2),
			b5300		(3),
			b6300		(4),
			b7200		(5),
			b9600		(6),
			b12000	(7),
			b14400	(8)
			}
		ACCESS  read-write
		STATUS  mandatory
		DESCRIPTION  ""
		::= { fsChanProfileTableEntry 11 }

	fsChanFaxInactTimeout OBJECT-TYPE
		SYNTAX  INTEGER (10..32000)
		ACCESS  read-write
		STATUS  mandatory
		DESCRIPTION  ""
		::= { fsChanProfileTableEntry 12 }

	fsChanNonLinProceMode OBJECT-TYPE
		SYNTAX  INTEGER {
			off		(1),
			on		(2)
			}
		ACCESS  read-write
		STATUS  mandatory
		DESCRIPTION  ""
		::= { fsChanProfileTableEntry 13 }

	fsChanEncapType OBJECT-TYPE
		SYNTAX  INTEGER {
			undefined	(1),
			frf11		(2),
			h-323		(3)
			}
		ACCESS  read-write
		STATUS  mandatory
		DESCRIPTION  ""
		::= { fsChanProfileTableEntry 14 }

	fsChanVADThreshold OBJECT-TYPE
		SYNTAX  DisplayString
		ACCESS  read-write
		STATUS  mandatory
		DESCRIPTION  ""
		::= { fsChanProfileTableEntry 15 }

	fsChanBlockSplitOptMode OBJECT-TYPE
		SYNTAX  INTEGER {
			off	(1),
			on	(2)
			}
		ACCESS  read-write
		STATUS  mandatory
		DESCRIPTION  ""
		::= { fsChanProfileTableEntry 16 }

	fsChanEnhanceBits OBJECT-TYPE
		SYNTAX  INTEGER 
		ACCESS  read-write
		STATUS  mandatory
		DESCRIPTION  ""
		::= { fsChanProfileTableEntry 17 }

	fsChanProfileStatus OBJECT-TYPE
		SYNTAX  INTEGER {
                  view    (1),
                  add     (2),
			delete  (3),
                  modify  (4)
			}
		ACCESS  read-write
		STATUS  mandatory
		DESCRIPTION  ""
		::= { fsChanProfileTableEntry 18 }

fsChannelToneTableConfig OBJECT IDENTIFIER ::= { fsVoiceConfig 3 }

fsChannelTone OBJECT-TYPE
	SYNTAX  INTEGER {
		default		(1),
		alternate         (2),
            xgcp              (3),
            north-american    (4),
            german            (5),
            new-zealand       (6),
            italian           (7),
            chinese           (8),
            taiwanese         (9),
            hong-kong         (10),
            malaysian         (11),
            brazilian         (12)
		}
	ACCESS  read-write
	STATUS  mandatory
	DESCRIPTION  ""
	::= { fsChannelToneTableConfig 1 }

fsChannelAmplitude OBJECT-TYPE
	SYNTAX  DisplayString	
      ACCESS  read-write
	STATUS  mandatory
	DESCRIPTION  ""
	::= { fsChannelToneTableConfig 2 }

fsChannelDynamicConfig OBJECT IDENTIFIER ::= { fsVoiceConfig 4 }

fsDynamicConfigTable OBJECT-TYPE
	SYNTAX  SEQUENCE OF FsDynamicConfigEntry
	ACCESS  not-accessible
	STATUS  mandatory
	DESCRIPTION  ""
	::= { fsChannelDynamicConfig 1 }

	FsDynamicConfigEntry ::= SEQUENCE {
		fsDyConfigChanNo			INTEGER,
		fsDyConfigRxGain			DisplayString,
            fsDyConfigTxGain			DisplayString,
            fsDyAdminStatus               INTEGER,
            fsDyVoiceRoutingUpdate        INTEGER,
            fsDyConfigStatus			INTEGER
		}

	fsDynamicConfigEntry OBJECT-TYPE
		SYNTAX  FsDynamicConfigEntry
		ACCESS  not-accessible
		STATUS  mandatory
		DESCRIPTION  ""
		INDEX { fsDyConfigChanNo }
		::= { fsDynamicConfigTable 1 }

	fsDyConfigChanNo OBJECT-TYPE
		SYNTAX  INTEGER {
			chan1		(1),
			chan2       (2),
			chan3       (3),
			chan4       (4),
			chan5       (5),
			chan6		(6),
			chan7       (7),
			chan8       (8),
			chan9       (9),
			chan10	(10),
                  chan11	(11),
			chan12	(12),
			chan13	(13),
			chan14	(14),
			chan15	(15),
			chan16	(16),
			chan17	(17),
			chan18	(18),
			chan19	(19),
			chan20	(20),
			chan21	(21),
                  chan22	(22),
			chan23	(23),
			chan24	(24),
			chan25	(25),
			chan26	(26),
			chan27	(27),
			chan28	(28),
			chan29	(29),
			chan30	(30)
			}
		ACCESS  read-only
		STATUS  mandatory
		DESCRIPTION  ""
		::= { fsDynamicConfigEntry 1 }

	fsDyConfigRxGain OBJECT-TYPE
		SYNTAX  DisplayString
		ACCESS  read-write
		STATUS  mandatory
		DESCRIPTION ""
		::= { fsDynamicConfigEntry 2 }

	fsDyConfigTxGain OBJECT-TYPE
		SYNTAX  DisplayString
		ACCESS  read-write
		STATUS  mandatory
		DESCRIPTION ""
		::= { fsDynamicConfigEntry 3 }

	fsDyAdminStatus OBJECT-TYPE
		SYNTAX  INTEGER {
			down   (1),
			up     (2)
			}
		ACCESS  read-write
		STATUS  mandatory
		DESCRIPTION  ""
		::= { fsDynamicConfigEntry 4 }

	fsDyVoiceRoutingUpdate OBJECT-TYPE
		SYNTAX  INTEGER {
			yes     (1),
			no      (2),
                  no-act  (3)
			}
		ACCESS  read-write
		STATUS  mandatory
		DESCRIPTION  ""
		::= { fsDynamicConfigEntry 5 }

	fsDyConfigStatus OBJECT-TYPE
		SYNTAX  INTEGER {
			view   (1),
			modify (2)
			}
		ACCESS  read-write
		STATUS  mandatory
		DESCRIPTION  ""
		::= { fsDynamicConfigEntry 6 }

-- ***************************************************************************
-- CDR parameters

fsChannelCdrConfig OBJECT IDENTIFIER ::= { fsVoiceConfig 5 }

fsCdrPriHostLogging OBJECT-TYPE
	SYNTAX  INTEGER {
		enable       (1),
		disable      (2),
            undefined    (3)
		}
	ACCESS  read-write
	STATUS  mandatory
	DESCRIPTION  ""
	::= { fsChannelCdrConfig 1 }

fsCdrPriHostIpAddr OBJECT-TYPE
   	SYNTAX  IpAddress
	ACCESS  read-write
	STATUS  mandatory
	DESCRIPTION  ""
	::= { fsChannelCdrConfig 2 }

fsCdrPriFacility OBJECT-TYPE
	SYNTAX  INTEGER {
		syslog       (1),
		local0       (2),
            local1       (3),
            local2       (4),
            local3       (5),
            local4       (6),
            local5       (7),
            local6       (8),
            local7       (9),
            invalid      (10)
		}
	ACCESS  read-write
	STATUS  mandatory
	DESCRIPTION  ""
	::= { fsChannelCdrConfig 3 }

fsCdrPriHostMsgFormat OBJECT-TYPE
	SYNTAX  INTEGER {
		verbose      (1),
            non-verbose  (2),
            both         (3),
            invalid      (4)
		}
	ACCESS  read-write
	STATUS  mandatory
	DESCRIPTION  ""
	::= { fsChannelCdrConfig 4 }

fsCdrSecHostLogging OBJECT-TYPE
	SYNTAX  INTEGER {
		enable       (1),
		disable      (2),
            undefined    (3)
		}
	ACCESS  read-write
	STATUS  mandatory
	DESCRIPTION  ""
	::= { fsChannelCdrConfig 5 }

fsCdrSecHostIpAddr OBJECT-TYPE
     	SYNTAX  IpAddress
	ACCESS  read-write
	STATUS  mandatory
	DESCRIPTION  ""
	::= { fsChannelCdrConfig 6 }

fsCdrSecFacility OBJECT-TYPE
	SYNTAX  INTEGER {
		syslog       (1),
		local0       (2),
            local1       (3),
            local2       (4),
            local3       (5),
            local4       (6),
            local5       (7),
            local6       (8),
            local7       (9),
            invalid      (10)
		}
	ACCESS  read-write
	STATUS  mandatory
	DESCRIPTION  ""
	::= { fsChannelCdrConfig 7 }

fsCdrSecHostMsgFormat OBJECT-TYPE
	SYNTAX  INTEGER {
		verbose      (1),
            non-verbose  (2),
            both         (3),
            invalid      (4)
		}
	ACCESS  read-write
	STATUS  mandatory
	DESCRIPTION  ""
	::= { fsChannelCdrConfig 8 }

fsCdrCallType OBJECT-TYPE
	SYNTAX  INTEGER {
		com-calls    (1),
		all-calls    (2)
		}
	ACCESS  read-write
	STATUS  mandatory
	DESCRIPTION  ""
	::= { fsChannelCdrConfig 9 }

fsCdrEntryDisplay OBJECT-TYPE
	SYNTAX  INTEGER (1..25) 
	ACCESS  read-write
	STATUS  mandatory
	DESCRIPTION  ""
	::= { fsChannelCdrConfig 10 }

-- ***************************************************************************
-- Channel copy parameters

fsChannelCopyConfig OBJECT IDENTIFIER ::= { fsVoiceConfig 6 }

fsChannelCopySource OBJECT-TYPE
	SYNTAX  INTEGER {
		chan1		(1),
		chan2       (2),
		chan3       (3),
		chan4       (4),
		chan5       (5),
		chan6		(6),
		chan7       (7),
		chan8       (8),
		chan9       (9),
		chan10	(10),
            chan11	(11),
		chan12	(12),
		chan13	(13),
		chan14	(14),
		chan15	(15),
		chan16	(16),
		chan17	(17),
		chan18	(18),
		chan19	(19),
		chan20	(20),
		chan21	(21),
            chan22	(22),
		chan23	(23),
		chan24	(24),
		chan25	(25),
		chan26	(26),
		chan27	(27),
		chan28	(28),
		chan29	(29),
		chan30	(30)
		}
	ACCESS  read-write
	STATUS  mandatory
	DESCRIPTION  ""
	::= { fsChannelCopyConfig 1 }

fsChannelCopyTarget OBJECT-TYPE
      SYNTAX  DisplayString
	ACCESS  read-write
	STATUS  mandatory
	DESCRIPTION  ""
	::= { fsChannelCopyConfig 2 }

fsChannelCopyStart OBJECT-TYPE
	SYNTAX  INTEGER {
		initiate	(1),
            other       (2)
		}
	ACCESS  read-write
	STATUS  mandatory
	DESCRIPTION ""
	::= { fsChannelCopyConfig 3 }


-- ***************************************************************************
-- Fastcomm Private Enterprise Traps

checkStatus TRAP-TYPE
	ENTERPRISE  fastcomm
	DESCRIPTION 
		"This trap is reserved for test only"
	::= 0

memoryLow TRAP-TYPE
	ENTERPRISE  fastcomm
	DESCRIPTION 
		"This trap is generated when FRADs have memory
		 problems"
	::= 1

frPhysicalLineUp TRAP-TYPE
	ENTERPRISE  fastcomm
	DESCRIPTION 
		"This trap is sent when DTR ON has been detected
             by a FR port."
	::= 2

frPhysicalLineDown TRAP-TYPE
	ENTERPRISE  fastcomm
	DESCRIPTION 
		"This trap is sent when DTR DOWN has been detected
             by a FR port."
	::= 3

frPortMgmtUp TRAP-TYPE
	ENTERPRISE  fastcomm
	DESCRIPTION 
		"This trap is sent when FR management is UP. For
	       FR port on network side, this means that the port
		 begins responding to polling. For FR port on user
		 side, this means the port begins receiving polling.

		 NOTE:
		 This trap is sent only when the previous status is
		 ether 'init' or 'portMgmtDown'."
	::= 4
	    
frPortMgmtDown TRAP-TYPE
	ENTERPRISE  fastcomm
	DESCRIPTION 
		"This trap is sent when FR management is DOWN. For
	       FR port on network side, this means that the port
		 stops responding to polling. For FR port on user
	       side, this means the port stops receiving polling.

		 NOTE:
		 This trap is sent only when the previous status is
		 ether 'init' or 'portMgmtUp'."
	::= 5

frDlciUp TRAP-TYPE
	ENTERPRISE  fastcomm
	DESCRIPTION 
		"This trap is sent when a dlci is active.

		 NOTE:
		 This trap is sent only when the previous status is
		 ether 'new' or 'dlciDown'."
	::= 6
	    
frDlciDown TRAP-TYPE
	ENTERPRISE  fastcomm
	DESCRIPTION 
		"This trap is sent when a dlci is inactive. 

		 NOTE:
		 This trap is sent only when the previous status is
		 ether 'new' or 'dlciUp'."
	::= 7

x25SVCUp TRAP-TYPE
	ENTERPRISE  fastcomm
	DESCRIPTION 
		"This trap is sent when a X25 SCV is up." 
	::= 8

x25SVCDown TRAP-TYPE
	ENTERPRISE  fastcomm
	DESCRIPTION 
		"This trap is sent when a X25 SVC is down." 
	::= 9

END
