PICTURETEL-VCS-MIB DEFINITIONS ::= BEGIN

IMPORTS
MODULE-IDENTITY, OBJECT-TYPE, OBJECT-IDENTITY, NOTIFICATION-TYPE, Counter32, Gauge32, enterprises
FROM SNMPv2-SMI

TruthValue, TimeStamp, TimeInterval, DisplayString,  RowStatus, TEXTUAL-CONVENTION
FROM SNMPv2-TC;

pictureTel                OBJECT IDENTIFIER ::= { enterprises 274 }

products                  OBJECT IDENTIFIER ::= { pictureTel 5 }

pictureTelVCSModule MODULE-IDENTITY

	LAST-UPDATED    "0101030000Z"
	ORGANIZATION    "PictureTel Corporation"
	CONTACT-INFO
		"Postal:
			PictureTel Corporation
			100 Minuteman Drive
			Andover, MA 01810-1031
			USA"
	DESCRIPTION
	"The PictureTel VCS Administration MIB specifies a conceptual group of observable
	 events and objects.  These events and objects comprise the management information 
	 necessary to effectively administrate a PictureTel videoconferencing system.

	Copyright 2001 PictureTel Corporation.  All rights reserved.  Reproduction of this 
	document is authorized on the condition that the foregoing copyright notice is included.

	This SNMP MIB module (Specification) embodies PictureTel Corporation's proprietary 
	intellectual property. PictureTel Corporation retains all title and ownership in the 
	Specification, including any revisions.

	PictureTel Corporation grants all interested parties a non-exclusive license to use 
	and distribute an unmodified copy of this Specification in connection with management 
	of PictureTel Corporation products, and without fee, provided this copyright notice 
	and license appear on all copies.

	This Specification is supplied 'AS IS,' and PictureTel Corporation makes no warranty, 
	either express or implied, as to the use, operation, condition, or performance of the 
	Specification."

	REVISION        "0101030000Z"
	DESCRIPTION
		"Rev 0.0.11
		3 Jan 2001 12:00  
		Release version"
::= { products 5 }

--
-- Textual Conventions used in this module
--

CallBandwidthType ::= TEXTUAL-CONVENTION
	STATUS	current
	DESCRIPTION
		"Enumerated type representing current call bandwidth"
	SYNTAX	INTEGER {
		unknown(0),
		cb1x64K(1),
		cb2x64K(2),
		cb1x128K(3),
		cb1x192K(4),
		cb1x256K(5),
		cb1x320K(6),
		cb1x384K(7),
		cb1x512K(8),
		cb1x768K(9),
		cb1x1152K(10),
		cb1x1472K(11),
		cb1x1536K(12),
		cb1x1920K(13)
		}


VideoAlgorithmType ::= TEXTUAL-CONVENTION
	STATUS	current
	DESCRIPTION
		"Enumerated type representing current video algorithms"
	SYNTAX	INTEGER {
		unknown(0),
		h261(1),
		h263(2),
		h263p(3),
		max(4)
	 	}

AudioAlgorithmType ::= TEXTUAL-CONVENTION
	STATUS	current
	DESCRIPTION
		"Enumerated type representing current audio algorithms"
	SYNTAX	INTEGER {
		minOrOffUnframed(0),
		offFramed(1),
		g711Unknown(2),
		g711alaw48(3),
		g711ulaw48(4),
		g711alaw56(5),
		g711ulaw56(6),
		g711alaw64(7),   -- same as AUDIO_ALGORITHM_G711_A_LAW_UNFRAMED
		g711ulaw64(8),   -- same as AUDIO_ALGORITHM_G711_U_LAW_UNFRAMED
		g722at48kbps(9),
		g722at56kbps(10),
		g722at64kbps(11),
		g7221at16kbps(12),  -- // reserved 
		g7221at24kbps(13),
		g7221at32kbps(14),
		g7235pt3kbps(15),
		g7236pt3kbps(16),
		g728(17),
		pt724(18),
		siren7at16kbps(19),
		siren7at24kbps(20),
		siren7at32kbps(21),
		siren14at24kbps(22),
		siren14at32kbps(23),
		siren14at48kbps(24),
		maxOrBestCapsAudio(25)
		}

DataProtocolType ::= TEXTUAL-CONVENTION
	STATUS	current
	DESCRIPTION
		"Enumerated type representing current data protocols"
	SYNTAX	INTEGER {
		off(0),
		h224lsd(1),
		h224mlp(2),
		h224lsdAndT120(3),
		h224mlpAndT120(4),
		t120(5)
		}

VideoResolutionType ::= TEXTUAL-CONVENTION
	STATUS	current
	DESCRIPTION
		"Enumerated type representing current video resolutions"
	SYNTAX	INTEGER {
		unknown(0),
		sqcif(1),         -- 0x00000001,    //  128x96
		qcif(2),          -- 0x00000002,    //  176x144
		cif(4),           -- 0x00000004,    //  352x288
		cif4(8),          -- 0x00000008,    //  704x576
		cif16(16),        -- 0x00000010,    // 1408x1152
		vga(32),          -- 0x00000020,    //  640x480
		vgaDiv4(64),      -- 0x00000040,    //  320x240
		svga(128),        -- 0x00000080,    //  800x600
		svgaDiv4(256),    -- 0x00000100,    //  400x300
		xvga(512),        -- 0x00000200,    // 1024x768
		xvgaDiv4(1024),   -- 0x00000400,    //  512x384
		xvgaDiv16(2048),  -- 0x00000800,    //  256x192
		ntsc(4096),       -- 0x00001000,    //  704x480
		ntscDiv4(8192),   -- 0x00002000,    //  352x240
		max(32767)        -- 0x7FFF        since this is an INTEGER (not LONG)
 --		max(2147467264),     0x7FFFC000    we will use max INT instead
		}


MediaChannelStatusType ::= TEXTUAL-CONVENTION
	STATUS	current
	DESCRIPTION
		"Enumerated type representing current media channel status"
	SYNTAX	INTEGER {
		minOrClosed(0),
		openIP(1),
		maxOrOpenATM(2)
		}


--
-- pictureTelVCSModule Placeholders
--


-- Monitoring Area
ptMonitoring       OBJECT-IDENTITY
	STATUS          current
	DESCRIPTION     "OID for pictureTelVCSModule monitoring branch"
	::= { pictureTelVCSModule 1 }

-- H320 MIB placeholder
ptH320             OBJECT-IDENTITY
	STATUS          current
	DESCRIPTION     "OID - Subtree for root of H.320 module(s)"
	::= { pictureTelVCSModule 2 }

-- H323 MIB placeholder
ptH323             OBJECT-IDENTITY
	STATUS          current
	DESCRIPTION     "OID - Subtree for root of H.323 module(s)"
	::= { pictureTelVCSModule 3 }

-- Configuration MIB placeholder
ptConfiguration    OBJECT-IDENTITY
	STATUS          current
	DESCRIPTION     "OID - Subtree for root of configuration module(s)"
	::= { pictureTelVCSModule 4 }

-- ISDNVoiceOnly MIB placeholder
ptISDNVoiceOnly OBJECT-IDENTITY
	STATUS          current
	DESCRIPTION     "OID - Subtree for root of ISDN voice-only module(s)"
	::= { pictureTelVCSModule 5 }

-- System Statistics MIB placeholder
ptSystemStatistics OBJECT-IDENTITY
	STATUS          current
	DESCRIPTION     "OID - Subtree for root of the system statistics module(s)"
	::= { pictureTelVCSModule 6 }

-- Control MIB placeholder
ptControl OBJECT-IDENTITY
	STATUS          current
	DESCRIPTION     "OID - Subtree for root of control module(s)"
	::= { pictureTelVCSModule 7 }



--  ptMonitoring Branch consists of: 
--  ptMonitoring\ptMonSystem area
--  ptMonitoring\ptTraps     area

ptMonSystem                OBJECT-IDENTITY
	STATUS                  current
	DESCRIPTION              "OID for ptMonitoring/System area"
	::= { ptMonitoring 1 }


ptTraps                    OBJECT-IDENTITY
	STATUS                  current
	DESCRIPTION              "OID for ptMonitoring/Traps area"
	::= { ptMonitoring 2 }


-- ptMonitoring\ptMonSys

ptMonSysName               OBJECT-TYPE
	SYNTAX                  DisplayString
	MAX-ACCESS              read-only
	STATUS                  current
	DESCRIPTION             "An administratively assigned name for the videoconferencing
				system. If the name is unknown, the value contained in this
				object is the zero-length string. This value is the same as the
				system name defined in the system software."
	REFERENCE               "This object contains a value identical to that of the MIB-II
				sysName object."
	::= { ptMonSystem 1 }


ptMonSysDescription        OBJECT-TYPE
	SYNTAX                  DisplayString
	MAX-ACCESS              read-only
	STATUS                  current
	DESCRIPTION     
				"A textual description of the videoconferencing system.  The
				value is a string containing the vendor name, the product name,
				and the product version.  Here is an example:  `PictureTel 
				Venue 2000 version 1.3'."
	REFERENCE       
				"This object contains a value identical to that of the MIB-II 
				sysDescr object."
	::= { ptMonSystem 2 }


ptMonSysOID        OBJECT-TYPE
	SYNTAX          OBJECT IDENTIFIER
	MAX-ACCESS      read-only
	STATUS          current
	DESCRIPTION
			"The product identifier for the PictureTel system.  The 
			value of this managed object is an Object Value Assignment 
			(OVA), residing within the registration subtree of the
			vendor's enterprise name space.  This object is useful in 
			verifying the model and version of the vendor's service."
	REFERENCE
			"This object contains a value identical to that of the MIB-II 
			sysObjectID object."
	::= { ptMonSystem 3 }



ptMonSysUpTime     OBJECT-TYPE
	SYNTAX          TimeStamp
	MAX-ACCESS      read-only
	STATUS          current
	DESCRIPTION
			"The elapsed time since the PictureTel SNMP agent was started."
	REFERENCE
			"This object contains a value identical to that contained in 
			the MIB-II sysUpTime object."
	::= { ptMonSystem 4 }


ptMonSysContact     OBJECT-TYPE
	SYNTAX          DisplayString
	MAX-ACCESS      read-only
	STATUS          current
	DESCRIPTION
			"The textual identification of the on-site support staff 
			responsible for the videoconferencing system installation.  If 
			no contact information is known, the value contained in this 
			object is the zero-length string."
	REFERENCE
			"This object contains a value identical to that contained in 
			the MIB-II sysContact object."
	::= { ptMonSystem 5 }

ptMonSysLocation    OBJECT-TYPE
	SYNTAX          DisplayString
	MAX-ACCESS      read-only
	STATUS          current
	DESCRIPTION
			"The physical location of the videoconferencing system (e.g., 
			`Main conference room - 3rd floor').  If the location is
			unknown, the value contained in this object is the zero-length                                                                                  string."
	REFERENCE
			"This object contains a value identical to that of the MIB-II 
			sysLocation object."
	::= { ptMonSystem 6 }




-- ptMonitoring\Traps

ptNotificationPrefix OBJECT IDENTIFIER
	::= { ptTraps 0 }

pictureTelTrapSystemRebooting NOTIFICATION-TYPE
	OBJECTS { ptMonSysName }
	STATUS  current
	DESCRIPTION
		"Notification that system is about to reboot"
	::= { ptNotificationPrefix 1 }

pictureTelTrapSystemShutdown NOTIFICATION-TYPE
	OBJECTS { ptMonSysName }
	STATUS  current
	DESCRIPTION
		"Notification that system is entering shutdown"
	::= { ptNotificationPrefix 2 }

pictureTelTrapAgentStarted NOTIFICATION-TYPE
	OBJECTS { ptMonSysName }
	STATUS  current
	DESCRIPTION
		"Notification that SNMP agent started"
	::= { ptNotificationPrefix 3 }

pictureTelTrapAgentShutdown NOTIFICATION-TYPE
	OBJECTS { ptMonSysName }
	STATUS  current
	DESCRIPTION
		"Notification that the SNMP agent is shuting down"
	::= { ptNotificationPrefix 4 }

pictureTelTrapH320IncomingCall NOTIFICATION-TYPE
	OBJECTS { ptMonSysName }
	STATUS  current
	DESCRIPTION
		"Notification of H.320 incoming call."
	::= { ptNotificationPrefix 5 }

pictureTelTrapH323IncomingCall NOTIFICATION-TYPE
	OBJECTS { ptMonSysName }
	STATUS  current
	DESCRIPTION
		"Notification of H.323 incoming call"
	::= { ptNotificationPrefix 6 }

pictureTelTrapISDNVoiceOnlyIncomingCall NOTIFICATION-TYPE
	OBJECTS { ptMonSysName }
	STATUS  current
	DESCRIPTION
		"Notification of ISDN voice-only incoming call"
	::= { ptNotificationPrefix 7 }

pictureTelTrapH320CallConnected NOTIFICATION-TYPE
	OBJECTS { ptMonSysName }
	STATUS  current
	DESCRIPTION
		"Notification that H.320 call connected"
	::= { ptNotificationPrefix 8 }

pictureTelTrapH323CallConnected NOTIFICATION-TYPE
	OBJECTS { ptMonSysName }
	STATUS  current
	DESCRIPTION
		"Notification that H.323 call connected"
	::= { ptNotificationPrefix 9 }

pictureTelTrapISDNVoiceOnlyCallConnected NOTIFICATION-TYPE
	OBJECTS { ptMonSysName }
	STATUS  current
	DESCRIPTION
		"Notification that ISDN voice-only call connected"
	::= { ptNotificationPrefix 10 }

pictureTelTrapDialing NOTIFICATION-TYPE
	OBJECTS { ptMonSysName }
	STATUS  current
	DESCRIPTION
		"Notification that system is dialing a call"
	::= { ptNotificationPrefix 11 }

pictureTelTrapRinging NOTIFICATION-TYPE
	OBJECTS { ptMonSysName }
	STATUS  current
	DESCRIPTION
		"Notification that dialed call progressed to ringing state"
	::= { ptNotificationPrefix 12 }

pictureTelTrapConnecting NOTIFICATION-TYPE
	OBJECTS { ptMonSysName }
	STATUS  current
	DESCRIPTION
		"Notification that dialed call is connecting"
	::= { ptNotificationPrefix 13 }

pictureTelTrapConnected NOTIFICATION-TYPE
	OBJECTS { ptMonSysName }
	STATUS  current
	DESCRIPTION
		"Notification that dialed call successfully connected"
	::= { ptNotificationPrefix 14 }

pictureTelTrapMultiPointConferenceStarted NOTIFICATION-TYPE
	OBJECTS { ptMonSysName }
	STATUS  current
	DESCRIPTION
		"Notification that system dialed into the bridge"
	::= { ptNotificationPrefix 15 }

pictureTelTrapMultiPointConferenceEnded NOTIFICATION-TYPE
	OBJECTS { ptMonSysName }
	STATUS  current
	DESCRIPTION
		"Notification that system dropped out from a multipoint (bridge) call"
	::= { ptNotificationPrefix 16 }

pictureTelTrapH320CallDisconnected NOTIFICATION-TYPE
	OBJECTS { ptMonSysName }
	STATUS  current
	DESCRIPTION
		"Notification that H.320 call disconnected"
	::= { ptNotificationPrefix 17 }

pictureTelTrapH323CallDisconnected NOTIFICATION-TYPE
	OBJECTS { ptMonSysName }
	STATUS  current
	DESCRIPTION
		"Notification that H.323 call disconnected"
	::= { ptNotificationPrefix 18 }

pictureTelTrapISDNVoiceOnlyCallDisConnected NOTIFICATION-TYPE
	OBJECTS { ptMonSysName }
	STATUS  current
	DESCRIPTION
		"Notification that ISDN voice-only call disconnected"
	::= { ptNotificationPrefix 19 }

pictureTelTrapISDNNotReady NOTIFICATION-TYPE
	OBJECTS { ptMonSysName }
	STATUS  current
	DESCRIPTION
		"Notification that ISDN is unplugged or inaccessible"
	::= { ptNotificationPrefix 20 }

pictureTelTrapConnectFailed NOTIFICATION-TYPE
	OBJECTS { ptMonSysName }
	STATUS  current
	DESCRIPTION
		"Notification that attempt to make a call (connect) failed"
	::= { ptNotificationPrefix 21 }

pictureTelTrapAutoSPIDFailure NOTIFICATION-TYPE
	OBJECTS { ptMonSysName }
	STATUS  current
	DESCRIPTION
		"Notification that Auto SPID failed"
	::= { ptNotificationPrefix 22 }

pictureTelTrapDocumentServerUnreachable NOTIFICATION-TYPE
	OBJECTS { ptMonSysName }
	STATUS  current
	DESCRIPTION
		"Notification that system is not able to contact Document Server"
	::= { ptNotificationPrefix 23 }

pictureTelTrapGatekeeperUnreachable NOTIFICATION-TYPE
	OBJECTS { ptMonSysName }
	STATUS  current
	DESCRIPTION
		"Notification that system is not able to register with the gatekeeper"
	::= { ptNotificationPrefix 24}

pictureTelTrapDirectoryServerUnreachable NOTIFICATION-TYPE
	OBJECTS { ptMonSysName }
	STATUS  current
	DESCRIPTION
		"Notification that system is not able to contact Directory Server"
	::= { ptNotificationPrefix 25 }

pictureTelTrapCameraUnplugged NOTIFICATION-TYPE
	OBJECTS { ptMonSysName }
	STATUS  current
	DESCRIPTION
		"Notification that camera was unplugged"
	::= { ptNotificationPrefix 26 }

pictureTelTrapVideoMuted NOTIFICATION-TYPE
	OBJECTS { ptMonSysName }
	STATUS  current
	DESCRIPTION
		"Notification that near-end video is muted"
	::= { ptNotificationPrefix 27 }

pictureTelTrapVGASettingProblem NOTIFICATION-TYPE
	OBJECTS { ptMonSysName }
	STATUS  current
	DESCRIPTION
		"Notification that there is a VGA setting problem"
	::= { ptNotificationPrefix 28 }

pictureTelTrapMICUnplugged NOTIFICATION-TYPE
	OBJECTS { ptMonSysName }
	STATUS  current
	DESCRIPTION
		"Notification that near-end microphone was unplugged"
	::= { ptNotificationPrefix 29 }

pictureTelTrapAudioMuted NOTIFICATION-TYPE
	OBJECTS { ptMonSysName }
	STATUS  current
	DESCRIPTION
		"Notification that near-end audio is muted"
	::= { ptNotificationPrefix 30 }

pictureTelTrapBatteriesLow NOTIFICATION-TYPE
	OBJECTS { ptMonSysName }
	STATUS  current
	DESCRIPTION
		"Notification that IR keypad batteries are running low"
	::= { ptNotificationPrefix 31 }

pictureTelTrapLAMBLow NOTIFICATION-TYPE
	OBJECTS { ptMonSysName }
	STATUS  current
	DESCRIPTION
		"Notification that LAMB batteries are running low"
	::= { ptNotificationPrefix 32 }

END
