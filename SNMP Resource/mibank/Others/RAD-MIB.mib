-- 
-- file :rad0485.pkb
-- 
RAD-MIB DEFINITIONS ::= BEGIN


--RAD0485-MIB
--Last revision: 01/10/02  SMI-v2
--
--                 
			

--Title:     rad0400   MIB
-- *** This file is for the modified newmasking MIB. ***
-- Copyright 2000 RAD Data Communications, Ltd.
-- All Rights Reserved.  

-- It is RAD's intent to encourage the widespread use of
-- this Specification in connection with the management of
-- RAD products. RAD grants vendors, end-users,
-- and other interested parties a non-exclusive license to
-- use this Specification in connection with the management
-- of RAD products.

-- This Specification is supplied "as is," and RAD makes
-- no warranty, either express or implied, as to the use,
-- operation, condition, or performance of the Specification.

IMPORTS
	  fddimibPORTPCMState             FROM FDDI-SMT73-MIB
	  rptrGroupOperStatus,            
	  rptrPortOperStatus			  FROM SNMP-REPEATER-MIB
	  rpMauMediaAvailable             FROM MAU-MIB
--      OBJECT-TYPE , 
      Integer32 , Counter32,
      TimeTicks,enterprises,
      IpAddress, Gauge32,
      OBJECT-TYPE, MODULE-IDENTITY,
      NOTIFICATION-TYPE, 
      OBJECT-IDENTITY                 FROM SNMPv2-SMI
      TimeStamp, TAddress,
--      TEXTUAL-CONVENTION, 
      DisplayString, RowStatus, 
      DateAndTime, TruthValue         FROM SNMPv2-TC
--      MODULE-COMPLIANCE, OBJECT-GROUP FROM SNMPv2-CONF
      AtmTrafficDescrParamIndex       FROM ATM-TC-MIB
--      AtmTrafficDescrParamIndex,
      atmVplVpi, atmVclVpi, atmVclVci,
	  aal5VccVpi, aal5VccVci,
      atmVclEntry, aal5VccEntry       FROM ATM-MIB
      frPVCEndptDLCIIndex             FROM FRNETSERV-MIB
	  VlanIndex 	                  FROM Q-BRIDGE-MIB
	  atmfCESCbrIndex,
	  atmfCESConfEntry                FROM ATMF-CES
      InterfaceIndex, ifAlias,
      ifIndex                         FROM IF-MIB
      imaGroupIndex, imaLinkIfIndex,
      imaGroupFailureStatus           FROM IMA-MIB 
      dsx1LineStatus, 
      dsx1LineStatusLastChange,
      dsx1CurrentIndex, dsx1LineIndex,
      dsx1IntervalIndex, dsx1IntervalNumber, 
      dsx1LoopbackStatus, 
      dsx1TotalIndex                  FROM DS1-MIB
      dsx3LineStatus, 
      dsx3LoopbackStatus              FROM DS3-MIB
      PerfCurrentCount, 
      PerfIntervalCount,
      PerfTotalCount                  FROM PerfHist-TC-MIB
      MmTAddressTag,MmEndpointID,
      MmAliasAddress,
		--MmH323EndpointType, 
	  MmGatekeeperID,MmAliasTag       FROM MULTI-MEDIA-REG-TC
	  SnmpAdminString                 FROM SNMP-FRAMEWORK-MIB
	  isdnSignalingEntry              FROM ISDN-MIB
	  frAtmIwfConnectionEntry		  FROM FR-ATM-PVC-SERVICE-IWF-MIB
      hdsl2ShdslEndpointCurrEntry,
      hdsl2ShdslInvIndex, 
      hdsl2ShdslEndpointSide,
	  hdsl2ShdslSpanConfProfileEntry  FROM HDSL2-SHDSL-LINE-MIB
	  IfIndexType					  FROM RFC1381-MIB;

-- Some MIB compilers need those two lines:
-- enterprises OBJECT IDENTIFIER ::=
--		     { iso org(3) dod(6) internet(1) private(4) 1 }

     rad MODULE-IDENTITY
         LAST-UPDATED "200210011220Z"
         ORGANIZATION "RAD MIB"
         CONTACT-INFO
           "        Smadar Tauber

            Postal: RAD Data Communications LTD.
                    24 Raoul Wallenberg St.	(Ziv-Towers)
                    Tel-Aviv, Israel

                    Tel: +972-3-765-9973
                    Fax: +972-3-644-0930

            E-mail: smadar_t@rad.co.il"
         DESCRIPTION
            "RAD MIB, version 485." 
         REVISION     "200202191210Z"
         DESCRIPTION
            "RAD MIB, version 480."
         ::= { enterprises 164 }


-- rad OBJECT IDENTIFIER ::= { enterprises 164 }
radTokenRing OBJECT IDENTIFIER ::= { rad 1 } -- RAD Token Ring tree
radFddi      OBJECT IDENTIFIER ::= { rad 2 } -- rad FDDI Tree
radWan       OBJECT IDENTIFIER ::= { rad 3 } -- RAD WAN
radBridges  OBJECT IDENTIFIER ::= {rad 4 }
radConverters OBJECT IDENTIFIER ::= { rad 5 }  -- RAD Converters products' tree
radGen        OBJECT IDENTIFIER ::= { rad 6} -- General information
radStkHub         OBJECT IDENTIFIER ::=  { rad 7 } -- stackable products
radPS        OBJECT IDENTIFIER ::= { rad 8 }  -- Packet Switch
radRouter    OBJECT IDENTIFIER ::= { rad 11 }  -- Routers
rtrBridge    OBJECT IDENTIFIER ::= { radRouter 7 }  
radAtm		 OBJECT IDENTIFIER ::= { rad 12 }  -- ATM Products
radExperimental OBJECT IDENTIFIER ::= { rad 20 }  -- Drafts that have no MIB tree yet
-- igmpStdMIB MODULE-IDENTITY ::= { radExperimental 1 }
-- apsMIB  OBJECT IDENTIFIER  ::= { radExperimental 2 }
-- atmApsMIB OBJECT IDENTIFIER ::= { radExperimental 3 }
-- frsldMIB OBJECT IDENTIFIER ::= { radExperimental 4 }
-- cpIwfMIB OBJECT IDENTIFIER ::= { radExperimental 5 }
-- hdsl2ShdslMIB OBJECT IDENTIFIER ::= { radExperimental 6 }


MacAddress ::= OCTET STRING (SIZE(6))
TimeSlots  ::= OCTET STRING (SIZE(4))


-- 
-- file :v:\doc\rdv\mib\ver485\radgen.txt
-- 
--First Version Date:   25.01.99              
--By:        Orly Nicklass
--File:      radgen.txt

--Last Update: 21-Aug-2002 by Yig'al Hachmon

systems OBJECT IDENTIFIER ::= { radGen 1}  --    list of RAD products

radSysTR  OBJECT IDENTIFIER ::= { systems 1 } -- RAD Token Ring 

radRADring    OBJECT IDENTIFIER  ::= { radSysTR  1 }

radTMA  OBJECT IDENTIFIER  ::= { radSysTR  2 }

radRingMonitor    OBJECT IDENTIFIER  ::= { radSysTR  3 }

radSysFddi OBJECT IDENTIFIER ::= { systems 2 } -- RAD Fddi 

radFDX100  OBJECT IDENTIFIER ::= { radSysFddi  1 } -- RAD Fddi
 
radSysWan OBJECT IDENTIFIER ::= { systems 3 }  -- RAD Wan products

radSysWanEvents OBJECT-IDENTITY
     STATUS  current
     DESCRIPTION
     "The events for RAD Wan products."
     ::= { radSysWan 0 }

radMP2100      OBJECT IDENTIFIER ::= { radSysWan  1 }
radMP2104      OBJECT IDENTIFIER ::= { radSysWan  2 }
radMP2100B     OBJECT IDENTIFIER ::= { radSysWan  3 }
radMP2100F     OBJECT IDENTIFIER ::= { radSysWan  4 }

radMP2100H      OBJECT IDENTIFIER ::= { radSysWan  5 }
radMP2104H      OBJECT IDENTIFIER ::= { radSysWan  6 }
radMP2200B      OBJECT IDENTIFIER ::= { radSysWan  7 }
radMP2200F      OBJECT IDENTIFIER ::= { radSysWan  8 }

radMX3000       OBJECT IDENTIFIER ::= { radSysWan  9 }
radMX3004       OBJECT IDENTIFIER ::= { radSysWan 10 }
radMX30			OBJECT IDENTIFIER ::= { radSysWan 11 }
radMX300		OBJECT IDENTIFIER ::= { radSysWan 12 }

radVOIP         OBJECT IDENTIFIER ::= { radSysWan 13 }

radKM2100	    OBJECT IDENTIFIER ::= { radSysWan 15 }
radKM2104		OBJECT IDENTIFIER ::= { radSysWan 16 }

radDXC30        OBJECT IDENTIFIER ::= { radSysWan 20 }
radDXC10A       OBJECT IDENTIFIER ::= { radSysWan 21 }
radDXC8R        OBJECT IDENTIFIER ::= { radSysWan 22 }
radDXC30E       OBJECT IDENTIFIER ::= { radSysWan 23 }
radDXC3000      OBJECT IDENTIFIER ::= { radSysWan 24 }
radDXC8RNew     OBJECT IDENTIFIER ::= { radSysWan 25 }

radFcdE1L        OBJECT IDENTIFIER ::= { radSysWan 29 }
radFcdT1         OBJECT IDENTIFIER ::= { radSysWan 30 }
radFcdE1         OBJECT IDENTIFIER ::= { radSysWan 31 }
radFcdE1I        OBJECT IDENTIFIER ::= { radSysWan 32 }
radFcdT1M        OBJECT IDENTIFIER ::= { radSysWan 33 }
radFcdE1M        OBJECT IDENTIFIER ::= { radSysWan 34 }
radFcdIP         OBJECT IDENTIFIER ::= { radSysWan 35} 
radFcdT1A        OBJECT IDENTIFIER ::= { radSysWan 36 }
radFcdE1A        OBJECT IDENTIFIER ::= { radSysWan 37 }
radFcdW          OBJECT IDENTIFIER ::= { radSysWan 38 }
radFcdSTM        OBJECT IDENTIFIER ::= { radSysWan 39 }

radHtuE1Sa      OBJECT IDENTIFIER ::= { radSysWan 40 }
radHtuE1        OBJECT IDENTIFIER ::= { radSysWan 41 }	 --card
radHtu2Sa       OBJECT IDENTIFIER ::= { radSysWan 42 }
radHtu2         OBJECT IDENTIFIER ::= { radSysWan 43 }	 --card
radAsmi450R768Sa OBJECT IDENTIFIER ::= { radSysWan 44 }
radAsmi450R768  OBJECT IDENTIFIER ::= { radSysWan 45 }	 --card
radAsmi450R1152Sa  OBJECT IDENTIFIER ::= { radSysWan 46 }
radAsmi450R1152 OBJECT IDENTIFIER ::= { radSysWan 47 }	 --card

radLrs12F        OBJECT IDENTIFIER ::= { radSysWan 48 }
radLrs12B        OBJECT IDENTIFIER ::= { radSysWan 49 }
radLrs52         OBJECT IDENTIFIER ::= { radSysWan 50 }

radHcdE1Sa       OBJECT IDENTIFIER ::= { radSysWan 51 }
radHcdE1         OBJECT IDENTIFIER ::= { radSysWan 52 }  --card
radHtuT1Sa       OBJECT IDENTIFIER ::= { radSysWan 53 }
radHtuT1         OBJECT IDENTIFIER ::= { radSysWan 54 }	 --card

radOptimux4E1         OBJECT IDENTIFIER ::= { radSysWan 55 }
radOptimux4T1         OBJECT IDENTIFIER ::= { radSysWan 56 }
radOptimuxXLE1         OBJECT IDENTIFIER ::= { radSysWan 57 }
radOptimuxXLT1         OBJECT IDENTIFIER ::= { radSysWan 58 }
radOptimuxXL16E1       OBJECT IDENTIFIER ::= { radSysWan 59 }

radImx64        OBJECT IDENTIFIER ::= { radSysWan 60 }
radImx6L        OBJECT IDENTIFIER ::= { radSysWan 61 }
radImx2         OBJECT IDENTIFIER ::= { radSysWan 62 }
radImx4T1       OBJECT IDENTIFIER ::= { radSysWan 63 }
radImx4E1       OBJECT IDENTIFIER ::= { radSysWan 64 }
radImx2T1E1     OBJECT IDENTIFIER ::= { radSysWan 65 }
radImxi4		OBJECT IDENTIFIER ::= { radSysWan 66 }

radOptimux4T1L    OBJECT IDENTIFIER ::= { radSysWan 68 }  --SA Low Cost
radOptimux4E1L    OBJECT IDENTIFIER ::= { radSysWan 69 }  --SA Low Cost
radHtuE1SaV2      OBJECT IDENTIFIER ::= { radSysWan 70 }
radHtuE1V2        OBJECT IDENTIFIER ::= { radSysWan 71 }  --card
radFomiE3         OBJECT IDENTIFIER ::= { radSysWan 72 }  --card
radFomiT3         OBJECT IDENTIFIER ::= { radSysWan 73 }  --card
radOpt4E1C        OBJECT IDENTIFIER ::= { radSysWan 74 }  --card
radOpt4T1C        OBJECT IDENTIFIER ::= { radSysWan 75 }  --card
radPrbiE3         OBJECT IDENTIFIER ::= { radSysWan 76 }  --SA
radPrbiT3         OBJECT IDENTIFIER ::= { radSysWan 77 }  --SA
radHcd4Sa         OBJECT IDENTIFIER ::= { radSysWan 78 }  --SA
radOptimuxT3      OBJECT IDENTIFIER ::= { radSysWan 79 }  --SA

radFRmon          OBJECT IDENTIFIER ::= { radSysWan 80 } 
radIpMux4         OBJECT IDENTIFIER ::= { radSysWan 81 } 
radIpMux1         OBJECT IDENTIFIER ::= { radSysWan 82 } 
radIpMux16        OBJECT IDENTIFIER ::= { radSysWan 83 } 
radIpMux1E        OBJECT IDENTIFIER ::= { radSysWan 84 }
radVmux2100       OBJECT IDENTIFIER ::= { radSysWan 85 }
-- reserved for radMP104          OBJECT IDENTIFIER ::= { radSysWan 86 }
-- reserved for radMP204          OBJECT IDENTIFIER ::= { radSysWan 87 }
radVmux110        OBJECT IDENTIFIER ::= { radSysWan 88 }

-- reserved for radFcd155         OBJECT IDENTIFIER ::= { radSysWan 90 }

radIpMux8        OBJECT IDENTIFIER ::= { radSysWan 91 }



radSysBRG OBJECT IDENTIFIER ::= { systems 4 }  -- RAD Bridges products

radTRE1  OBJECT IDENTIFIER ::= { radSysBRG 1 }  -- RAD Bridges products

radTRE1D  OBJECT IDENTIFIER ::= { radSysBRG 2 }  -- RAD Bridges products

radTRE8  OBJECT IDENTIFIER ::= { radSysBRG 3 }  -- RAD Bridges products

radTRE8D  OBJECT IDENTIFIER ::= { radSysBRG 4 }  -- RAD Bridges products

radMBE1  OBJECT IDENTIFIER ::= { radSysBRG 5 }  -- RAD Bridges products

radMBE1D  OBJECT IDENTIFIER ::= { radSysBRG  6 }  -- RAD Bridges products

radMBE8  OBJECT IDENTIFIER ::= { radSysBRG  7 }  -- RAD Bridges products

radMBE8D  OBJECT IDENTIFIER ::= { radSysBRG  8 }  -- RAD Bridges products

radMLBT   OBJECT IDENTIFIER ::= { radSysBRG  9 }  -- RAD Bridges products 

radFEB4DAS    OBJECT IDENTIFIER ::= { radSysBRG  10 }  -- RAD Bridges products

radTrimBrg10  OBJECT IDENTIFIER ::= { radSysBRG 11 }  -- RAD Bridges products

radTrimBrg16  OBJECT IDENTIFIER ::= { radSysBRG 12 }  -- RAD Bridges products

radRRTRE8  OBJECT IDENTIFIER ::= { radSysBRG 13 }  -- RAD Bridges products

radRRTRE8D  OBJECT IDENTIFIER ::= { radSysBRG 14 }  -- RAD Bridges products

radRRMLBT   OBJECT IDENTIFIER ::= { radSysBRG 15 }  -- RAD Bridges products 

radRRMLBTF   OBJECT IDENTIFIER ::= { radSysBRG 16 }  -- RAD Bridges products 

radRRTRE1D  OBJECT IDENTIFIER ::= { radSysBRG 17 }  -- RAD Bridges products

radTRERAS  OBJECT IDENTIFIER ::= { radSysBRG 18 }  -- RAD Bridges products

radTRERASa  OBJECT IDENTIFIER ::= { radSysBRG 19 }  -- RAD Bridges products

radMBERAS  OBJECT IDENTIFIER ::= { radSysBRG 20 }  -- RAD Bridges products

radMBERASa  OBJECT IDENTIFIER ::= { radSysBRG 21 }  -- RAD Bridges products
 
radFEB4FDX   OBJECT IDENTIFIER ::= { radSysBRG 22 }  -- RAD Bridges products

radFEB4SAS  OBJECT IDENTIFIER ::= { radSysBRG 23 }  -- RAD Bridges products

radRRFTBDAS  OBJECT IDENTIFIER ::= { radSysBRG 24 }  -- RAD Bridges products

radRRFTBSAS  OBJECT IDENTIFIER ::= { radSysBRG 25 }  -- RAD Bridges products

radFTBDAS    OBJECT IDENTIFIER ::= { radSysBRG 26 }  -- RAD Bridges products

radFTBSAS    OBJECT IDENTIFIER ::= { radSysBRG 27 }  -- RAD Bridges products

radFastWay100    OBJECT IDENTIFIER ::= { radSysBRG 28 }  -- RAD Bridges products

radSysCnvrtr OBJECT IDENTIFIER ::= { systems 5 }  -- RAD Converters products

radSTC1   OBJECT IDENTIFIER ::= { radSysCnvrtr 1 }  -- RAD Converters products

radSTC2   OBJECT IDENTIFIER ::= { radSysCnvrtr 3 }  -- RAD Converters products

radSTC1UDP  OBJECT IDENTIFIER ::= { radSysCnvrtr 4 }  -- RAD Converters products

radSTC2UDP  OBJECT IDENTIFIER ::= { radSysCnvrtr 6 }  -- RAD Converters products

radFTC1   OBJECT IDENTIFIER ::= { radSysCnvrtr 10 }  -- RAD Converters products

radFTC2   OBJECT IDENTIFIER ::= { radSysCnvrtr 12 }  -- RAD Converters products

radFTC1UDP    OBJECT IDENTIFIER ::= { radSysCnvrtr 13 }  -- RAD Converters products

radFTC2UDP    OBJECT IDENTIFIER ::= { radSysCnvrtr 15 }  -- RAD Converters products

radSEC1   OBJECT IDENTIFIER ::= { radSysCnvrtr 20 }  -- RAD Converters products

radSEC2   OBJECT IDENTIFIER ::= { radSysCnvrtr 22 }  -- RAD Converters products

radSEC1UDP   OBJECT IDENTIFIER ::= { radSysCnvrtr 23 }  -- RAD Converters products

radSEC2UDP   OBJECT IDENTIFIER ::= { radSysCnvrtr 25 }  -- RAD Converters products

radFEC1   OBJECT IDENTIFIER ::= { radSysCnvrtr 30 }  -- RAD Converters products

radFEC2   OBJECT IDENTIFIER ::= { radSysCnvrtr 32 }  -- RAD Converters products

radFEC1UDP   OBJECT IDENTIFIER ::= { radSysCnvrtr 33 }  -- RAD Converters products

radFEC2UDP   OBJECT IDENTIFIER ::= { radSysCnvrtr 35 }  -- RAD Converters products

radSysStkHub  OBJECT IDENTIFIER ::= { systems 7 }  -- RAD Stackable products

radRBHE    OBJECT IDENTIFIER ::= { radSysStkHub 1 }  -- RAD Stackable products

radRBHT    OBJECT IDENTIFIER ::= { radSysStkHub 2 }  -- RAD Stackable products

radRBHEEvents OBJECT-IDENTITY
     STATUS  current
     DESCRIPTION
     "The events for RAD Stackable products."
     ::= { radRBHE 0 }

radRBHTEvents OBJECT-IDENTITY
     STATUS  current
     DESCRIPTION
     "The events for RAD Stackable products."
     ::= { radRBHT 0 }

radETS4fddiDAS   OBJECT IDENTIFIER ::= { radSysStkHub 3 }  -- RAD Stackable products

radETS4fddiSAS   OBJECT IDENTIFIER ::= { radSysStkHub 4 }  -- RAD Stackable products

radSAHEMX  OBJECT IDENTIFIER ::= { radSysStkHub 5 }  -- RAD Stackable products

radSAHTM   OBJECT IDENTIFIER ::= { radSysStkHub 6 }  -- RAD Stackable products

radETS4   OBJECT IDENTIFIER ::= { radSysStkHub 7 }  -- RAD Stackable products

radSAHEMU  OBJECT IDENTIFIER ::= { radSysStkHub 8 }  -- RAD Stackable products


unknown    	OBJECT IDENTIFIER ::= { radSysStkHub 9 }  -- RAD Stackable products

radSAH16Eint   OBJECT IDENTIFIER ::= { radSysStkHub 10 }  -- RAD Stackable products

radSAH16Tint   OBJECT IDENTIFIER ::= { radSysStkHub 11 }  -- RAD Stackable products

radSAH16Eext   OBJECT IDENTIFIER ::= { radSysStkHub 12 }  -- RAD Stackable products

radSAH16Text   OBJECT IDENTIFIER ::= { radSysStkHub 13 }  -- RAD Stackable products



radSysPS OBJECT IDENTIFIER ::=  { systems 8 } -- RAD Packet Switch  (PS) products 

radSysPSEvents OBJECT-IDENTITY
     STATUS  current
     DESCRIPTION
     "The events for RAD Packet Switch  (PS) products."
     ::= { radSysPS 0 }

radSPS2  OBJECT IDENTIFIER ::=  { radSysPS 1 } -- RAD Packet Switch  (PS) products 

radSPS3  OBJECT IDENTIFIER ::=  { radSysPS 2 } -- RAD Packet Switch  (PS) products 

radSPS6  OBJECT IDENTIFIER ::=  { radSysPS 3 } -- RAD Packet Switch  (PS) products 

radSPS9  OBJECT IDENTIFIER ::=  { radSysPS 4 } -- RAD Packet Switch  (PS) products 

radSPS12 OBJECT IDENTIFIER ::=  { radSysPS 5 } -- RAD Packet Switch  (PS) products 

radAPD2  OBJECT IDENTIFIER ::=  { radSysPS 6 } -- RAD Packet Switch  (PS) products 

radAPD8  OBJECT IDENTIFIER ::=  { radSysPS 7 } -- RAD Packet Switch  (PS) products 

radAPS8  OBJECT IDENTIFIER ::=  { radSysPS 8 } -- RAD Packet Switch  (PS) products 

radAPS16 OBJECT IDENTIFIER ::=  { radSysPS 9 } -- RAD Packet Switch  (PS) products 

radAPS24 OBJECT IDENTIFIER ::=  { radSysPS 10 } -- RAD Packet Switch  (PS) products 

radSPS3S  OBJECT IDENTIFIER ::=  { radSysPS 11} -- RAD Packet Switch  (PS) products 

radFPS8  OBJECT IDENTIFIER ::=  { radSysPS 12} -- RAD Packet Switch  (PS) products 

radFPS12  OBJECT IDENTIFIER ::=  { radSysPS 13} -- RAD Packet Switch  (PS) products 

radSPS3ScSL  OBJECT IDENTIFIER ::= { radSysPS 14} -- RAD Packet Switch  (PS) products 

radSPS3Sc2S  OBJECT IDENTIFIER ::=  { radSysPS 15} -- RAD Packet Switch  (PS) products 

radFPS8c OBJECT IDENTIFIER ::=  { radSysPS 16} -- RAD Packet Switch  (PS) products

radFPS4 OBJECT IDENTIFIER ::=  { radSysPS 17} -- RAD Packet Switch  (PS) products



radSysEth  OBJECT IDENTIFIER ::= { systems 9 } -- RAD Ethernet products 

radEP8T    OBJECT IDENTIFIER ::= {radSysEth 1} -- RAD Ethernet products

radEP4TAUI   OBJECT IDENTIFIER ::= {radSysEth 2} -- RAD Ethernet products

radEP4T2FL   OBJECT IDENTIFIER ::= {radSysEth 3} -- RAD Ethernet products

radEP4TFL    OBJECT IDENTIFIER ::= {radSysEth 4} -- RAD Ethernet products

radEP4FL     OBJECT IDENTIFIER ::= {radSysEth 5} -- RAD Ethernet products


radEPR8T   OBJECT IDENTIFIER ::= {radSysEth 7} -- RAD Ethernet products

radEPR4TAUI  OBJECT IDENTIFIER ::= {radSysEth 8} -- RAD Ethernet products

radEPR4T2FL  OBJECT IDENTIFIER ::= {radSysEth 9} -- RAD Ethernet products

radEPR4TFL   OBJECT IDENTIFIER ::= {radSysEth 10} -- RAD Ethernet products

radEPR4FL    OBJECT IDENTIFIER ::= {radSysEth 11} -- RAD Ethernet products



radSysRtr  OBJECT IDENTIFIER ::= { systems 11 } -- RAD Router products 

radSysRtrEvents OBJECT-IDENTITY
     STATUS  current
     DESCRIPTION
     "The events for RAD Router products."
     ::= { radSysRtr 0 }

radRTED    OBJECT IDENTIFIER ::= {radSysRtr 1} -- RAD Router products

radRTEM    OBJECT IDENTIFIER ::= {radSysRtr 2} -- RAD Router products

radRTEC    OBJECT IDENTIFIER ::= {radSysRtr 3} -- RAD Router products

radWebRanger    OBJECT IDENTIFIER ::= {radSysRtr 4} -- RAD Router products

radTinyRouter   OBJECT IDENTIFIER ::= {radSysRtr 5} -- RAD Router products

radLA240	    OBJECT IDENTIFIER ::= {radSysRtr 6} -- RAD Router products

radSuperLan	    OBJECT IDENTIFIER ::= {radSysRtr 7} -- RAD Router products (LA-240)

radLA240I	    OBJECT IDENTIFIER ::= {radSysRtr 8} -- RAD Router products

radFcdIsdn      OBJECT IDENTIFIER ::= {radSysRtr 9} -- RAD Router products

radEFcdIp	    OBJECT IDENTIFIER ::= {radSysRtr 10} -- RAD Router products (FCD-IP/D)

radFcdIpD       OBJECT IDENTIFIER ::= {radSysRtr 11} -- RAD Router products

radFcdIpM       OBJECT IDENTIFIER ::= {radSysRtr 12} -- RAD Router products (LA-240)


radSysAtm  OBJECT IDENTIFIER ::= { systems 12 } -- RAD ATM products 

radSysAtmEvents OBJECT-IDENTITY
     STATUS  current
     DESCRIPTION
     "The events for RAD ATM products."
     ::= { radSysAtm 0 }

radStarSwitch    OBJECT IDENTIFIER ::= {radSysAtm 1} --RAD StartSwitch products

radStarSwitchATM25    OBJECT IDENTIFIER ::= {radStarSwitch 1} --RAD StartSwitch products
radStarSwitchATM25L   OBJECT IDENTIFIER ::= {radStarSwitch 2} --RAD StartSwitch products
radStarSwitchATM155   OBJECT IDENTIFIER ::= {radStarSwitch 3} --RAD StartSwitch products


radAtmCsuDsu  OBJECT IDENTIFIER ::= {radSysAtm 2} --RAD CSU/DSU products 

radAmcdE1  OBJECT IDENTIFIER ::= {radAtmCsuDsu 1} -- RAD CSU/DSU products
radAmcdT1  OBJECT IDENTIFIER ::= {radAtmCsuDsu 2} -- RAD CSU/DSU products
radAce20E  OBJECT IDENTIFIER ::= {radAtmCsuDsu 3} -- RAD CSU/DSU products
radAce20T  OBJECT IDENTIFIER ::= {radAtmCsuDsu 4} -- RAD CSU/DSU products

radAce2005 OBJECT IDENTIFIER ::= { radAtmCsuDsu 5} -- RAD ACE2005
radAce2002 OBJECT IDENTIFIER ::= { radAtmCsuDsu 6} -- RAD ACE2002
radAce2002E OBJECT IDENTIFIER ::= { radAtmCsuDsu 7} -- RAD ACE2002E

radAce2E  OBJECT IDENTIFIER ::= {radAtmCsuDsu 8} -- RAD CSU/DSU products
radAce2T  OBJECT IDENTIFIER ::= {radAtmCsuDsu 9} -- RAD CSU/DSU products

radMlAtmE1  OBJECT IDENTIFIER ::= {radAtmCsuDsu 10} -- RAD ATM Piggy
radMlAtmT1  OBJECT IDENTIFIER ::= {radAtmCsuDsu 11} -- RAD ATM Piggy

radAmc102  OBJECT IDENTIFIER ::= {radAtmCsuDsu 12} -- RAD AMC102
radAmc102c  OBJECT IDENTIFIER ::= {radAtmCsuDsu 13} -- RAD AMC102 CARD

radAce202 OBJECT IDENTIFIER ::= { radAtmCsuDsu 14} -- RAD ACE202

radAce  OBJECT IDENTIFIER ::= {radSysAtm 3} --RAD ACE products 
radAce101  OBJECT IDENTIFIER ::= {radAce 1} -- RAD ACE101
radAce102  OBJECT IDENTIFIER ::= {radAce 2} -- RAD ACE102
radAce50  OBJECT IDENTIFIER ::= {radAce 3} -- RAD ACE50

radSysLA	  OBJECT IDENTIFIER ::= {systems 13} --RAD  IAD (Integrated Access Device) products
radLA140      OBJECT IDENTIFIER ::= {radSysLA 1} -- RAD LA-140
radLA110      OBJECT IDENTIFIER ::= {radSysLA 2} -- RAD LA-110
radLA104      OBJECT IDENTIFIER ::= {radSysLA 3} -- RAD LA-104 (LA-110 with IMA)


radSysTerminal  OBJECT IDENTIFIER ::= {systems 100} --RAD Terminal Meta-MIB; 
-- no objects should be added to this branch in RAD MIB.                                     


agnt OBJECT IDENTIFIER ::= { radGen 2} 
-- agent general tree
-- Agent General  
agnHwVersion OBJECT-TYPE
      SYNTAX  DisplayString
      MAX-ACCESS  read-write
      STATUS  current
      DESCRIPTION
      "ASCII string for description and display of the agent hardware version,
      as it is known by the agent software.The user can update the version
       upon request when he changes   components in the agent's module  "
      ::= { agnt 1 }

agnTrapMask OBJECT-TYPE   
      SYNTAX  Integer32 
      MAX-ACCESS  read-write    
      STATUS  current
      DESCRIPTION
      "The value of this attribute determines the type of traps the 
       agent should mask and not send to the management console. The 
       value is differently determined for different products. There are 
       mainly two methods:
       - an integer number, specifying the traps' severity.
       - a sum of 2**n, where n is a bit assigned to a certain 
         masked trap group.
       User should consult the product specification, to find out 
       the method employed."
      ::= { agnt 2 }

agnTrapValue OBJECT-TYPE
	SYNTAX  OCTET STRING
	MAX-ACCESS  read-only
	STATUS deprecated
	DESCRIPTION
	"The value of the trap decoded in internal RAD format. Full description is given
	  in the Trap definition file"
	::= {agnt 3}

agnChangeCnt OBJECT-TYPE
	SYNTAX  Counter32
	MAX-ACCESS  read-only
	STATUS current
	DESCRIPTION
	"The number of changes in system configuration that were  reported to the 
	manager since last cold start"
	::= {agnt 4 }

agnSpecific OBJECT-TYPE
      SYNTAX  OBJECT IDENTIFIER
      MAX-ACCESS  read-only
      STATUS  current
      DESCRIPTION
      " Object identifier of entity containing additional information 
      regarding this instance."
      ::= { agnt 5}

agnConfigMsg OBJECT-TYPE   
      SYNTAX  OCTET STRING
      MAX-ACCESS  read-only
      STATUS  current
      DESCRIPTION
      "Full configuration message  coded in internal RAD application format.
       This entry describes agent's configuration.

       For MP-2200 R3, this object describes agent's support of the V5.1
       feature: 1 octet ; bit 0 (LSB). 
       '1' - V5.1 feature is supported
       '0' - V5.1 feature is not supported."
      ::= { agnt 6 }

-- Manager table to record all IP addresses

mngTrapIpTable  OBJECT-TYPE
	SYNTAX  SEQUENCE OF MngEntry
	MAX-ACCESS  not-accessible
	STATUS current
	DESCRIPTION
	"This table indicates  the destination address of the traps.
	  Internally it will be limited to ten addresses. "
	::= { agnt 7 }

mngEntry OBJECT-TYPE
	SYNTAX  MngEntry
	MAX-ACCESS  not-accessible
	STATUS current
	DESCRIPTION  "An entry in table."
	INDEX {  mngID }
	::= { mngTrapIpTable 1 }


MngEntry  ::=
	    SEQUENCE {
	mngID
	  Integer32,
	mngIP
	  IpAddress,
	mngIPMask
	  IpAddress,
    mngTrapMask
      Integer32	
    }

mngID OBJECT-TYPE
	SYNTAX  Integer32 
	MAX-ACCESS  read-only
	STATUS current
	DESCRIPTION
	" This value indicates an index of a specific IP address"
	::= { mngEntry 1 }

mngIP OBJECT-TYPE
	SYNTAX  IpAddress 
	MAX-ACCESS  read-write
	STATUS current
	DESCRIPTION
	"This value indicates  the  destination address of the traps. IP 0.0.0.0 removes the entry. "
	::= { mngEntry 2 }

mngIPMask OBJECT-TYPE
	SYNTAX  IpAddress 
	MAX-ACCESS  read-write
	STATUS deprecated
	DESCRIPTION
	"This value indicates  the  mask of the destination addresses of the traps. "
	::= { mngEntry 3 }

mngTrapMask OBJECT-TYPE
	SYNTAX  Integer32 
	MAX-ACCESS  read-write
	STATUS current
	DESCRIPTION
      "The value of this attribute determines the type of traps the 
       agent should mask and not send to this NMS. The 
       value is differently determined for different products. There are 
       mainly two methods:
       - an integer number, specifying the traps' severity.
       - a sum of 2**n, where n is a bit assigned to a certain 
         masked trap group.
       User should consult the product specification, to find out 
       the method employed."
	::= { mngEntry 4 }

agnIndication OBJECT-TYPE   
      SYNTAX  INTEGER {
		 faulty  (1), -- =major
		 warning (2),
		 normal  (3), -- off
		 minor   (4),
		 major   (5),
		 event   (6),
		 critical(7)
		}
      MAX-ACCESS  read-only
      STATUS  current
      DESCRIPTION
      "Attribute describing the state of the entity the agent is responsible for.
       In case of a modular entity, the value of this attribute will be according
       to the component which is in the worst state.
       The order of severity (from top to bottom) is:
       critical-> major (or faulty)-> minor-> event-> warning-> normal (off)."   
      ::= { agnt 8 }


agnMonitorModeCmd OBJECT-TYPE
	SYNTAX  INTEGER {
	notApplicable(1),
	off(2),
	on(3)
	}
	MAX-ACCESS  read-write
	STATUS current
	DESCRIPTION
	"Setting this attribute to ON, will enforce the agent to change its mode of operation to
	 Monitor Mode"
	::= {agnt 9}

agnLed OBJECT-TYPE
	SYNTAX  OCTET STRING
	MAX-ACCESS  read-only
	STATUS current
	DESCRIPTION
	"This entry specifies  the LEDs status of the agent module . Each led will be represented by 4 
	 bits  where the first 2 bits (left) will specify  the status :
	 (00=NA, 01=OFF, 10=ON, 11=BLINK),
     and the next two bits (right) will specify the color :
     (00=GREEN, 01=RED, 10=YELLOW, 11=GRAY)"
	::= {agnt 10}

trapTable  OBJECT-TYPE
	SYNTAX  SEQUENCE OF TrapEntry
	MAX-ACCESS  not-accessible
	STATUS current
	DESCRIPTION
	"This table includes the last few traps generated by the agent, for future retrieval. The table
	 has a limited capacity. If traps are not retrieved in proper time, they will be
	 over-written by new traps "
	::= {agnt 11}

trapEntry OBJECT-TYPE
	SYNTAX  TrapEntry
	MAX-ACCESS  not-accessible
	STATUS current
	DESCRIPTION  "An entry in table."
	INDEX {  trapID }
	::= { trapTable 1 }

TrapEntry  ::=
	    SEQUENCE {
	trapID
	  Integer32,
	trapVal
	  DisplayString,
	 trapTimeSinceOccurrence
	   TimeTicks
	}

trapID OBJECT-TYPE
	SYNTAX  Integer32 
	MAX-ACCESS  read-only
	STATUS current
	DESCRIPTION
	" This value indicates an index of a specific trap "
	::= { trapEntry 1 }

trapVal OBJECT-TYPE
	SYNTAX  DisplayString 
	MAX-ACCESS  read-only
	STATUS current
	DESCRIPTION
	"This value is the actual ASCII description  of the trap. "
	::= { trapEntry 2 }

trapTimeSinceOccurrence OBJECT-TYPE
	 SYNTAX    TimeTicks
	MAX-ACCESS  read-only
	STATUS current
	DESCRIPTION
	"This value indicates the amount of  time passed since the occurrence of the event that
	   trigger this trap. "
	::= { trapEntry 3 }

fileTransfer  OBJECT IDENTIFIER ::= { agnt 12 }

fileServerIP  OBJECT-TYPE
	SYNTAX  IpAddress
	MAX-ACCESS  read-write
	STATUS  current
	DESCRIPTION
	"The IP address of the server from which the file is loaded "
	::= { fileTransfer 1 }

fileName  OBJECT-TYPE
	SYNTAX  DisplayString
	MAX-ACCESS  read-write
	STATUS  current
	DESCRIPTION
	"The name of the file to be loaded. For protection, read returns
	 NULL. "
	::= { fileTransfer 2 }

fileTransCmd  OBJECT-TYPE
	SYNTAX  INTEGER {
	                 swDwnLoad     (1),
					 configDwnLoad (2),
					 configUpLoad  (3),
					 coProcDwnLoad (4),
					 stateUpLoad   (5),
					 dwnLoadUserFile   (6),
					 upLoadUserFile    (7), 
					 swDwnLoadAndReset (8), 
					 noOp            (255)
					}
	MAX-ACCESS  read-write
	STATUS  current
	DESCRIPTION
	"The command to be executed on fileName at fileServerIP."
	::= { fileTransfer 3 }
 
-- tftp  group  

tftpRetryTimeOut OBJECT-TYPE
    SYNTAX  Integer32
    MAX-ACCESS  read-write
    STATUS  current
    DESCRIPTION
        " General Retransmission time-out value (seconds) "
    -- DEFVAL  { 15 }
    ::= { fileTransfer 4 }

tftpTotalTimeOut OBJECT-TYPE
    SYNTAX  Integer32
    MAX-ACCESS  read-write
    STATUS  current
    DESCRIPTION
        " Total Retransmission time-out value (seconds) "
    -- DEFVAL  { 60 }
    ::= { fileTransfer 5 }

tftpStatus OBJECT-TYPE
    SYNTAX  INTEGER {
		noOp(2),
		connecting(3),
		transferringData(4),
		endedTimeOut(5),
		endedOk(6),
		error(7)
	}
    MAX-ACCESS  read-write
    STATUS  current
    DESCRIPTION
    "Status of tftp session. When a session ended with success,
    the tftpStatus should be endedOk(6). Before restarting a
    tftp session, the NMS should set the tftpStatus to noOp(2).
    That's the reason of MAX-ACCESS read-write to this field."
    DEFVAL  { noOp}
    ::= { fileTransfer 6 }

tftpError OBJECT-TYPE
    SYNTAX  OCTET STRING ( SIZE(2) )
    MAX-ACCESS  read-only
    STATUS  current
    DESCRIPTION
    " The MSB represents the standard error code.
    The LSB represents the private error code.
    0x0000 is No Error
    0x0100 is File Not Found
    0x0400 is Illegal TFTP operation
    0x0500 is Unknown transfer ID
    0x0001 is Server Overflow
    0x0002 is No empty UDP port
    0x0003 is No empty connection
    0x0004 is Illegal File Mode
    0x0007 is Illegal PDU size "
    DEFVAL  { '0000'h }
    ::= { fileTransfer 7 }

fileTransferToSubSystems OBJECT-TYPE
    SYNTAX  OCTET STRING 
    MAX-ACCESS  read-write
    STATUS  current
    DESCRIPTION
    " This object represents the sub-systems the fileTransCmd 
      refers to. It should be used when a system is divided 
      to sub-systems and each sub-system (or part of them) can 
	  have a different SW/Configuration.

	  Each bit of this object will represent one of the sub-systems.
	  Bit='1' - APPLY to respective sub-system
	  Bit='0' - DO NOT APPLY to respective sub-system

	  For the meaning of each bit, see product's specification.
	  User will select the sub-systems envolved by filling-in the bits
      that represent these sub-systems.
      In this case, the file represented by 'fileName' will 
	  include several parts, each representing one of the sub-systems.
	  The agent will refer only to the part/s indicated by this object.

      0 Octet Strings = not applicable  
      DEFVAL = 0h	for  the products that support this object."
    ::= { fileTransfer 8 }


fileNameWithinProduct  OBJECT-TYPE
	SYNTAX  DisplayString
	MAX-ACCESS  read-write
	STATUS  current
	DESCRIPTION
	"The file name used by the product within the product file system."
	::= { fileTransfer 9 }

--Internal SW Download table

intSwdlTable  OBJECT-TYPE 
      SYNTAX SEQUENCE OF IntSwdlEntry
      MAX-ACCESS not-accessible
      STATUS  current
      DESCRIPTION
      "This parameters table is for 
       internal Software down load. It also includes data 
       about all files contained in the Object from which 
       down-load is performed."
      ::= { fileTransfer 10 }

intSwdlEntry OBJECT-TYPE
      SYNTAX IntSwdlEntry
      MAX-ACCESS not-accessible
      STATUS current
	DESCRIPTION  "An entry in table."
	INDEX {intSwdlObjIdx, intSwdlFileIdx }
      ::= { intSwdlTable 1}

IntSwdlEntry ::=
      SEQUENCE {
      intSwdlObjIdx            Integer32,
	  intSwdlFileIdx           Integer32,
	  intSwdlFileName		   DisplayString,
	  intSwdlFileSwVer		   DisplayString,
	  intSwdlSwDate			   DisplayString,
	  intSwdlSize			   DisplayString,
	  intSwdlCmd			   INTEGER,
	  intSwdlToSubSystem	   OCTET STRING
      }

intSwdlObjIdx OBJECT-TYPE
      SYNTAX  Integer32
      MAX-ACCESS  read-only
      STATUS  current
      DESCRIPTION
      "The index of the object from which down-load is performed."
      ::= {intSwdlEntry 1}

intSwdlFileIdx OBJECT-TYPE
      SYNTAX  Integer32
      MAX-ACCESS  read-only
      STATUS  current
      DESCRIPTION
      "The index of the files included in intSwdlObjIdx.
       One of these files can be selected to be internally 
       downloaded."
      ::= {intSwdlEntry 2}

intSwdlFileName OBJECT-TYPE
      SYNTAX  	 DisplayString
      MAX-ACCESS  read-only
      STATUS  current
      DESCRIPTION
      "The name of the file."
      ::= {intSwdlEntry 3}

intSwdlFileSwVer OBJECT-TYPE
      SYNTAX  	 DisplayString
      MAX-ACCESS  read-only
      STATUS  current
      DESCRIPTION
      "The software version of the file."
      ::= {intSwdlEntry 4}

intSwdlSwDate OBJECT-TYPE
      SYNTAX  	 DisplayString
      MAX-ACCESS  read-only
      STATUS  current
      DESCRIPTION
      "The software version date of the file."
      ::= {intSwdlEntry 5}

intSwdlSize OBJECT-TYPE
      SYNTAX  	 DisplayString
      MAX-ACCESS  read-only
      STATUS  current
      DESCRIPTION
      "The size of the file."
      ::= {intSwdlEntry 6}

intSwdlCmd OBJECT-TYPE
      SYNTAX  	  INTEGER
	  				{
					notApplicable		(1),
					off		(2),
					on		(3)
					}
      MAX-ACCESS  read-write
      STATUS  current
      DESCRIPTION
      "The command to down-load a SW file to an object.
       The Agent will change the value of this MIB object to off(2) 
	  automatically, after accepting the command."
      ::= {intSwdlEntry 7}

intSwdlToSubSystem	OBJECT-TYPE   
      SYNTAX  OCTET STRING
      MAX-ACCESS  read-write
      STATUS  current
      DESCRIPTION
      " This object defines the subsystem for download.
       Bit='1'- APPLY to respective sub system.
       Bit='0'- DO NOT APPLY to respective sub system.
       For more details see product specification. 
       For every octet bit0=LSB, bit7=MSB"
      ::= { intSwdlEntry  8 }

--SW Download Status table

swdlStatusTable  OBJECT-TYPE 
      SYNTAX SEQUENCE OF SwdlStatusEntry
      MAX-ACCESS not-accessible
      STATUS  current
      DESCRIPTION
      "This parameters table is for software download status. 
       It also includes data about the files down-loaded or 
       attempted to be down-loaded."
      ::= { fileTransfer 11 }

swdlStatusEntry OBJECT-TYPE
      SYNTAX SwdlStatusEntry
      MAX-ACCESS not-accessible
      STATUS current
	DESCRIPTION  "An entry in table."
	INDEX {swdlStatusTypeIdx, swdlStatusIdx }
      ::= { swdlStatusTable 1}

SwdlStatusEntry ::=
      SEQUENCE {
      swdlStatusTypeIdx            Integer32,
	  swdlStatusIdx       		   Integer32,
	  swdlStatusFileName		   DisplayString,
	  swdlStatusSlot			   DisplayString,
	  swdlStatusSubSystem		   DisplayString,
	  swdlStatusStatus			   Integer32,
	  swdlStatusTime			   DisplayString
	       }

swdlStatusTypeIdx OBJECT-TYPE
      SYNTAX  Integer32
      MAX-ACCESS  read-only
      STATUS  current
      DESCRIPTION
      "The index of the down-load type (e.g. external (1) or internal (2))."
      ::= {swdlStatusEntry 1}

swdlStatusIdx OBJECT-TYPE
      SYNTAX  Integer32
      MAX-ACCESS  read-only
      STATUS  current
      DESCRIPTION
      "The index of the status rows."
      ::= {swdlStatusEntry 2}

swdlStatusFileName OBJECT-TYPE
      SYNTAX  	 DisplayString
      MAX-ACCESS  read-only
      STATUS  current
      DESCRIPTION
      "The name of the file."
      ::= {swdlStatusEntry 3}

swdlStatusSlot OBJECT-TYPE
      SYNTAX  	 DisplayString
      MAX-ACCESS  read-only
      STATUS  current
      DESCRIPTION
      "The slot of the updated (or attempted to be updated) object."
      ::= {swdlStatusEntry 4}

 swdlStatusSubSystem OBJECT-TYPE
      SYNTAX  	 DisplayString
      MAX-ACCESS  read-only
      STATUS  current
      DESCRIPTION
      "The subsystem that updated (or attempted to be updated)."
      ::= {swdlStatusEntry 5}

swdlStatusStatus  OBJECT-TYPE
      SYNTAX  	  Integer32
      MAX-ACCESS  read-only
      STATUS  current
      DESCRIPTION
      "The status of the down load process.
	  Value:  Fail (2), OK (3), InProcess (4)."
      ::= {swdlStatusEntry 6}

swdlStatusTime	   OBJECT-TYPE
          SYNTAX   DisplayString
          MAX-ACCESS  read-only
          STATUS  current
          DESCRIPTION
          "This MIB parameter indicates the time SW download was finished.
           The format shuld be YYYY-MM-DD, hh:mm:ss"

          ::= {swdlStatusEntry 7}

clearDwldStatusLog  OBJECT-TYPE
	SYNTAX  Integer32
	MAX-ACCESS  read-write
	STATUS  current
	DESCRIPTION
	"This object clears the status log.
	  Value: off(2), external(3), internal(4)
	  The Agent will change the value of this MIB object to off(2) 
	  automatically, after accepting the command ."
	::= { fileTransfer 12 }


systemReset  OBJECT-TYPE
	SYNTAX  INTEGER	{
	                 off         (2),
					 on          (3), --HW
					 resetConfig (4)  
				    }
	MAX-ACCESS  read-write
	STATUS  current
	DESCRIPTION
	"Reset action to be performed on the system."
	::= { agnt 13 }

systemTiming  OBJECT IDENTIFIER ::= { agnt 14 }

systemDate OBJECT-TYPE
        SYNTAX  DisplayString
        MAX-ACCESS  read-write
        STATUS  current
        DESCRIPTION
           "System date."
        ::= { systemTiming 1 }
        
systemTime OBJECT-TYPE
        SYNTAX  DisplayString
        MAX-ACCESS  read-write
        STATUS  current
        DESCRIPTION
           "System time."
        ::= { systemTiming 2 }


systemPort  OBJECT IDENTIFIER ::= { agnt 15 }

physicalConnectorTable OBJECT-TYPE
	SYNTAX  SEQUENCE OF PhysicalConnectorEntry
	MAX-ACCESS  not-accessible
	STATUS current
	DESCRIPTION
	"This table includes the connector type of ports or interfaces."
	::= {systemPort 1}

physicalConnectorEntry OBJECT-TYPE
	SYNTAX  PhysicalConnectorEntry
	MAX-ACCESS  not-accessible
	STATUS current
	DESCRIPTION  "An entry in table."
	INDEX {portIdx}
	::= { physicalConnectorTable 1 }

PhysicalConnectorEntry  ::=
	    SEQUENCE {
	portIdx
	  Integer32,
	physicalConnector
	  INTEGER,
	portOptWaveLength
	  INTEGER,
	portOptMode
	  INTEGER
	}

portIdx OBJECT-TYPE
	SYNTAX  Integer32 
	MAX-ACCESS  read-only
	STATUS current
	DESCRIPTION
	"This object is an index of the specific port or interface.
	 For a port, the index will be as agreed between agent and 
	 application.
	 For an interface, ifIndex may be used."
	::= { physicalConnectorEntry 1 }

physicalConnector OBJECT-TYPE
	SYNTAX  INTEGER 
	        {
			other (1),
			v35   (2),	  --34 pin female
			rs530 (3),	  --DB25
			x21   (4),	  --DB15
			bnc   (5),
			utp   (6),	  --RJ45
			aui   (7),
			rs422 (8),	  --DB25
			crossUtp (9), --RJ45
			rj45    (10),
			v24     (11), --DB25
			g703    (12), --TB5
			termBlock3AndRj45 (13),
			terminalBlock3    (14),
			terminalBlock5    (15),
			terminalBlock7    (16),
			db25              (17),
			db15              (18),
			rj45ethernet      (19),
			termBlock5AndRj45 (20),
			db9               (21),
			g703E1            (22),  --BNC-RJ45-BNC	
			g703E1-LTU        (23),  --BNC-RJ45-BNC
			sc                (24),	 --sc optical 
			st                (25),	 --st optical
			stl               (26),
			fc                (27),	 --fc optical
			tb5w              (28),  --Term-Block-5-Wire (for HCD)
			termBlock6AndRj45 (29),
			ethBnc            (30),
			scsi26            (31),  --SCSI with 26 pins
			eth4381           (32),  --RJ45 with two embeded LEDs
			twoBnc			  (33),  --Two BNC
			scsi50            (34),  --SCSI with 50 pins
			twoMiniBnc        (35),  --Two mini BNC
			sf1               (36),  --sf1=single fiber optical 
			terminalBlock4    (37),
			sf2         	  (38),  --sf2=single fiber optical
			db25Balanced      (39),  --DB25 Balanced
			v36               (40),
			block4W           (41),  --like in WR connector for Modems
			iripRj45          (42),
			irEthQRj45        (43),
			iripBnc           (44),
			rs530WA           (45),  --rs530/IR that solves a wander problem for SDH network	 
			v35WA             (46),  --v35/IR that solves a wander problem for SDH network
			irEthQBnc         (47),
			v35Db25           (48),  --V.35 with connector DB25
			rj11              (49),  --Used for FXS & FXO 	 
			mtrj              (50),  --optical
			lc                (51),  --optical
			terminalBlock2    (52),
			irEth10s100       (53),  --IR-ETH 10/100
			scsi68            (54),  -- SCSI 68 pins
			sf3				  (55),  -- sf3=single fiber of sc optical  
			fcLH			  (56),  -- fc Long Haul
			none             (255)    	
			}	 
	MAX-ACCESS  read-only
	STATUS current
	DESCRIPTION
	"The connector of the port/interface.
	 other - none of the specified connectors
	 none -  no connector."
	::= { physicalConnectorEntry 2 }

portOptWaveLength OBJECT-TYPE
    SYNTAX  INTEGER {
		notApplicable(1),
		nm850(2),
		nm1300(3),
		nm1300Laser(4),
		nm1550Laser(5),
		nm1300LaserLH(6),
		nm1550LaserLH(7)
	}
    MAX-ACCESS  read-only
    STATUS  current
    DESCRIPTION
     "Wave Length of an Optical interface/port in [nm] and specification if 
      Laser LH,Laser or LED.
      notApplicable - for non-optical ports."
     ::= { physicalConnectorEntry 3 }

portOptMode OBJECT-TYPE
    SYNTAX  INTEGER {
		notApplicable(1),
		singleMode(2),
		multiMode(3)
		
	}
    MAX-ACCESS  read-only
    STATUS  current
    DESCRIPTION
     "Laser Mode of an Optical Laser interface/port.
       notApplicable - for non-Laser ports."
     ::= { physicalConnectorEntry 4 }



prtSupervisory  OBJECT IDENTIFIER ::= { systemPort 2 }


prtSpTable OBJECT-TYPE
      SYNTAX SEQUENCE OF PrtSpEntry
      MAX-ACCESS not-accessible
      STATUS current
	DESCRIPTION  "A table."
	::=  {prtSupervisory 1}

prtSpEntry OBJECT-TYPE
      SYNTAX PrtSpEntry
      MAX-ACCESS not-accessible
      STATUS current
      DESCRIPTION
      "Supervisory port parameter table."
      INDEX {prtSupervisoryIndex }
      ::= { prtSpTable 1}

PrtSpEntry ::=
      SEQUENCE {
      prtSupervisoryIndex       Integer32,
	  prtSupervisoryRate        INTEGER,
	  prtSupervisoryDataBits    INTEGER,
	  prtSupervisoryParity      INTEGER,
	  prtSupervisoryStopBits    INTEGER,
	  prtSupervisoryUsage       INTEGER,
	  prtSupervisoryInterface   INTEGER,
	  prtSupervisoryCTS		    INTEGER,
	  prtSupervisoryDcdDelay    INTEGER,
	  prtSupervisoryDSR		    INTEGER,
	  prtSupervisoryRoutProtocol   INTEGER
      }				  
					  

prtSupervisoryIndex OBJECT-TYPE
      SYNTAX  Integer32
      MAX-ACCESS  read-only
      STATUS  current
      DESCRIPTION
      "The SP port index. 
       The LS byte of the integer is the port index 1..255. 
       The MS byte is different than 0 only if the port belongs to 
       a module. In	that case it is the module number."
      ::= { prtSpEntry 1}

prtSupervisoryRate     OBJECT-TYPE
      SYNTAX  INTEGER
	      {
        auto      (1),
        s300bps   (2),
        s1200bps  (3),
        s2400bps  (4),
        s4800bps  (5),
        s9600bps  (6),
        s19200bps (7),
        s38400bps (8),
        s57600bps (9),
        s115200bps (10)
	      }
      MAX-ACCESS  read-write
      STATUS  current
      DESCRIPTION
      "This attribute indicates the operation rate (speed) of the 
       port.
       auto - automatic rate selection, by the agent."
      ::= { prtSpEntry 2}

prtSupervisoryDataBits OBJECT-TYPE
      SYNTAX  INTEGER
	      {
        dataBits7 (1),
        dataBits8 (2)
	      }
      MAX-ACCESS  read-write
      STATUS  current
      DESCRIPTION
      "This attribute indicates the number of data bits in an async 
       frame"
      ::= { prtSpEntry 3}

prtSupervisoryParity OBJECT-TYPE
      SYNTAX  INTEGER
	      {
        none  (1),
        odd   (2),
        even  (3)
	      }
      MAX-ACCESS  read-write
      STATUS  current
      DESCRIPTION
      "This attribute indicates the parity mode in an async frame"
      ::= { prtSpEntry 4}

prtSupervisoryStopBits OBJECT-TYPE
      SYNTAX  INTEGER
	      {
		notApplicable  (1),
        stopBits1      (2),
        stopBits1dot5  (3),
        stopBits2      (4)
	      }
      MAX-ACCESS  read-only
      STATUS  current
      DESCRIPTION
      "This attribute indicates the parity mode in an async frame."
      ::= { prtSpEntry 5}

prtSupervisoryUsage OBJECT-TYPE
      SYNTAX  INTEGER
	      {
		unknown (1),
		noUse   (2),
		terminal(3),
		nmsSlip (4),
		nmsPpp  (5),
		muxSlip (6),
		muxPpp  (7),
		dialOut (8)
	      }
      MAX-ACCESS  read-write
      STATUS  current
      DESCRIPTION
      "This attribute indicates the usage of the SP port."
      ::= { prtSpEntry 6}

prtSupervisoryInterface OBJECT-TYPE
      SYNTAX  INTEGER
	      {
		  notApplicable(1),
          dce  (2),
          dte  (3)
	      }
      MAX-ACCESS  read-write
      STATUS  current
      DESCRIPTION
      "This attribute indicates the supervisory port interface."
      ::= { prtSpEntry 7}

prtSupervisoryCTS OBJECT-TYPE
      SYNTAX  INTEGER
	      {
          	notApplicable   (1),
          	on            	(2),        --Old value for DCE.
			rts           	(3),        --Old value for DCE 
			dteWait         (4),        --DTE will wait for CTS to become active before transmit date.
			dteIgnore       (5)         --DTE will Ignore CTS signal and will transmit date anyway.
	      }
      MAX-ACCESS  read-write
      STATUS  current
      DESCRIPTION
	  "CTS line state." 
      ::= { prtSpEntry 8}

prtSupervisoryDcdDelay OBJECT-TYPE
      SYNTAX  INTEGER
	      {
          notApplicable (1),
          d0   (2),
          d10  (3),
		  d50  (4),
		  d100 (5),
		  d200 (6),
		  d300 (7)
	      }
      MAX-ACCESS  read-write
      STATUS  current
      DESCRIPTION
	  "DCD delay in msec." 
      ::= { prtSpEntry 9}

prtSupervisoryDSR OBJECT-TYPE
      SYNTAX  INTEGER
	      {
          notApplicable (1),
          on   (2),
          dtr  (3)
	      }
      MAX-ACCESS  read-write
      STATUS  current
      DESCRIPTION
	  "DSR line state." 
      ::= { prtSpEntry 10}

prtSupervisoryRoutProtocol OBJECT-TYPE
      SYNTAX  INTEGER
       {
        notApplicable (1),
  		none          (2),
        proprietary   (3),
        rip2          (4)
       }
      MAX-ACCESS  read-write
      STATUS  current
      DESCRIPTION
      "This attribute indicates the routing protocol of the port.
       notApplicable - for DP."
      ::= { prtSpEntry 11}

--Port Performance Data

prtPerformance  OBJECT IDENTIFIER ::= { systemPort 3 }

prtPerfTable OBJECT-TYPE
	SYNTAX  SEQUENCE OF PrtPerfEntry
	MAX-ACCESS  not-accessible
	STATUS current
	DESCRIPTION
	"This table includes G.826 ports or interfaces."
	::= {prtPerformance 1}

prtPerfEntry OBJECT-TYPE
	SYNTAX  PrtPerfEntry
	MAX-ACCESS  not-accessible
	STATUS current
	DESCRIPTION  "An entry in table."
	INDEX {prtPerfIdx, prtPerfPeriodRef}
	::= { prtPerfTable 1 }

PrtPerfEntry  ::=
	    SEQUENCE {
	prtPerfIdx
	  Integer32,
	prtPerfPeriodRef
	  INTEGER,
	prtPerfElapsedTime
	  Integer32,
	prtPerfUAS
	  Integer32,
	prtPerfES
	  Integer32,
	prtPerfSES
	  Integer32,
	prtPerfBBE
	  Integer32,
	prtPerfBlocksPerSec
	  Integer32,
	prtPerfTimeTag
	  TimeTicks,
	prtPerfSaveAndResetCmd
	  INTEGER
	  }

prtPerfIdx OBJECT-TYPE
	SYNTAX  Integer32 
	MAX-ACCESS  read-only
	STATUS current
	DESCRIPTION
	"This object is an index of the specific port or interface.
	 For a port, the index will be as agreed between agent and 
	 application.
	 For an interface, ifIndex may be used."
	::= { prtPerfEntry 1 }

prtPerfPeriodRef OBJECT-TYPE
	SYNTAX  INTEGER 
	      {
          currentPeriod (1),
          lastPeriod    (2)
	      }
	MAX-ACCESS  read-only
	STATUS  current
	DESCRIPTION
	"This object is an index that specifies which period of time, the next
	 5 objects refer to.
	 currentPeriod - the period since last prtPerfSaveAndResetCmd received or
	           since Start-up (if no prtPerfSaveAndResetCmd was received since
	           Start-up) until now.
	 lastPeriod - the period between last two commands of prtPerfSaveAndResetCmd.
	           - If only one command occured since Start-up: the period between 
	             Start-up and last command.
	           - If no command occured since Start-up: this period will not 
	             actually exist. In this case, he following 5 objects will be 0."
	::= { prtPerfEntry 2 }

prtPerfElapsedTime OBJECT-TYPE
	SYNTAX  Integer32 
	MAX-ACCESS  read-only
	STATUS  current
	DESCRIPTION
	"Elapsed Time in seconds.
	 - for prtPerfPeriodRef=currentPeriod:
	   The period since last prtPerfSaveAndResetCmd received or	since Start-up 
	   (if no prtPerfSaveAndResetCmd was received since	Start-up) until now.
	 - for prtPerfPeriodRef=lastPeriod:
	   The value of prtPerfElapsedTime when last prtPerfSaveAndResetCmd
	   was received."
	::= { prtPerfEntry 3 }

prtPerfUAS OBJECT-TYPE
	SYNTAX  Integer32 
	MAX-ACCESS  read-only
	STATUS  current
	DESCRIPTION
	"Number of Unavailable Seconds for the reference period (prtPerfPeriodRef)."
	::= { prtPerfEntry 4 }

prtPerfES OBJECT-TYPE
	SYNTAX  Integer32 
	MAX-ACCESS  read-only
	STATUS  current
	DESCRIPTION
	"Number of Errored Seconds for the reference period (prtPerfPeriodRef)."
	::= { prtPerfEntry 5 }

prtPerfSES OBJECT-TYPE
	SYNTAX  Integer32 
	MAX-ACCESS  read-only
	STATUS  current
	DESCRIPTION
	"Number of Severely Errored Seconds for the reference period (prtPerfPeriodRef)."
	::= { prtPerfEntry 6 }

prtPerfBBE OBJECT-TYPE
	SYNTAX  Integer32 
	MAX-ACCESS  read-only
	STATUS  current
	DESCRIPTION
	"Number of Background Block (or Frame) Errors for the reference period 
	 (prtPerfPeriodRef)."
	::= { prtPerfEntry 7 }

prtPerfBlocksPerSec OBJECT-TYPE
	SYNTAX  Integer32 
	MAX-ACCESS  read-only
	STATUS  current
	DESCRIPTION
	"Blocks per second (or frames per second) of the port/interface indicated by 
	 portIdx. This object is constant for a certain port/interface.
	 It is not affected by the prtPerfPeriodRef index."
	::= { prtPerfEntry 8 }

prtPerfTimeTag OBJECT-TYPE
	SYNTAX  TimeTicks 
	MAX-ACCESS  read-only
	STATUS  current
	DESCRIPTION
	"Time Tag of Last Period: sysUpTime when last prtPerfSaveAndResetCmd was
	 executed.
	 This object is applicable only for prtPerfPeriodRef=lastPeriod.
	 For prtPerfPeriodRef=currentPeriod, the value will always be 0."
	::= { prtPerfEntry 9 }

prtPerfSaveAndResetCmd OBJECT-TYPE
    SYNTAX   INTEGER
	      {
    		off(2),
	    	on (3)
	      }
    MAX-ACCESS  read-write
    STATUS  current
    DESCRIPTION
    "A command per port/interface, to Save data of Current Period in Last Period
     data-set and start a new counting period for Current Period.
     This object is applicable only for prtPerfPeriodRef=currentPeriod.
     Setting this object to on(3) for prtPerfPeriodRef=last, will cause the agent
     to return: Bad Value response.
     When setting validly this object to on(3), agent will perform the required 
     command and will reset automatically the value of this object to off(2).
     Setting this object to off(2), will do nothing."
    ::= { prtPerfEntry 10 }

--Port Test Data

prtTest OBJECT IDENTIFIER ::= { systemPort 4 }

prtTestTable OBJECT-TYPE
	SYNTAX  SEQUENCE OF PrtTestEntry
	MAX-ACCESS  not-accessible
	STATUS current
	DESCRIPTION
	"This table includes test data for ports or interfaces."
	::= {prtTest 1}

prtTestEntry OBJECT-TYPE
	SYNTAX  PrtTestEntry
	MAX-ACCESS  not-accessible
	STATUS current
	DESCRIPTION  "An entry in table."
	INDEX {prtTestIdx}
	::= { prtTestTable 1 }

PrtTestEntry  ::=
	    SEQUENCE {
     	prtTestIdx
	    Integer32,
    	prtTestCmdAndStatus
        Integer32,
    	prtBertCounter
        Integer32,
		prtTestInitiator
		INTEGER,
		prtTestTimeout
		Integer32
        } 

prtTestIdx OBJECT-TYPE
	SYNTAX  Integer32  
	MAX-ACCESS  read-only
	STATUS current
	DESCRIPTION
	"This object is an index of the specific port or interface.
	 For a port, the index will be as agreed between agent and 
	 application.
	 For an interface, ifIndex may be used."
	::= { prtTestEntry 1 }

prtTestCmdAndStatus OBJECT-TYPE
      SYNTAX  Integer32
      MAX-ACCESS  read-write
      STATUS  current
      DESCRIPTION
      "Setting this object to a value as detailed further on 
       (except 0) will initiate a test on the specific port. 
       The test/s requested will be set according to the respective
       bit. The value of this object will be a sum of (2**n), where n is
       the Bit:
         TEST                  BIT	                     VALUE
        -----------            ---						------
        reserved                0						   1
		PayloadLoop=RLB     	1 (=Remote Loopback)	   2
        LineLoop=DIG            2 (=Digital)			   4
        OtherLoop               3						   8
        InwardLoop=LLB          4 (=Local Loopback)       16
        BERT                    5						  32
        LC                      6                         64
		ToneInjection			7						 128
		Inband 				    8			   			 256

        e.g : If the requested value is 20 -> 010100  ->
              Bits 2 & 4 are set -> the requested tests are :
                                    LineLoopback=DIG
                                    InwardLoopback=LLB
                                      
       Not all tests combinations are valid.
	   For valid test combination, see each product's specification.
	   For LRS52, only single test is allowed simultaneously

       The terminology and order of the first tests (except BERT) 
       is according to the one used for Test Status of DS1 and DS3 standards.
	   The notations : RLB, LLB, DIG are the most used in RAD's products, but they 
	   can be different. For exact definition see product's spec. 

       Setting this object to stop (value=0 ; all bits are 0), 
       will stop all the user requested tests running on the 
       selected port.

       When no test is running on the port, the Get value (test status)
	   will be 0.

	   PayloadLoop=RLB
	     The received signal at this interface is looped
	     through the device.  Typically the received signal
	     is looped back for retransmission after it has
	     passed through the device's framing function.

	   LineLoop=DIG
	     The received signal at this interface does not
	     go through the device (minimum penetration) but
	     is looped back out.

	   OtherLoop
	     Loopbacks that are not defined here.

	   InwardLoop=LLB 
	     The sent signal at this interface is looped back
	     through the device.

	   LC
	     This loop is applicable only for HSSI interface, towards the router .
	   
	   ToneInjection
		 This loop is applicable for analog voice (like FXS)."

   	  ::= { prtTestEntry 2 }

prtBertCounter   OBJECT-TYPE
      SYNTAX  Integer32
      MAX-ACCESS  read-only
      STATUS  current
      DESCRIPTION
      "This object indicates the number of BERT errors encountered
       during the BERT operation.
       It is valid only when BERT (Bit Error Rate Test) is active on the 
       specific port.
       The Counter starts from zero (0) anytime BERT is initiated."
      ::= { prtTestEntry 3}

prtTestInitiator OBJECT-TYPE
    SYNTAX   INTEGER
	      {
    		unknown   (1),
    		user      (2),
	    	remoteUnit(3),
			dteRouter (4)
	      }
    MAX-ACCESS  read-only
    STATUS  current
    DESCRIPTION
    "This object indicates who initiated this port's test/s."
    ::= { prtTestEntry 4 }

prtTestTimeout OBJECT-TYPE
   SYNTAX   Integer32  (0..4095)
   MAX-ACCESS  read-write
   STATUS  current
   DESCRIPTION
   "This object is applicable only when a single 
   test is running. It indicates the test 
   activation timeout in minutes.
   When the timeout expires, the test is stopped.
   Value of 0 indicates test may run Forever "
   ::= { prtTestEntry 5 }

--Port General Parameters

prtParam OBJECT IDENTIFIER ::= { systemPort 5 }

prtParamTable OBJECT-TYPE
	SYNTAX  SEQUENCE OF PrtParamEntry
	MAX-ACCESS  not-accessible
	STATUS current
	DESCRIPTION
	"This table includes general port parameters. The meaning is
	 different for every product that supports it due to a general
     parameter - prtControlCnfg.
	 
	 For ACE2002:
	 This table is used as a mechanism to create the next interface index.
     The algorithm description: 
     The NMS will send the agent the following get command: get(nextIfIndex.index), 
     where index=interface on which the new index is dependent on. 
     Upon this command the agent will generate and return the new index to the NMS."
	::= {prtParam 1}

prtParamEntry OBJECT-TYPE
	SYNTAX  PrtParamEntry
	MAX-ACCESS  not-accessible
	STATUS current
	DESCRIPTION  "An entry in table."
	INDEX {prtParamIdx}
	::= { prtParamTable 1 }

PrtParamEntry  ::=
	    SEQUENCE {
	prtParamIdx
	  Integer32,
	prtControlCnfg
	  Integer32,
    prtParamClkSrc
	  INTEGER,
    prtParamPhantom
	  INTEGER,
    prtParamResetStatsCmd
	  INTEGER,
	prtParamLastResetStatsTime
	  TimeStamp
	}

prtParamIdx OBJECT-TYPE
	SYNTAX  Integer32 
	MAX-ACCESS  read-only
	STATUS current
	DESCRIPTION
	"This object is an index of the specific port or interface.
	 For a port, the index will be as agreed between agent and 
	 application.
	 For an interface, ifIndex may be used.
	 
	 For ACE2002:
	 This parameter is the physical layer ifIndex of the slot on 
     which the NMS requires the next interface index."
	::= { prtParamEntry 1 }

prtControlCnfg OBJECT-TYPE
	SYNTAX  Integer32 
	MAX-ACCESS  read-write
	STATUS current
	DESCRIPTION
	"This object may be used for port RW general parameter/s.
	 For detailed meaning, see product's spec.
	 Supported by: PRBi-E3/T3.
	 
	 For ACE2002:
	 This parameter will include the value of the new index 
	 generated by agent.
	 
	 For Optimux-T3:
	 This parameter will be used for Release Remote LLB Command:
	 on=2= Set value only. Command to release LLB of Remote Unit.
	       Agent will return automatically to 'off' value after performing
	       the command.
	 off=3=Get value only.
	 
	 
	 For LA140
	 This parameter will be used as EchoCanceler per timeslot
	 off = 2 Echo Canceler is disabled
	 on =  3 Echo Canceler is enabled "
	::= { prtParamEntry 2 }

prtParamClkSrc OBJECT-TYPE
    SYNTAX  INTEGER {
       loopTiming    (1),
       localTiming   (2),
       throughTiming (3),
	   adaptive      (4),
	   notApplicable (255)
    }
    MAX-ACCESS  read-write
    STATUS  current
    DESCRIPTION
       "The source of Transmit Clock.
        'loopTiming' or 'loopback' indicates that the recovered receive clock 
         is used as the transmit clock.

        'localTiming' or 'internal' indicates that a local clock
         source is used or when an external clock is
         attached to the box containing the interface.

        'throughTiming' or 'external' indicates that recovered receive clock 
         from another card or interface is used as the transmit clock.
         
        'adaptive' indicates that the clock is recovered according
         to the received data flow rate. "
	::= { prtParamEntry 3 }


prtParamPhantom OBJECT-TYPE
    SYNTAX  INTEGER {
       notApplicable (1),
       disable       (2),
       enable        (3)
	}
	MAX-ACCESS  read-write
	STATUS current
	DESCRIPTION
	"Power feeding to another device."
	::= { prtParamEntry 4 }

prtParamResetStatsCmd OBJECT-TYPE
    SYNTAX  INTEGER {
       off(2),
	   on (3)
	}
    MAX-ACCESS  read-write
    STATUS  current
    DESCRIPTION
    "Reset statistics of the selected port."
    ::= { prtParamEntry 5 }

prtParamLastResetStatsTime OBJECT-TYPE
     SYNTAX  TimeStamp
     MAX-ACCESS  read-only
     STATUS  current
     DESCRIPTION
     "The value of MIB II's sysUpTime object at the last time that 
      prtParamResetStatsCmd was Set to on(3) for this port.  
      If prtParamResetStatsCmd was never Set to on(3) since last 
      re-initialization of the agent, then this object contains a zero value.
      This object enables calculating the running time of Statistics
      counters for this port, by: [sysUpTime-prtParamLastResetStatsTime]."
     ::= { prtParamEntry 6 }


prtIP OBJECT IDENTIFIER ::= { systemPort 6 }

prtIpParamTable OBJECT-TYPE
	SYNTAX  SEQUENCE OF PrtIpParamEntry
	MAX-ACCESS  not-accessible
	STATUS current
	DESCRIPTION  "A table - Parameters for IP Ports."
	::= {prtIP 1}

prtIpParamEntry OBJECT-TYPE
	SYNTAX  PrtIpParamEntry
	MAX-ACCESS  not-accessible
	STATUS current
	DESCRIPTION  "An entry in table."
	INDEX { prtIpParamConfigIdx, prtIpParamSlotIdx, prtIpParamIdx }
	::= { prtIpParamTable 1 }

PrtIpParamEntry  ::=
    SEQUENCE {
    prtIpParamConfigIdx	      Integer32,
    prtIpParamSlotIdx  	      Integer32,
    prtIpParamIdx             Integer32,
	prtIpParamHostIP	      IpAddress,
	prtIpParamHostMask	      IpAddress,
	prtIpParamDefaultGateway  IpAddress,
	prtIpParamMediaMode		  INTEGER,
	prtIpParamMediaRate		  INTEGER,
	prtIpParamMngVlanSupport  INTEGER,
	prtIpParamMngVlanId       Integer32,
	prtIpParamMngVlanPriority Integer32,
	prtIpParamRingMode		  INTEGER
	}

prtIpParamConfigIdx OBJECT-TYPE
	SYNTAX  Integer32 
	MAX-ACCESS  read-only
	STATUS current
	DESCRIPTION 
	"This object indicates the Configuration number (1..255) 
     referred.
     Value of 255 specifies the TmpCnfg (Scratch).
     For products having Agent and Edit configurations, 
     Write operation for the table entries is allowed only to 
     Config=255."
	::= { prtIpParamEntry 1 }

prtIpParamSlotIdx OBJECT-TYPE
    SYNTAX  Integer32   
    MAX-ACCESS  read-only
    STATUS  current
    DESCRIPTION
    "This object indicates a unique number of the slot position 
     in which the module is inserted.
     notApplicable = 255 (for products that don't have slots).
       
     For KM:
     kmxMlA (103),
     kmxMlB (104)."
    ::= { prtIpParamEntry 2 }

prtIpParamIdx OBJECT-TYPE
	SYNTAX  Integer32 
	MAX-ACCESS  read-only
	STATUS current
	DESCRIPTION
	"This object indicates a unique Port Index."
	::= { prtIpParamEntry 3 }

prtIpParamHostIP OBJECT-TYPE
    SYNTAX  IpAddress 
    MAX-ACCESS  read-write
    STATUS  current
    DESCRIPTION
    "The host interface IP address."
    ::= { prtIpParamEntry 4 }

prtIpParamHostMask OBJECT-TYPE
    SYNTAX  IpAddress 
    MAX-ACCESS  read-write
    STATUS  current
    DESCRIPTION
    "The host interface subnet mask."
    ::= { prtIpParamEntry 5 }

prtIpParamDefaultGateway OBJECT-TYPE
    SYNTAX  IpAddress
    MAX-ACCESS  read-write
    STATUS  current
    DESCRIPTION
    "Default Gateway's IP Address."
    ::= { prtIpParamEntry 6 }

prtIpParamMediaMode OBJECT-TYPE
    SYNTAX  INTEGER
	{
       notApplicable (1),
       halfDuplex    (2),
       fullDuplex    (3) 
    }
    MAX-ACCESS  read-only
    STATUS  current
    DESCRIPTION
    "This object indicates the real Media Mode."
    ::= { prtIpParamEntry 7 }

prtIpParamMediaRate OBJECT-TYPE
    SYNTAX  INTEGER
	{
       notApplicable (1),
       r10Mbps       (2),
       r100Mbps      (3) 
    }
    MAX-ACCESS  read-only
    STATUS  current
    DESCRIPTION
    "This object indicates the real Media Rate (Mbps)."
    ::= { prtIpParamEntry 8 }

prtIpParamMngVlanSupport OBJECT-TYPE
    SYNTAX  INTEGER 
    {
    notApplicable(1),
    no		(2),
    yes	    (3)
    }
    MAX-ACCESS  read-write
    STATUS  current
    DESCRIPTION
    "Management VLAN support (Tagging).
     no - No support of VLAN Tagging.
     yes - 4 VLAN bytes will be added to the frame."
    ::= { prtIpParamEntry 9 }

prtIpParamMngVlanId OBJECT-TYPE
     SYNTAX  Integer32 
     MAX-ACCESS  read-write
     STATUS  current
     DESCRIPTION
     "Management VLAN ID."
     ::= { prtIpParamEntry 10 }
  
prtIpParamMngVlanPriority OBJECT-TYPE
     SYNTAX  Integer32 
     MAX-ACCESS  read-write
     STATUS  current
     DESCRIPTION
     "Management VLAN Frame priority."
     ::= { prtIpParamEntry 11 }

prtIpParamRingMode OBJECT-TYPE
    SYNTAX  INTEGER
	{
       notApplicable (1),
       disable       (2),
       enable        (3) 
    }
    MAX-ACCESS  read-write
    STATUS  current
    DESCRIPTION
    "This object indicates If Ring Mode is enabled or not."
    ::= { prtIpParamEntry 12 }


systemResetAllStatsCmd OBJECT-TYPE
      SYNTAX   INTEGER
	      {
    		off(2),
	    	on (3)
	      }
      MAX-ACCESS  read-write
      STATUS  current
      DESCRIPTION
       "Reset statistics of all ports and connections of the device."
      ::= { agnt 16 }

systemClearTablesCmd OBJECT-TYPE
      SYNTAX   INTEGER
	      {
    		off(2),
	    	tempCnfgTables (3)
	      }
      MAX-ACCESS  read-write
      STATUS  current
      DESCRIPTION
       "tempCnfgTables - Set *RowStatus = destroy for all entries of 
                         some tables having *RowStatus object, for 
                         temporary configuration only! (255).
                         For the relevant tables, see product's specification.
                         This object should be used by WAN product applications 
                         before performing the Update operation, in order to clear 
                         old entries of these tables. 
        off - agent will automatically change to this value, after performing the 
              command. "
      ::= { agnt 17 }

systemParameter OBJECT-TYPE
      SYNTAX   Integer32
      MAX-ACCESS  read-write
      STATUS  current
      DESCRIPTION
       "This parameter can be used for different purposes: 
        - TELNET session time-out in seconds.
	   	- Ace20: when trying to create row in a table that already
				 has row with the same values, if set of values has to be unique
				 in table, this attribute is set to the index of the existing row.
		- Optimux-T3: when CH interfaces are RJ-45, user can select via this
		         object, the interface type for each Group of channels: T1 or E1:
		         The selection will be a sum of the following Bits.
		         '0' = T1
		         '1' = E1
		         Bit    Group               Value for each Bit having '1'
				  1		  1 (CH-1..CH-8)        	  1
				  2		  2 (CH-9..CH-12)       	  2
				  3		  3 (CH-13..CH-20)	          4
				  4		  4 (CH-21..CH-28)	          8
				 Examples:
				 15 = all Groups are selected to be E1
				  6 = Group 2 and Group 3 are selected to be E1 
				     (Group 1 and Group 4 are T1).
		- FCD-A, FCD-M: user can select via this object the configuration
		         used for Get values of MSDSL parameters that don't have
		         configuration index.
		         1  =active configuration
		         255=temporary configuration.
		         Set of this object should be done before Getting the MSDSL 
		         RW parameters.
		- Ace2002: This parameter indicates the number of intervals that
		         were successfully uploaded upon statistics collection session.
		        
		- FCD-IP, WR, FCD-IPD, LA-240:
		         This parameter indicates whether Telnet Access is enabled/disabled:
		         Values:
				 2 - Telnet Access is Disabled.
				 3 - Telnet Access is Enabled.
				 
		- Vmux-110: This parameter value equals maximum number of bundles."
       ::= { agnt 18 }

 
agnGlobalAlarmMask OBJECT-TYPE   
      SYNTAX OCTET STRING 
      MAX-ACCESS  read-write    
      STATUS  current
      DESCRIPTION
      "The value of this attribute determines the alarm traps the 
       agent should mask and not send to the managers.
       Each bit from a certain octet represents a certain alarm."
      ::= { agnt 19 }

alarmSeverity   OBJECT-TYPE
      	SYNTAX   INTEGER
	      	{
			event		(3),
			minor		(4),
			major		(5),
	    	warning		(6),
			critical	(7)
	  		}
      	MAX-ACCESS  read-only
      	STATUS  current
      	DESCRIPTION
       	"This object specifies the severity of the alarms."
      ::= { agnt 20 }

alarmState   OBJECT-TYPE
      	SYNTAX   INTEGER
	      	{
			off (2), 	-- End, 
			on  (3) 	-- Start.
	  		}
      	MAX-ACCESS  read-only
      	STATUS  current
      	DESCRIPTION
       "."
      ::= { agnt 21 }


agnTestStatus OBJECT-TYPE
	SYNTAX	INTEGER
		{
		 off			(2),
		 on 			(3)
		}

	MAX-ACCESS	read-only
	STATUS	current
	DESCRIPTION
	"Indicates the current test status (for all levels: system,
	   card, port).
       This attribute will be set to: 
         on(3): when there is at least one test	in progress on the
                system/card/port
		 off(2): when there is NO test in progress on the
    	         system/card/port" 
      ::= {agnt 22  }

systemSaveAndResetAllStatsCmd OBJECT-TYPE
      SYNTAX   INTEGER
	      {
    		off(2),
	    	on (3)
	      }
    MAX-ACCESS  read-write
    STATUS  current
    DESCRIPTION
    "on  - a command to Save data of Current Period in Last Period
           data-set and start a new counting period for Current Period.
     off - agent will automatically change to this value, after performing the 
           command."
      ::= { agnt 23 }

systemDefaultGateway OBJECT-TYPE
      SYNTAX   IpAddress
    MAX-ACCESS  read-write
    STATUS  current
    DESCRIPTION
    "Default Gateway's IP Address."
      ::= { agnt 24 }

-- PS Table
systemPsTable OBJECT-TYPE
	SYNTAX  SEQUENCE OF SystemPsEntry
	MAX-ACCESS  not-accessible
	STATUS current
	DESCRIPTION
	"This table describes the PS types of a device.
	Usage of this table is specified in the device's NMS SRS"
	::= { agnt 25 }

systemPsEntry OBJECT-TYPE
	SYNTAX  SystemPsEntry
	MAX-ACCESS  not-accessible
	STATUS current
	DESCRIPTION  "An entry in table."
	INDEX {systemPsIndex1, systemPsIndex2}
	::= { systemPsTable 1 }

SystemPsEntry  ::=
	    SEQUENCE {
	systemPsIndex1
	  Integer32,
	systemPsIndex2
	  Integer32,
	systemPsType
	  INTEGER,
	systemPsStatus
	  INTEGER,
	systemPsHotSwap
	  INTEGER
	}

systemPsIndex1 OBJECT-TYPE
	SYNTAX  Integer32 
	MAX-ACCESS  read-only
	STATUS current
	DESCRIPTION
	"First Index. 
	In HUBs:
	1 = PS-A slot
	2 = PS-B slot.
	In SA units:
	1 = PS1
	2 = PS2
	Default = 1"
	::= { systemPsEntry 1 }

systemPsIndex2 OBJECT-TYPE
	SYNTAX  Integer32 
	MAX-ACCESS  read-only
	STATUS current
	DESCRIPTION
	"Second Index. 
	In HUBs:
	1 always.
    In SA units:
	1 = Local
	2 = Remote
	Default = 1."
	::= { systemPsEntry 2 }

systemPsType OBJECT-TYPE
      SYNTAX  INTEGER
	      {
		  none       (1),
	      ac         (2),
	      dc         (3),
		  acDc       (4),
		  acPF       (5),
		  dcPF       (6)		  
	      }
      MAX-ACCESS  read-only
      STATUS  current
      DESCRIPTION
      "The type of PS, for a stand-alone product.
      acDc - AC with rj45 DC.
      acPF - Power Feeding (phantom) box that is feeding another box by external AC.
      dcPF - Power Feeding (phantom) box that is feeding another box by external DC."
      ::= { systemPsEntry 3 }

systemPsStatus OBJECT-TYPE
      SYNTAX  INTEGER
	      {
		  notApplicable  (1),
	      failed         (2),
	      ok             (3)
	      }
      MAX-ACCESS  read-only
      STATUS  current
      DESCRIPTION
      "The Status of the PS unit."
      ::= { systemPsEntry 4 }

systemPsHotSwap	OBJECT-TYPE
      SYNTAX  INTEGER
	      {
		  notApplicable  (1),
	      fixed          (2),
	      hotSwap        (3)
	      }
      MAX-ACCESS  read-only
      STATUS  current
      DESCRIPTION
      "Is PS unit hot swap or fixed."
      ::= { systemPsEntry 5 }

agnFans OBJECT-TYPE
	SYNTAX  OCTET STRING
	MAX-ACCESS  read-only
	STATUS current
	DESCRIPTION
	"This entry specifies the FANs existence and status. 
	 Each fan will be represented by 2 bits,
	 where the first bit (right) will specify the existence:
	 (0= Not exist, 1=exist),
     and the left bit will specify it's status
     (0= OK, 1=FAIL), so for each fan:
     00 - FAN does not exist
     01 - FAN exists and OK
     11 - FAN exists and is Failed 
	 bits 0-1 are for first fan
	 bits 2-3 are for 2nd fan (if exists)."
     ::= { agnt 26 }

agnSendTrapParameter OBJECT-TYPE
	SYNTAX  Integer32
	MAX-ACCESS  read-write
	STATUS current
	DESCRIPTION
	"This object specifies if the agent will attach a specific
	parameter to a trap.
	
	For ACE2002 the agent will attach or not the openViewSeverity 
	parameter according to the value of this parameter:
	1 - will attach openViewSeverity.
	0 - will not attach openViewSeverity."
     ::= { agnt 27 }

--agnt 28-29 are reserved

xcIndexNext  OBJECT-TYPE
          SYNTAX         Integer32 (0..2147483647)
          MAX-ACCESS         read-only
          STATUS         current
          DESCRIPTION
           "This object contains an appropriate value to
            be used for xcIndex when creating
            entries in the xcTable.  The value
            0 indicates that no unassigned entries are
            available. To obtain the xcIndex
            value for a new entry, the manager issues a
            management protocol retrieval operation to obtain
            the current value of this object.  After each
            retrieval, the agent should modify the value to
            the next unassigned index.
            After a manager retrieves a value the agent will
            determine through its local policy when this index
            value will be made available for reuse."
          ::= { agnt 30 }

--XC Table
xcTable OBJECT-TYPE
      SYNTAX SEQUENCE OF XcEntry
      MAX-ACCESS not-accessible
      STATUS current
      DESCRIPTION
      "Configuration of system cross-connect entries.
      The table follows the behavior described in RFC 2515, 
      RFC 1604 regarding the creation deletion and modification 
      of an entry within the table."
      ::= { agnt 31 }

xcEntry OBJECT-TYPE
      SYNTAX XcEntry
      MAX-ACCESS not-accessible
      STATUS current
	DESCRIPTION  "An entry in table."
	INDEX { xcIndex, xcIfIndex1, xcVpi, xcVci, xcIfIndex2 }
      ::= { xcTable 1}

XcEntry ::=
      SEQUENCE {
	 xcIndex        Integer32,
     xcIfIndex1   	Integer32,
     xcVpi 	        Integer32,
     xcVci 	        Integer32,
     xcIfIndex2   	Integer32,
	 xcRowStatus    RowStatus,
	 xcDescr        DisplayString,
     xcAdminStatus  INTEGER,
     xcOperStatus   INTEGER
      }

xcIndex OBJECT-TYPE
      SYNTAX  Integer32
      MAX-ACCESS  not-accessible
      STATUS  current
      DESCRIPTION
      "Cross Connect Identifier."
      ::= { xcEntry 1 }

xcIfIndex1 OBJECT-TYPE
      SYNTAX  Integer32
      MAX-ACCESS  not-accessible
      STATUS  current
      DESCRIPTION
      "The interface Index from the ifTable, which identify one side 
      of the connection."
      ::= { xcEntry 2 }

xcVpi OBJECT-TYPE
      SYNTAX  Integer32 
      MAX-ACCESS  read-create
      STATUS  current
      DESCRIPTION
      "The VPI of the ATM End-Point."
      ::= { xcEntry 3 }

xcVci OBJECT-TYPE
      SYNTAX  Integer32 
      MAX-ACCESS  read-create
      STATUS  current
      DESCRIPTION
      "The VCI of the ATM End-Point."
      ::= { xcEntry 4 }

xcIfIndex2 OBJECT-TYPE
      SYNTAX  Integer32
      MAX-ACCESS  read-create
      STATUS  current
      DESCRIPTION
      "The interface Index from the ifTable, which identifies the other 
      side of the connection."
      ::= { xcEntry 5 }

xcRowStatus  OBJECT-TYPE
      SYNTAX  RowStatus
     MAX-ACCESS   read-create
     STATUS   current
     DESCRIPTION
     "This parameter allows NMS to create/delete entries of this table."
     ::= { xcEntry 6 }

xcDescr  OBJECT-TYPE
     SYNTAX  DisplayString
     MAX-ACCESS   read-create
     STATUS   current
     DESCRIPTION
     "A textual string containing information about the
      xc entry."
     ::= { xcEntry 7 }


xcAdminStatus OBJECT-TYPE
        SYNTAX   INTEGER {
           up(1),
           down(2)
            }
      MAX-ACCESS  read-create
      STATUS  current
      DESCRIPTION
                 "The desired administrative status of this
            bi-directional cross-connect."
      ::= { xcEntry 8 }

xcOperStatus OBJECT-TYPE
        SYNTAX   INTEGER {
           up(1),
           down(2),
           unknown(3)
           }
      MAX-ACCESS  read-only
      STATUS  current
      DESCRIPTION
      "The operational status of this bi-directional 
      cross-connect."
      ::= { xcEntry 9 }

systemModule  OBJECT IDENTIFIER ::= { agnt 32 }


modlParam  OBJECT IDENTIFIER ::= { systemModule 1 }

modlParamTable OBJECT-TYPE
      SYNTAX SEQUENCE OF ModlParamEntry
      MAX-ACCESS not-accessible
      STATUS current
      DESCRIPTION
      "This table include parameters for system modules."
      ::= { modlParam 1 }

modlParamEntry OBJECT-TYPE
      SYNTAX ModlParamEntry
      MAX-ACCESS not-accessible
      STATUS current
	DESCRIPTION  "An entry in table."
	INDEX { modlParamIndex }
      ::= { modlParamTable 1}

ModlParamEntry ::=
      SEQUENCE {
	 modlParamIndex        Integer32,
     modlParamReset 	    INTEGER,
     modlParamSwdlStatus	INTEGER,
	 modlParamLeds          OCTET STRING
      }

modlParamIndex OBJECT-TYPE
      SYNTAX  Integer32
      MAX-ACCESS  read-only
      STATUS  current
      DESCRIPTION
      "The module index.
       The index can be the slot number or any other module index as described
       in the specifications of the device.
       For Vmux-2100 device, the index will have values of: 1..4 for slots 1..4."
      ::= { modlParamEntry 1 }

modlParamReset  OBJECT-TYPE
	SYNTAX  INTEGER	{
	                 off         (2),
					 on          (3),
					 factory	 (4) 			 
				    }
	MAX-ACCESS  read-write
	STATUS  current
	DESCRIPTION
	"Reset action to be performed on the module. 
	 Set the parameter will be done always to on(3) or factory (4). 
	 After performing the Reset operation, Agent will automatically set the parameter to off(2)."
	::= { modlParamEntry 2 }
		   
modlParamSwdlStatus  OBJECT-TYPE
    SYNTAX  INTEGER	{
	notApplicable	(1),
	off         	(2),
	inProcess   	(3) 
		    }
    MAX-ACCESS  read-only
    STATUS  current
    DESCRIPTION
      "This parameter indicates whatever the swdl is in process or not."
    ::= {modlParamEntry 3}

modlParamLeds  OBJECT-TYPE
	SYNTAX  OCTET STRING
	MAX-ACCESS  read-only
	STATUS current
	DESCRIPTION
	"This entry specifies the LEDs status of the module.
	 Each led is represented by 4 bits where the first 2 bits (left) specify  the status :
	 (00=NA, 01=OFF, 10=ON, 11=BLINK),
     and the next two bits (right) specify the color :
     (00=GREEN, 01=RED, 10=YELLOW, 11=GRAY).
     The order of the LEDS is from top to bottom, left to right:
     For each row starting from the top, the LEDS are returned from left to right."
     ::= {modlParamEntry 4}

agnNearFarConnection OBJECT-TYPE   
      SYNTAX  INTEGER {
		 notApplicable	(1),
		 disconnected  	(2), 
		 connected 		(3)
		 		}
      MAX-ACCESS  read-only
      STATUS  current
      DESCRIPTION
      "This parameter describes the connection between near-end and far-end agents."   
      ::= { agnt 33 }


agnAccess OBJECT IDENTIFIER ::= {agnt 34} 

agnTelnetAccess OBJECT-TYPE
	SYNTAX  INTEGER
	{
	 disable       (2),
	 enable        (3),
	 managersOnly  (4)
	 }
	MAX-ACCESS  read-write
	STATUS current
	DESCRIPTION
	"Enable/Disable accessing the device via Telnet.
	
	 disable - no one will be allowed to access the device via Telnet.
	 enable - all users are allowed Telnet Access.
	 managersOnly - Only manager stations listed in the manager's list are allowed."
     ::= { agnAccess 1 }


--TRAPS

--NOTIFICATIONS

systemsEvents OBJECT-IDENTITY
     STATUS  current
     DESCRIPTION
     "The events for RAD products."
     ::= { systems 0 }

tftpStatusChangeTrap  NOTIFICATION-TYPE
     OBJECTS       { tftpStatus }
     STATUS current
     DESCRIPTION     
     "This trap is sent whenever the status of tftp changed."
     ::= { systemsEvents 1 }

agnStatusChangeTrap  NOTIFICATION-TYPE
	OBJECTS		{agnIndication }
    STATUS current
	DESCRIPTION
	"This trap is sent whenever the state of the entity the agent is
	 responsible for changed.
	 TDM devices will send agnTestStatus variable to indicate the current test status."
	::= { systemsEvents 2 }

prtStatusChangeTrap  NOTIFICATION-TYPE
    STATUS current
	DESCRIPTION
	"This trap is sent whenever the state of a port changed.
	 Attached, will be parameter/s that indicate the new port status.
	 The attached variables will be specified in the specifications
	 of the products supporting this trap."
	::= { systemsEvents 3 }

swdlStatusResult	    NOTIFICATION-TYPE
	OBJECTS			{swdlStatusFileName}
    STATUS  current
	DESCRIPTION
	"This notification is sent when Software Down Load is finished.
	 The attached object indicates the File Name."
	::= { systemsEvents 4 }

intSwdlSlotFileMismatch	    NOTIFICATION-TYPE
	OBJECTS			{intSwdlFileName}
    STATUS  current
	DESCRIPTION
	"This notification is sent when the card in the chosen slot doesn't match 
	 the chosen file.
	 The attached object indicates the File Name."
	::= { systemsEvents 5 }

agnCounterChange  NOTIFICATION-TYPE
    STATUS  current
	DESCRIPTION
	"This notification is sent when the value of a specific Counter is changed.
	 Agent can send as attached object the updated Counter.
	 For details about this Counter and attached object, see spec of the relevant
	 application."
	::= { systemsEvents 6 }

prtClkSrcChangeTrap NOTIFICATION-TYPE
      STATUS  current
      DESCRIPTION
	  "This trap is sent upon any port clock change."
    ::= { systemsEvents 7 }

moduleFailTrap NOTIFICATION-TYPE
      STATUS  current
      DESCRIPTION
	  "This trap is sent upon a module failure."
    ::= { systemsEvents 8 }
	
moduleInitFailTrap NOTIFICATION-TYPE
    STATUS current
      DESCRIPTION
	  "This trap is sent upon a module initialization failure."
	::= { systemsEvents 9 }

clkSrcChangeTrap NOTIFICATION-TYPE
      STATUS  current
      DESCRIPTION
	  "This trap is sent upon any change in Clock Source."
    ::= { systemsEvents 10 }

agnUploadDataTrap  NOTIFICATION-TYPE
     STATUS current
     DESCRIPTION     
     "This trap is sent upon an upload data session termination.
     For more details see product specification."
     ::= { systemsEvents 11 }

enrollmentTrap  NOTIFICATION-TYPE
     STATUS current
     DESCRIPTION     
     "This trap is a periodic trap, which is sent to manager 
      until Agent gets any response (Get or Set) from this manager."
     ::= { systemsEvents 12 }

agnPowerFailureTrap  NOTIFICATION-TYPE
     STATUS current
     DESCRIPTION     
     "This trap is sent upon power failure. It is applicable for 
     devices having one PS unit, which sense in advance the failure,
     and still have time to send this trap before it goes off."
     ::= { systemsEvents 13 }
-- 
-- file :v:\doc\rdv\mib\Before~1\trgen.txt
-- 
--Version:  4.0
--Date:   16.10.94		
--By:        Orly Nicklass
--File:       TRGEN.TXT
--Last update: 05.12.95

trGen  OBJECT IDENTIFIER ::= {radTokenRing 1}

--

agnRR OBJECT IDENTIFIER ::= {trGen 1} --agent RAD ring general information

ringTR OBJECT IDENTIFIER ::= { trGen 2 } --ring general information

segTR OBJECT IDENTIFIER ::= { trGen 3} --  segment  general information

moduleTR OBJECT IDENTIFIER ::= {trGen 4}  --  Module general information

prtTR OBJECT IDENTIFIER ::= {trGen  5 } --port general information

--
-- RADRing agent  specific information
--

agnRRcoprocHwVersion OBJECT-TYPE
      SYNTAX  DisplayString
      MAX-ACCESS  read-write
      STATUS  current
      DESCRIPTION
      "ASCII string for description and display of the CML\IB hardware
       version. If the entry is not applicable, it will display the string -NOT APPLICABLE-"
      ::= { agnRR 1 }

agnRRrecMode OBJECT-TYPE
           SYNTAX  INTEGER {
         	unknown(1),
                slow(2),
                fast(3),
                notSupported(4)
                   }
           MAX-ACCESS  read-write
           STATUS  current
           DESCRIPTION
           "The manager station can assist the agent in the autorecovery
            process by setting this value to  SLOW(1). This value indicates
            the presence of old modules within the radring hub. Autorecovery 
            process will be faster for new modules. However it might fail
            if set to FAST(2) and old modules are inserted."
           ::= { agnRR 2 }

agnRRmaskIBMalrt OBJECT-TYPE
           SYNTAX  INTEGER {
                unknown(1),
                disabled(2),
                enabled(3)
                   }
           MAX-ACCESS  read-write
           STATUS  current
           DESCRIPTION
          "When this object is set to the value of Enabled(3),
           Agent-traps that are not masked will also be sent to the IBM LAN manager 
           using IBM's Alert Transport Service Protocol.
           This object is applicable only for TR agents."
      ::= { agnRR 3}

agnRRResetConfig OBJECT-TYPE
           SYNTAX  INTEGER {
                off(2),
                on(3),
                notSupported(4)
                   }
           MAX-ACCESS  read-write
           STATUS  current
           DESCRIPTION
          "Setting the value to ON(3)is interpreted as a reset command
           for the agent NV Ram. When reset process is ended, a trap
           will be issued. If the entry is not applicable, The value notSupported will be read."
           ::= { agnRR 4 }

agnRRSwReset OBJECT-TYPE
           SYNTAX  INTEGER {
                off(2),
                on(3)
                   }
           MAX-ACCESS  read-write
           STATUS  deprecated
           DESCRIPTION
          "Setting the value to ON(3)is interpreted as a  software reset command
           for the agent. When reset process is ended, a trap  will be issued. "
           ::= { agnRR 5 }

agnRRRingReportMngr OBJECT-TYPE
           SYNTAX  INTEGER {
                off(2),
                on(3)
                   }
           MAX-ACCESS  read-write
           STATUS  deprecated
           DESCRIPTION
          "Setting the value to ON(3) is interpreted as assigning the duty of  Ring Report 
	Manager on  the agent "
           ::= { agnRR 6 }

agnRRSubSysCommState  OBJECT-TYPE
           SYNTAX  INTEGER {
                failed(2),
                ok(3),
                 notSupported(4)
                   }
           MAX-ACCESS  read-only
           STATUS  current
           DESCRIPTION
          "This attribute indicates the status of communication between the two agent's
	processors.  The communication is failed when the CML/NM card is removed"
           ::= { agnRR  7 }

--
-- Ring information for the ring the agent is connected to. It is traffic information and
-- isolated error information.
--	       

ringResetStatistics OBJECT-TYPE   
      SYNTAX  INTEGER {  
           unknown(1),
           off(2), 
           on(3)
      }
      MAX-ACCESS  read-write    
      STATUS  current
      DESCRIPTION
      "Setting the value of this attribute to ON(3) resets all the inband
      statistics and error counters." 
           ::= { ringTR 1 }

ringCurrentTraffic OBJECT-TYPE 
      SYNTAX  Integer32	  
      MAX-ACCESS  read-only
      STATUS  current
      DESCRIPTION
      "Momentary traffic for the last time interval. The traffic is expressed in
      percents of the maximum Tokenring traffic ."
      ::= { ringTR 2 }

ringPeakTraffic OBJECT-TYPE 
      SYNTAX  Integer32   
      MAX-ACCESS  read-only
      STATUS  current
      DESCRIPTION
      "Maximal traffic value since last reset of Agent or statistics.
      Expressed in percents of the maximum Tokenring traffic."
      ::= { ringTR 3 }

ringTrafficTreshold OBJECT-TYPE 
      SYNTAX  Integer32		    
      MAX-ACCESS  read-write
      STATUS  current
      DESCRIPTION
      "Traffic threshold value. When reached, a trap will be sent to the management
      console. Expressed in percents of the maximum Tokenring traffic"
      ::= { ringTR 4 }

ringLineErrCnt OBJECT-TYPE
      SYNTAX  Counter32
      MAX-ACCESS  read-only
      STATUS  current
      DESCRIPTION
       "This counter is incremented when a frame
       or token is copied or repeated by any of the
       stations on the ring, the E bit is zero in the frame
       or token and one of the following
       conditions exists: 1) there is a
       non-data bit (J or K bit) between the SD
       and the ED of the frame or token, or
       2) there is an FCS error in the frame."
      ::= { ringTR 5 }

ringLineErr OBJECT-TYPE
      SYNTAX  Integer32
      MAX-ACCESS  read-only
      STATUS  current
      DESCRIPTION
       "This counter is incremented when a frame
       or token is copied or repeated by any of the
       stations on the ring, the E bit is zero in the frame
       or token and one of the following
       conditions exists: 1) there is a
       non-data bit (J or K bit) between the SD
       and the ED of the frame or token, or
       2) there is an FCS error in the frame."
      ::= { ringTR 6 }

ringBurstErrCnt OBJECT-TYPE
      SYNTAX  Counter32
      MAX-ACCESS  read-only
      STATUS  current
      DESCRIPTION
      "This counter is incremented when any of the stations
       on the ring detects the absence of transitions for five
       half-bit timers (burst-five error)."
      ::= { ringTR 7 }

ringBurstErr OBJECT-TYPE
      SYNTAX  Integer32
      MAX-ACCESS  read-only
      STATUS  current
      DESCRIPTION
      "This counter is incremented when any of the stations
       on the ring detects the absence of transitions for five
       half-bit timers (burst-five error)."
      ::= { ringTR 8 }

ringACFCErrCnt  OBJECT-TYPE
      SYNTAX  Counter32
      MAX-ACCESS  read-only
      STATUS  current
      DESCRIPTION
     "This counter is incremented when any of the stations
     on the ring receives an AMP or SMP frame in which A is
     equal to C is equal to 0, and then receives
     another SMP frame with A is equal to C is
     equal to 0 without first receiving an AMP
     frame. It denotes a station that cannot set
     the AC bits properly."
      ::= { ringTR 9 }


ringACFCErr OBJECT-TYPE
      SYNTAX  Integer32
      MAX-ACCESS  read-only
      STATUS  current
      DESCRIPTION
     "This counter is incremented when any of the stations
     on the ring receives an AMP or SMP frame in which A is
     equal to C is equal to 0, and then receives
     another SMP frame with A is equal to C is
     equal to 0 without first receiving an AMP
     frame. It denotes a station that cannot set
     the AC bits properly."
      ::= { ringTR 10 }


ringTotErrCnt OBJECT-TYPE
      SYNTAX  Counter32
      MAX-ACCESS  read-only
      STATUS  current
      DESCRIPTION
      "The total of the above described errors"
      ::= { ringTR 11 }

ringTotErr OBJECT-TYPE
      SYNTAX  Integer32
      MAX-ACCESS  read-only
      STATUS  current
      DESCRIPTION
      "The total of the above described errors"
      ::= { ringTR 12 }

ringTotErrThreshold OBJECT-TYPE
 SYNTAX  Integer32
      MAX-ACCESS  read-write
      STATUS  current
      DESCRIPTION
      "The threshold value of the total of the above described errors.When the threshold is reached 
        a trap indicating the status of the ring (SOFT ERROR)will be sent to the management station"
      ::= { ringTR 13}

ringStatus OBJECT-TYPE 
      SYNTAX  INTEGER {
        unknown(1),
        normal(2),
        softError(3),
        beacon(4)
	 }   
      MAX-ACCESS  read-only
      STATUS  current
      DESCRIPTION
      "Describes the status of the LAN segment the agent is attached to:
      Normal(2) - The LAN segment is operating normally
      SoftError(3) - The Token ring LAN segment (ring) is experiencing 
                      intermittent failures that temporarily harm the 
                      ring's performance and cause data to be transmitted
                      more than ones.
      Beaconing(4) - The ring is not operative; no data is transmitted."
      ::= { ringTR 14 }

ringConfigMsg OBJECT-TYPE   
      SYNTAX  OCTET STRING
      MAX-ACCESS  read-only
      STATUS  current
      DESCRIPTION
      "Full configuration message  coded in internal RAD application format.
      This entry describes ring information. "
      ::= { ringTR 15 }

ringCurrentTrafficCnt OBJECT-TYPE 
      SYNTAX   Counter32
      MAX-ACCESS  read-only
      STATUS  current
      DESCRIPTION
      "Momentary traffic for the last time interval. The traffic is expressed as bits per second."
      ::= { ringTR 16 }

--
-- Segments 
--
segTRTable OBJECT-TYPE
               SYNTAX SEQUENCE OF SegTREntry
               MAX-ACCESS not-accessible
               STATUS current
			   DESCRIPTION
			   "Segments."
               ::= { segTR 1}

segTREntry OBJECT-TYPE
               SYNTAX SegTREntry
               MAX-ACCESS not-accessible
               STATUS current
			   DESCRIPTION
			   "An entry in table segTRTable."
               INDEX { segTRID}
               ::= { segTRTable 1}
   
SegTREntry ::= 
            SEQUENCE {
               segTRID
                  Integer32,
               segTRLastSlot
                  Integer32,
               segTRFirstSlot
                  Integer32,
               segTRStatus
                  INTEGER
                 }

segTRID OBJECT-TYPE
           SYNTAX  Integer32  (1..20) 
           MAX-ACCESS  read-only
           STATUS  current
           DESCRIPTION
           "Segment unique identification number (internal). It is  
	        the extreme left slot, marking the beginning of the 
	        segment."
           ::= {  segTREntry 1 }

segTRLastSlot OBJECT-TYPE  
           SYNTAX  Integer32   
           MAX-ACCESS  read-only
           STATUS  current
           DESCRIPTION
           "Location of the right most slot marking the end of the 
            segment. In the RADring hub it is slot number 20 or the slot 
            where end of segment module is inserted or the slot before
            a beginning of a new segment. ( End of segment 
            module could be one with termination on or TIO, TFR, TCR etc.)"
           ::= {  segTREntry 2 }

segTRFirstSlot OBJECT-TYPE
           SYNTAX  Integer32     
           MAX-ACCESS  read-only
           STATUS  current
           DESCRIPTION
           "Location of the left most slot marking the beginning
           of the segment. In the RADring hub it is slot number 1 or 
           the slot number following the end of segment module, or where
           a repeater or TIO is inserted."
           ::= {  segTREntry 3 }

segTRStatus OBJECT-TYPE 
      SYNTAX  INTEGER {
        unknown(1),
        beaconing(2),
        normal(3)
	 }   
      MAX-ACCESS  read-only
      STATUS  current
      DESCRIPTION
      "Describes the status of the segment :
      Normal(3) - The segment is operating normally
      Beaconing(2) - The ring is not operative; no data is transmitted.
      Segment without inband module within its limit will display Unknown(1).
       This entry is specially usefull when the hub is configured with multiple segments
        and each segment is part of another net"
      ::= { segTREntry 4 }


--
-- Modules parameters structure
-- contains general information about the modules 
--

mdlTRTable  OBJECT-TYPE
      SYNTAX SEQUENCE OF MdlTREntry
      MAX-ACCESS not-accessible
      STATUS current
	  DESCRIPTION
	  "Modules parameters structure
	   contains general information about the modules."
      ::= { moduleTR 1 }

mdlTREntry OBJECT-TYPE
      SYNTAX    MdlTREntry
      MAX-ACCESS    not-accessible
      STATUS    current
	  DESCRIPTION
	  "An entry in table mdlTRTable."
      INDEX     { mdlTRID  }
      ::= { mdlTRTable 1 }
 
MdlTREntry ::=
      SEQUENCE {
          mdlTRID
              Integer32,
          mdlTRSegID
              Integer32,
          mdlTRType 
              INTEGER,
          mdlTRHwVer
              DisplayString,
          mdlTRSwVer 
             DisplayString,
          mdlTRTotalNoOfPrt 
             Integer32,
         mdlTRSpecific
             OBJECT IDENTIFIER
          }

mdlTRID  OBJECT-TYPE
      SYNTAX  Integer32 
      MAX-ACCESS  read-only
      STATUS  current
      DESCRIPTION
      "The slot number where the module is inserted. Can not be greater
       than chNoSlot"  
      ::= { mdlTREntry 1 }        

mdlTRSegID  OBJECT-TYPE
      SYNTAX  Integer32 
      MAX-ACCESS  read-only
      STATUS  current
      DESCRIPTION
      "The segment number where the module belongs to. One of the 
       segTRID values."  
      ::= {mdlTREntry 2 }        

mdlTRType OBJECT-TYPE
      SYNTAX  INTEGER {
            unknown(1),
            empty(2),
            tl4s(3),
            tl4su(4),
            tl4sd(5),
            tl4cx(6), 
            tl4u(7),
            tl2edu(8), 
            tl2eds(9),
            tl2edsu(10),
            tl2f(11),   
            tja(12),      
            tio(13),
            tfr(14),
            tfc1(15),
            tfc2(16),
            tcr(17),
            tl4au(18),
            tl4as(19),
            tl4asd(20),
            tl4asu(21),
            tre1d(22),
            tre(23),
            tre8d(24),
            stc1(25),
            stc2(26),
            ftc(27),
            cmlib(28),
            tl2fsat(29),
            nonTR(30),
            tau(31),	-- for all TAUs type
            rmu(32)	-- for all RMUs type
      }
      MAX-ACCESS  read-only
      STATUS  deprecated
      DESCRIPTION
      "Indicates the type of the module connected at the specified slot number."
      ::= { mdlTREntry 3 }

mdlTRHwVer OBJECT-TYPE
      SYNTAX  DisplayString
      MAX-ACCESS  read-write
      STATUS  current
      DESCRIPTION
      "ASCII string for description and display of the module's hardware version,
      as it is known by the module's software. A manager can record his own 
      hardware upgrade."
      ::= { mdlTREntry 4 }

mdlTRSwVer OBJECT-TYPE
      SYNTAX  DisplayString
      MAX-ACCESS  read-only
      STATUS  current
      DESCRIPTION
      "ASCII string for description and display of the module's 
       software version. A value of NOT APPLICABLE will be recorded
       for module having no independent processor."
      ::= { mdlTREntry  5 }

mdlTRTotalNoOfPrt OBJECT-TYPE
      SYNTAX  Integer32 
      MAX-ACCESS  read-only
      STATUS  current
      DESCRIPTION
      "This entry describes the number of possible ports/lobes/links
        connection in the module (not all ports hardware should be active) ." 
      ::= { mdlTREntry 6 }


mdlTRSpecific OBJECT-TYPE
      SYNTAX  OBJECT IDENTIFIER
      MAX-ACCESS  read-only
      STATUS  current
      DESCRIPTION
      " Object identifier of entity containing additional information 
      regarding this instance. This entry is type specific."
      ::= { mdlTREntry 7 }
--
-- TReral port table for any media type
--

prtTRTable OBJECT-TYPE
      SYNTAX SEQUENCE OF PrtTREntry
      MAX-ACCESS not-accessible
      STATUS current
	  DESCRIPTION
	  "TReral port table for any media type."
      ::= { prtTR 1 }

prtTREntry OBJECT-TYPE
      SYNTAX    PrtTREntry
      MAX-ACCESS    not-accessible
      STATUS    current
	  DESCRIPTION
	  "An entry in table prtTRTable."
      INDEX     {  prtTRModuleID,prtTRID  }
      ::= { prtTRTable 1 }
 
PrtTREntry ::=
      SEQUENCE {
          prtTRModuleID
             Integer32,
          prtTRID
             Integer32,
          prtTRFunctionality
             INTEGER,
          prtTRConnectorType         
             INTEGER,
          prtTRAdminCmd
	 INTEGER,
          prtTRActiveState
             INTEGER,
          prtTRTrapMaskEnable
             INTEGER,
          prtTRstatus
             INTEGER,
          prtTRCableProtectEnable
              INTEGER,
          prtTRCableState
               INTEGER,
          prtTRMACAddress
             MacAddress,
          prtTRSpecific 
              OBJECT IDENTIFIER

          }

prtTRModuleID OBJECT-TYPE  
      SYNTAX  Integer32   
      MAX-ACCESS  read-only
      STATUS  current
      DESCRIPTION
      "A unique identifier of the module(slot no.)this port is attached to."
      ::= { prtTREntry 1 }

prtTRID OBJECT-TYPE  
      SYNTAX  Integer32   
      MAX-ACCESS  read-only
      STATUS  current
      DESCRIPTION
      "A unique identifier of the port within its module."
      ::= { prtTREntry 2 }

prtTRFunctionality OBJECT-TYPE
      SYNTAX  INTEGER {
           unknown(1),		
           ringin(2) ,
           ringout(3) ,
           satellite(4),
           lobe(5),
           link(6),
           tja(7),
           none(8),		-- N.C. repeater
           smart-port(9)              -- for RR-SAT if prtRRMode is set to smart-port
      }
      MAX-ACCESS  read-only
      STATUS  current
      DESCRIPTION
      "Describes the functionality of the port in a Token ring topology or other implementations."
      ::= { prtTREntry 3 }

prtTRConnectorType OBJECT-TYPE
      SYNTAX  INTEGER {
                notApplicable(1),		
	idc(2),      
	rj45(3),
                srj45(4),
                db9(5),      
                bnc(6),
                foSt(7),
	db25(8) 
--           foSma(9),          
--           foFc(10)
      }
      MAX-ACCESS  read-only
      STATUS  current
      DESCRIPTION
      "Type of hardware connector in the port." 
      ::= { prtTREntry 4 }

prtTRAdminCmd OBJECT-TYPE 
      SYNTAX  INTEGER {
          unknown(1),
          disable(2),
          enable(3),
          short(4),
          normal(5)
      }
      MAX-ACCESS  read-write
      STATUS  current
      DESCRIPTION
      "By setting this attribute to DISABLE(2) or SHORT(4) the 
       management station can force this  lobe/port/link-connection  to be 
        removed and block any access to the  network via this lobe/port/link.
       It is not mandatory that a certain lobe/port/link will support all the 
       enumerated states. The state of the lobe/port/link is type specific and
        indicated within the specific group"
 	::= { prtTREntry 5 }

prtTRActiveState OBJECT-TYPE
      SYNTAX  INTEGER {
           unknown(1),
           off(2),
           on(3),
           standby(4)
      }
      MAX-ACCESS  read-only
      STATUS  current
      DESCRIPTION
      "This attribute describes the electrical or optical activity 
       state of  a lobe or the state of a port.  Certain values may
       not be applicable in some cases"
      ::= { prtTREntry 6 }

prtTRTrapMaskEnable OBJECT-TYPE   
      SYNTAX  INTEGER {  
	   off(2),
	   on(3)
      }
      MAX-ACCESS  read-write    
      STATUS  current
      DESCRIPTION
      "When this attribute is set to OFF by the management console the 
       agent starts sending the unmasked traps related to this port. 
       Otherwise no traps from this port are sent."
      ::= { prtTREntry 7 }

prtTRstatus OBJECT-TYPE
      SYNTAX  INTEGER {
          unknown(1),
          disabledManuall(2),
          disabledAutorec(3),
          disabledSecurity(4),
          disableAuto(5),
          disableFlip(6),
          inserted(7),
          bypass(8),
          forcedloop(9),
          trunkfail(10),
          normal(11)
      }
      MAX-ACCESS  read-only
      STATUS  current
      DESCRIPTION
      "This attribute indicates the status of this lobe/port 
       connection:
      DISABLED - (2) to  (6) indicates the reason for the disabled state.
      INSERTED - (7)indicates that the lobe hardware inserts this lobe 
                 into the ring , thus it becomes part of the ring.
      BYPASS   - (8)indicates that the ring bypasses this lobe and the 
                 lobe hardware provides loopback connection towards the 
                 station for media test purposes.
      FORCEDLOOP - (9) indicates the port is in a loopback state and the 
                 main ring is connected to the backup path.
      TRUNKFAIL - (10) indicates that the ring connection is broken for a
                 repeater, converter or a cable protector.
      NORMAL   - (11) indicates the port is in normal condition.
      It is not mandatory that a certain lobe/port will support all the 
      enumerated states."
      ::= { prtTREntry 8 }

prtTRCableProtectEnable OBJECT-TYPE
      SYNTAX  INTEGER {
           unknown(1),
           off(2),    
           on(3),
            inhibit(4)   
      }	
      MAX-ACCESS  read-only
      STATUS  current
      DESCRIPTION
      "The value of this attribute determines activation of the cable-fault
      protection mechanism of  TCR and the optical link mechanism of
      TFR and TFC ."
      ::= { prtTREntry  9 }

prtTRCableState OBJECT-TYPE
      SYNTAX  INTEGER {
           unknown(1),
           failed(2),    
           normal(3),
           remoteFailed(4)    
      }
      MAX-ACCESS  read-only
      STATUS  current
      DESCRIPTION
      "The value of this attribute determines the cable status
       of  TCR and the optical link mechanism of
       TFR and TFC ."
      ::= { prtTREntry  10}


prtTRMACAddress OBJECT-TYPE
           SYNTAX  MacAddress
           MAX-ACCESS  read-only
           STATUS  current
           DESCRIPTION
           "The value of this object is the specific MAC address 
           of this interface which uniquely identifies this Interface 
           on a ring."
           ::= { prtTREntry 11 }

prtTRSpecific OBJECT-TYPE
      SYNTAX  OBJECT IDENTIFIER 
      MAX-ACCESS  read-only
      STATUS  current
      DESCRIPTION
      " Object identifier of entity containing additional information 
      regarding this instance. This entry is type specific."
      ::= { prtTREntry 12}

prtTRMacAddressTable OBJECT-TYPE
      SYNTAX SEQUENCE OF PrtTRMacAddressEntry
      MAX-ACCESS not-accessible
      STATUS current
	  DESCRIPTION
	  "."
      ::= { prtTR 2 }

prtTRMacAddressEntry OBJECT-TYPE
      SYNTAX    PrtTRMacAddressEntry
      MAX-ACCESS    not-accessible
      STATUS    current
	  DESCRIPTION
	  "An entry in table prtTRMacAddressTable."
      INDEX     {  prtTRMacAddressModuleID,prtTRMacAddressPortID, prtTRMacAddressID}
      ::= { prtTRMacAddressTable 1 }
 
PrtTRMacAddressEntry ::=
      SEQUENCE {
          prtTRMacAddressModuleID
             Integer32,
          prtTRMacAddressPortID
             Integer32,
          prtTRMacAddressID
             Integer32,
          prtTRMACAddressValue
             MacAddress
          }

prtTRMacAddressModuleID OBJECT-TYPE  
      SYNTAX  Integer32   
      MAX-ACCESS  read-only
      STATUS  current
      DESCRIPTION
      "A unique identifier of the module(slot no.)this port is attached to."
      ::= { prtTRMacAddressEntry 1 }

prtTRMacAddressPortID OBJECT-TYPE  
      SYNTAX  Integer32   
      MAX-ACCESS  read-only
      STATUS  current
      DESCRIPTION
      "A unique identifier of the port within its module."
      ::= { prtTRMacAddressEntry 2 }

prtTRMacAddressID OBJECT-TYPE  
      SYNTAX  Integer32   (1..250)
      MAX-ACCESS  read-only
      STATUS  current
      DESCRIPTION
      "A identifier of the MAC address in the list according to the ring order"
      ::= { prtTRMacAddressEntry 3 }

prtTRMACAddressValue OBJECT-TYPE
           SYNTAX  MacAddress
           MAX-ACCESS  read-only
           STATUS  current
           DESCRIPTION
           " MAC address from the list of addresses connected to this port"
           ::= { prtTRMacAddressEntry 4 }

-- 
-- file :v:\doc\rdv\mib\Before~1\radring.txt
-- 



--Version:    4.00
--Original : 30.11.93
--Last revision:  05.12.95              
--File:          radring.txt
				   
--

radRing  OBJECT IDENTIFIER ::= {radTokenRing 2}

--

chasRR OBJECT IDENTIFIER ::= {radRing 1} -- Chassis  information

segRR  OBJECT IDENTIFIER ::= { radRing 2 } --  segment information

moduleRR  OBJECT IDENTIFIER ::= { radRing 3 } --Module  information

prtRR OBJECT IDENTIFIER ::= { radRing 4 } --  Port  information


--
-- Chassis description for any object having to be surrounded by a frame
--
chType OBJECT-TYPE
      SYNTAX  DisplayString
      MAX-ACCESS  read-write
      STATUS  current
      DESCRIPTION
	" This value indicates which type of enclosure  the Rad agent is managing. The default value will be RadRing"
      ::= { chasRR 1 }

chNoSlot OBJECT-TYPE
      SYNTAX  Integer32 
      MAX-ACCESS  read-only
      STATUS  current
      DESCRIPTION
      "This value indicates the number of manageable slots in the chassis.
	   Not all slots must be occupied."
      ::= { chasRR 2 }

chPSPrimary OBJECT-TYPE
      SYNTAX  INTEGER {
	    unknown(1),        
	    off(2),
	    fault(3),
	    active(4),
	    recovered(5),
	    none(6)
      }
      MAX-ACCESS  read-only
      STATUS  current
      DESCRIPTION
      "This attribute indicates the status of the main (primary) power 
       supply  unit "
      ::= { chasRR 3 }

chPSSecondary OBJECT-TYPE
      SYNTAX  INTEGER {
	   unknown(1),        
	   off( 2),
	   fault(3),
	   active(4),
	   recovered(5),
	   none( 6)
      }
      MAX-ACCESS  read-only
      STATUS  current
      DESCRIPTION
      "This attribute indicates the status of the secondary power 
       supply  unit"
      ::= { chasRR 4 }

chTemperature OBJECT-TYPE
      SYNTAX  INTEGER {
	   ok(1),
	   exceed(2)
      }
      MAX-ACCESS  read-only
      STATUS  current
      DESCRIPTION
      "This attribute indicates if the internal hub temperature exceeded
       the permissible maximum "
      ::= { chasRR 5 }

chEtMainClock OBJECT-TYPE
      SYNTAX  INTEGER {
           unknown(1),
           ok(2),
           fault(3)
      }
      MAX-ACCESS  read-only
      STATUS  current
      DESCRIPTION
      "This attribute indicates the status of Eternet repeater main clock
      in RadRingII hub"
      ::= { chasRR 6 }

chEtSecClock OBJECT-TYPE
      SYNTAX  INTEGER {
           unknown(1),
           ok(2),
           fault(3)
      }
      MAX-ACCESS  read-only
      STATUS  current
      DESCRIPTION
      "This attribute indicates the status of Eternet repeater secondary clock
      in RadRingII hub"
      ::= { chasRR 7 }

--
-- RADRing segments' specific information
--

segRRSecurityTable OBJECT-TYPE
	       SYNTAX SEQUENCE OF SegRRSecEntry
	       MAX-ACCESS not-accessible
	       STATUS current
	       DESCRIPTION
		   "RADRing segments' specific information"
	       ::= { segRR 1}

segRRSecEntry OBJECT-TYPE
	       SYNTAX SegRRSecEntry
	       MAX-ACCESS not-accessible
	       STATUS current
	       DESCRIPTION
		   "An entry in table segRRSecurityTable."
	       INDEX { segRRID, segRRSecID}
	       ::= { segRRSecurityTable 1}
   
SegRRSecEntry ::= 
	    SEQUENCE {
	   segRRID
	      Integer32,
	   segRRSecID
	      Integer32,
	   segRRSecEnable
	      INTEGER,
	   segRRSecurityPattern
	      MacAddress,
	   segRRSecurityMask
	      MacAddress
	} 

segRRID OBJECT-TYPE
	   SYNTAX  Integer32  (1..21)
	   MAX-ACCESS  read-only
	   STATUS  current
	   DESCRIPTION
	   "Segment unique identification number (internal). It is  
	    the extreme left slot, marking the beginning of the 
	    segment.
	    TR segment no.: 1 .. 20 
	    Ethernet segment no.: 21."
      ::= { segRRSecEntry 1 }

segRRSecID OBJECT-TYPE
	   SYNTAX  Integer32  
	   MAX-ACCESS  read-only
	   STATUS  current
	   DESCRIPTION
	   "Segment's security unique identification number"
      ::= { segRRSecEntry 2 }

segRRSecEnable  OBJECT-TYPE
	   SYNTAX  INTEGER {
		off(2),
		on(3)
	}
	   MAX-ACCESS  read-write
	   STATUS  current
	   DESCRIPTION
	   "This entry indicates whether the specific segment's security is active or not"
      ::= { segRRSecEntry 3 }

segRRSecurityPattern OBJECT-TYPE
      SYNTAX  MacAddress
      MAX-ACCESS  read-write
      STATUS  current
      DESCRIPTION
      "A six-octet (48 bit) pattern, where the masked bits of segTRSecurityMask
       need to match the MAC address of each port within the segment. A Value of 
       all-zeros  indicates no security."
      ::= { segRRSecEntry 4 }

segRRSecurityMask  OBJECT-TYPE
      SYNTAX  MacAddress
      MAX-ACCESS  read-write
      STATUS  current
      DESCRIPTION
      "Mask of the allowed MAC address that can be connected through 
      the ports within  the segment"
    ::= { segRRSecEntry 5}

--
-- RADRing  specific modules' information
--

mdlRRTable OBJECT-TYPE
	       SYNTAX SEQUENCE OF MdlRREntry
	       MAX-ACCESS not-accessible
	       STATUS current
	       DESCRIPTION
		   "RADRing  specific modules' information"
	       ::= { moduleRR 1 }

mdlRREntry OBJECT-TYPE
	       SYNTAX MdlRREntry
	       MAX-ACCESS not-accessible
	       STATUS current
	       DESCRIPTION
		   "An entry in table mdlRRTable."
	       INDEX { mdlRRid}
	       ::= { mdlRRTable 1}

MdlRREntry ::= 
	    SEQUENCE {
	    mdlRRid
	  Integer32,
	     mdlRRTLRstatus
	   INTEGER,
	     mdlRRtermination
	   INTEGER,
	    mdlRRReset                     
	  INTEGER, 
	     mdlRRLed
	   OCTET STRING,
	     mdlRRSpeed
	   INTEGER,    
	     mdlRRMngAutoDis
	   INTEGER,
	     mdlRRAutodisable
	   INTEGER,             
	     mdlRRConfigMsg
	   OCTET STRING,
	     mdlRRMngState
	   INTEGER,
	     mdlRRType 
	   INTEGER,
	     mdlRRHwVer 
	   DisplayString,
	     mdlRRSwVer 
	   DisplayString,
	     mdlRRSpecific 
       OBJECT IDENTIFIER 
	   }

mdlRRid OBJECT-TYPE
	   SYNTAX  Integer32  (1..20)
	   MAX-ACCESS  read-only
	   STATUS  current
	   DESCRIPTION
	   "Unique number to identify the module. It indicates the slot
	    number the module is inserted in."
	 ::= { mdlRREntry 1}

mdlRRTLRstatus  OBJECT-TYPE   
      SYNTAX  INTEGER {
			unknown(1),
		off(2),
		on(3)
		}
      MAX-ACCESS  read-only
      STATUS  current
      DESCRIPTION
	"This entry specifies the status of the setup on the TL-2/Exx
	 modules. When the value is ON, lobe one is the only active lobe. This entry
	  will have the value UNKNOWN for all other modules   "
      ::= { mdlRREntry 2 }

mdlRRtermination  OBJECT-TYPE
      SYNTAX  INTEGER {
	   unknown(1),          
	   off(2),
	   on(3)
      }
      MAX-ACCESS  read-only
      STATUS  current
      DESCRIPTION
      "Attribute describing the termination state as set by the switches on the
       lobe modules"
      ::= { mdlRREntry 3 }


mdlRRReset  OBJECT-TYPE
      SYNTAX  INTEGER {
	   unknown(1),
	   off(2),
	   on(3)
	      }
      MAX-ACCESS  read-write
      STATUS  current
      DESCRIPTION
      "When this object is set to the value of ON(3),
       the module performs software reset. Upon completion, a trap  will
       be issued to the management station and  the value
       will be set to OFF. This entry will have the value of UNKNOWN (1) for 
       modules without independent processors. This command should be masked 
       for the agent module"
      ::= { mdlRREntry 4 }

mdlRRLed  OBJECT-TYPE   
      SYNTAX  OCTET STRING 
      MAX-ACCESS  read-only
      STATUS  current
      DESCRIPTION
	"This entry specifies  the LEDs status in the module . Each led will be represented by 4 bits
	where the first 2 bits will specify  the status (NA, OFF, ON, BLINK), and the next two bits
	will specify the color (RED, GREEN, YELLOW)"
      ::= { mdlRREntry 5}

mdlRRSpeed OBJECT-TYPE
      SYNTAX  INTEGER {
	unknown(1),        -- for WAN cards     
	fourMegabit(2),
	sixteenMegabit(3), 
	tenMegabit(4)      -- for Ethernet
      }
      MAX-ACCESS  read-only
      STATUS  current
      DESCRIPTION
      "Attribute describing the bandwidth of the media as set by the module switches."
      ::= { mdlRREntry 6 }

mdlRRMngAutoDis OBJECT-TYPE   
      SYNTAX   INTEGER {
		unknown(1),
		off(2),
		on(3)
	}
      MAX-ACCESS  read-only
      STATUS  obsolete
      DESCRIPTION
      "Attribute describing the setup of the MNG switch on the TL- Active cards. Value ON indicates 
       the ability of activating  the auto-disable mechanism of the card via management command. 
       Value   OFF indicates  that the activation of the auto-disable mechanism of the card  is according 
       to the switch setting.In this case the mdlRRAutodisable will not be available for write 
	   operation. Applicable to Token Ring cards only.
	   Replaced by mdlRRMngState."
      ::= { mdlRREntry 7}

mdlRRAutodisable  OBJECT-TYPE   
      SYNTAX   INTEGER {
		  notApplicable(1),
		  off(2),
		  on(3)
	}
      MAX-ACCESS  read-write
      STATUS  current
      DESCRIPTION
	"This attribute can be set by the manager if the value of mdlRRMngAutoDis is ON. It 
   	controls the behavior of the Active cards regarding the Auto-disable mechanism. All
	  ports will be in the same mode. Applicable to Token Ring cards only."
      ::= { mdlRREntry 8 }

 mdlRRConfigMsg OBJECT-TYPE   
      SYNTAX  OCTET STRING
      MAX-ACCESS  read-only
      STATUS  current
      DESCRIPTION
      "Full configuration message  coded in internal RAD application format.
      This entry describes  module' configuration. "
      ::= { mdlRREntry 9 }
 
mdlRRMngState OBJECT-TYPE   
      SYNTAX   INTEGER {
		unknown(1),
		disable(2),
		enable(3)
}
      MAX-ACCESS  read-only
      STATUS  current
      DESCRIPTION
      " This entry indicates  the setting of the module's switches. ENABLE means that the module 
       can accept management commands. "
      ::= { mdlRREntry 10 }


mdlRRType OBJECT-TYPE
      SYNTAX  INTEGER {
	    unknown(1),
	    empty(2),
	    tl4s(3),
	    tl4su(4),
	    tl4sd(5),
	    tl4cx(6), 
	    tl4u(7),
	    tl2edu(8), 
	    tl2eds(9),
	    tl2edsu(10),
	    tl2f(11),   
	    tja(12),      
	    tio(13),
	    tfr(14),
	    tfc1(15),
	    tfc2(16),
	    tcr(17),
	    tl4au(18),
	    tl4as(19),
	    tl4asd(20),
	    tl4asu(21),
	    tre1d(22),
	    tre(23),
	    tre8d(24),
	    stc1(25),
	    stc2(26),
	    ftc(27),
	    cmlib(28),
	    tl2fsat(29),
-- WAN
	    taV24(30),
	    taV11(31),
	    wangVs(32),
	    ta3x74(33),
	    ta3x(34),                    
-- rr-sat
	sat-asu(35),
	sat-asd(36),
	sat-su(37),
	sat-sd(38),
-- ethernet
	ep8t(39),
	ep4taui(40),
	ep4t2fl(41),
	ep4tfl(42),
	ep4fl(43),
-- epr
	epr8t(45),
	epr4taui(46),
	epr4t2fl(47),
	epr4tfl(48),
	epr4fl(49),
-- rr
	tl2fm(51),
	ftc2(53),
	mlbt(54),
	mlbtf(55),
	ftbDfo(56),
	ftbSfo(57),
	mbe8d(58),
	mbe1d(59),
	cmlibE(60)
      }
      MAX-ACCESS  read-only
      STATUS  current
      DESCRIPTION
      "Indicates the type of the module installed in the specified slot number."
      ::= { mdlRREntry 11}

mdlRRHwVer OBJECT-TYPE
      SYNTAX  DisplayString
      MAX-ACCESS  read-write
      STATUS  current
      DESCRIPTION
      "ASCII string for description and display of the module's hardware version,
      as it is known by the module's software. A manager can record his own 
      hardware upgrade."
      ::= { mdlRREntry 12 }

mdlRRSwVer OBJECT-TYPE
      SYNTAX  DisplayString
      MAX-ACCESS  read-only
      STATUS  current
      DESCRIPTION
      "ASCII string for description and display of the module's 
       software version. A value of NOT APPLICABLE will be recorded
       for a module having no independent processor."
      ::= { mdlRREntry  13 }

mdlRRSpecific OBJECT-TYPE
      SYNTAX  OBJECT IDENTIFIER
      MAX-ACCESS  read-only
      STATUS  current
      DESCRIPTION
      " Object identifier of entity containing additional information 
      regarding this instance. This entry is module type specific."
      ::= { mdlRREntry 14 }




--
-- Additional parameters that can be monitored for a segment with an inband module.
-- Module specific for Token Ring


mdlIBTable OBJECT-TYPE
	       SYNTAX SEQUENCE OF MdlIBEntry
	       MAX-ACCESS not-accessible
	       STATUS current
	       DESCRIPTION
		   "Additional parameters that can be monitored for a segment
		    with an inband module. Module specific for Token Ring"
	       ::= { moduleRR 2 }

mdlIBEntry OBJECT-TYPE
	       SYNTAX MdlIBEntry
	       MAX-ACCESS not-accessible
	       STATUS current
	       DESCRIPTION
		   "An entry in table mdlIBTable."
	       INDEX { mdlIBid}
	       ::= { mdlIBTable 1}

MdlIBEntry ::= 
	    SEQUENCE {
	       mdlIBid
		  Integer32,
	       mdlIBsegID
		  Integer32,
	       mdlIBCorrelationEnable
		  INTEGER,
	       mdlIBAutorecEnable
		  INTEGER,
	       mdlIBAutorecResult
		 INTEGER,
	       mdlIBcommand
		 INTEGER,
	       mdlIBstate
		 INTEGER,
	       mdlIBagnt
    	 INTEGER,
	       mdlIBIpAddress
		 IpAddress,
	       mdlIBLocalMacAddr
		 MacAddress,
	       mdlIBbrnInMacAddr
		 MacAddress,
	       mdlIBLocalAddrStatus
		 INTEGER,
	       mdlIBTrapMaskEnable
	 INTEGER
	 }

mdlIBid OBJECT-TYPE
	   SYNTAX  Integer32  (1..20)
	   MAX-ACCESS  read-only
	   STATUS  current
	   DESCRIPTION
	   "Unique number to identify the CML\IB module. It indicates the slot
	    number the module is inserted in"
	   ::= {  mdlIBEntry 1 }

mdlIBsegID OBJECT-TYPE
	   SYNTAX  Integer32  (1..20)
	   MAX-ACCESS  read-only
	   STATUS  current
	   DESCRIPTION
	   "Unique number to identify the segment where the CML\IB module
	    is inserted. It is one of the segTRID values."
	   ::= {  mdlIBEntry 2 }

mdlIBCorrelationEnable OBJECT-TYPE
	   SYNTAX  INTEGER {
		off(2),
		on(3)
		     }
	   MAX-ACCESS  read-write
	   STATUS  current
	   DESCRIPTION
	   "When set to ON(3), the in-band agent should perform 
	    correlation each time a station enters/leaves the segment."
	   ::= { mdlIBEntry 3 }

mdlIBAutorecEnable OBJECT-TYPE
	   SYNTAX  INTEGER {
		off(2),
		on(3)
		     }
	   MAX-ACCESS  read-write
	   STATUS  current
	   DESCRIPTION
	   "When set to ON(3), the in-band agent should perform 
	    autorecovery each time a beacon status is detected."
	   ::= { mdlIBEntry 4 }

mdlIBAutorecResult OBJECT-TYPE
	   SYNTAX  INTEGER {
		notStarted(1),
		started(2),
		segmentOk(3),
		segmentFixed(4),
		segmentClosed(5),
		failed(6),
		hubProblem(7)
		     }
	   MAX-ACCESS  read-only
	   STATUS  current
	   DESCRIPTION
	    "When autorecovery is completed the result will be reported (3)..(7).
	     While in autorecovery process, started(2) will be reported.
	     Before autorecovery process, notStarted(1) will be reported."  
	   ::= { mdlIBEntry 5 }

mdlIBcommand   OBJECT-TYPE
	 SYNTAX  INTEGER {
		       noOp(1),
		       open(2),
		       reset(3),
		       close(4)
		 }
	 MAX-ACCESS  read-write
	 STATUS  current
	 DESCRIPTION
		 "When this object is set to the value of
		  open(2), the station should go into the
		  open state.  The progress and success of
		  this command is given by the values of the
		  object mdlIBstate.
		      When this object is set to the value
		  of reset(3), then the station should do
		  a reset.  On a reset, all MIB counters
		  should retain their values, if possible.
		  Other side effects depend on the hardware chip set.
		      When this object is set to the value
		  of close(4), the station should go into
		  the closed state by removing itself
		  from the ring.
		      Setting this object to a value of
		  no-op(1) has no effect.
		      For read operation, this object has always a
		  value of no-op(1). It is not permitted to apply this 
	      command on an agent module."
	 ::= { mdlIBEntry 6 }

mdlIBstate OBJECT-TYPE
		     SYNTAX  INTEGER
		{ 
		unknown (1),
		opened(2),
		closed(3),
		opening(4),
		closing(5),
		badParam(6),
		lobeFailed(7),
		signalLoss(8),
		insertionTimeout(9),
		ringFailed(10),
		beaconning(11),
		duplicateMac(12),
		requestFailed(13),
		removeReceived(14),
		budFailure(15),
		initFailure(16)
		}                       
		     MAX-ACCESS  read-only
		     STATUS  current
		     DESCRIPTION
			     "The current adapter status, which can
			     be used to diagnose fluctuating problems."
	::= { mdlIBEntry 7 }

mdlIBagnt OBJECT-TYPE
	   SYNTAX  INTEGER  {
		off(2),
		on (3),
		standBy (4)
    	}
	   MAX-ACCESS  read-only
	   STATUS  current
	   DESCRIPTION
	" Indicates whether the specific inband module serves as:
	  - Active hub agent - (on)
	  - Ring Monitor (for TR module only) - (off)
	  - Standby agent - (standBy)"
	::= { mdlIBEntry 8 }

mdlIBIpAddress OBJECT-TYPE
      SYNTAX  IpAddress
      MAX-ACCESS  read-only
      STATUS  current
      DESCRIPTION
      "Indicates IP address of the module if the module serves as  
       an agent of itself."
      ::= {  mdlIBEntry 9}

mdlIBLocalMacAddr OBJECT-TYPE
	   SYNTAX  MacAddress
	   MAX-ACCESS  read-write
	   STATUS  current
	   DESCRIPTION
	   "The value of this object is the specific MAC address 
	   of this interface which uniquely identifies this interface 
	   on a ring.It is the address set by the management  and
           upon request it will replace the burn in address.
           Non-canonical format."
	   ::= { mdlIBEntry 10}

mdlIBLocalAddrStatus OBJECT-TYPE
	   SYNTAX  INTEGER {
		   unknown(1),
		   off(2),
		   on(3)
		}
	   MAX-ACCESS  read-write
	   STATUS  current
	   DESCRIPTION
	   "The value of this object specifies whether the specific 
	    MAC address  of this interface was set by the local 
	    management or it is the burn-in address in use."
	   ::= { mdlIBEntry 11 }

mdlIBbrnInMacAddr OBJECT-TYPE 
      SYNTAX   MacAddress
      MAX-ACCESS  read-only
      STATUS  current
      DESCRIPTION
	"The value of this object is the specific Burn-in MAC address 
	   of this interface which uniquely identifies this interface 
	   on a ring. Non-canonical format."
	   ::= { mdlIBEntry 12 }

mdlIBTrapMaskEnable OBJECT-TYPE
	   SYNTAX  INTEGER {
	    off(2),
	   on(3)
      }
      MAX-ACCESS  read-write    
      STATUS  current
      DESCRIPTION
      "When this attribute is set to OFF by the management console, the 
       agent starts sending the unmasked traps related to this module. 
       Otherwise, no traps are sent by this module."
	   ::= { mdlIBEntry 13 }

-- Special modules such as bridges/converters  that are within the hub
--

mdlBRGTable OBJECT-TYPE
	       SYNTAX SEQUENCE OF MdlBRGEntry
	       MAX-ACCESS not-accessible
	       STATUS current
	       DESCRIPTION
		   "Special modules such as bridges/converters  that are within the hub"
	       ::= { moduleRR 3 }

mdlBRGEntry OBJECT-TYPE
	       SYNTAX MdlBRGEntry
	       MAX-ACCESS not-accessible
	       STATUS current
	       DESCRIPTION
		   "An entry in table mdlBRGTable."
	       INDEX { mdlBRGid}
	       ::= { mdlBRGTable 1}

MdlBRGEntry ::= 
	    SEQUENCE {
	  mdlBRGid
	      Integer32,
	   mdlBRGReady
	      INTEGER,
	   mdlBRGStatus
	       DisplayString,
	    mdlBRGLocation
	       INTEGER,
	    mdlBRGIpAddress
	       IpAddress,
	    mdlBRGMacAddr
	       MacAddress,
		mdlBRGAdapterState
		   INTEGER,
		mdlBRGBypassSw
		   INTEGER
	 }

mdlBRGid OBJECT-TYPE
	   SYNTAX  Integer32  (1..20)
	   MAX-ACCESS  read-only
	   STATUS  current
	   DESCRIPTION
	   "Unique number to identify the module. It indicates the slot
	    number the module is inserted in."
	 ::= { mdlBRGEntry 1}

 mdlBRGReady  OBJECT-TYPE   
      SYNTAX  INTEGER {  
	   unknown(1),
	   off(2), 
	   on(3),
	    blink(4)
      }
      MAX-ACCESS  read-only    
      STATUS  current
      DESCRIPTION
       "This entry will have the value ON when packets can be transferred in the TRE module.
	 The value UNKNOWN will be used for all other modules where this characteristic is 
	not applicable"
	 ::= { mdlBRGEntry 2}

mdlBRGStatus OBJECT-TYPE   
      SYNTAX  DisplayString      
      MAX-ACCESS  read-only    
      STATUS  current
      DESCRIPTION
      "This entry specifies the status of operation of the STC or FTC modules. For other modules
	this value will read NOAP"
 ::= { mdlBRGEntry 3}

 mdlBRGLocation  OBJECT-TYPE   
      SYNTAX  INTEGER {  
	   unknown(1),
	   main(2), 
	   remote(3),
	   secondary(4)
      }
      MAX-ACCESS  read-only    
      STATUS  current
      DESCRIPTION
       "This entry indicates the configuration mode:
        - for the TRE bridge (main/remote) 
        - for MLB-T, MLBT-F (main/secondary) "
 ::= { mdlBRGEntry 4}

mdlBRGIpAddress OBJECT-TYPE
      SYNTAX  IpAddress
      MAX-ACCESS  read-only
      STATUS  current
      DESCRIPTION
      "Indicates IP address of the module if the module serves as  an agent of itself. For 
       all other modules the IP value will be 0.0.0.0"
      ::= {  mdlBRGEntry 5}


mdlBRGMacAddr OBJECT-TYPE 
      SYNTAX   MacAddress
      MAX-ACCESS  read-only
      STATUS  current
      DESCRIPTION
	"The value of this object is the specific MAC address 
	   of this interface which uniquely identifies this interface 
	   on a ring."
	   ::= { mdlBRGEntry 6}

mdlBRGAdapterState OBJECT-TYPE
		     SYNTAX  INTEGER
		{ 
		unknown (1),
		opened(2),
		closed(3),
		opening(4),					  
		closing(5),
		badParam(6),
		lobeFailed(7),
		signalLoss(8),
		insertionTimeout(9),
		ringFailed(10),
		beaconning(11),
		duplicateMac(12),
		requestFailed(13),
		removeReceived(14),
		budFailure(15),
		initFailure(16)
		}                       
		     MAX-ACCESS  read-only
		     STATUS  current
		     DESCRIPTION
			     "The current adapter status, which can
			      be used to diagnose fluctuating problems.
			      This object is applicable only for TR bridges
			      with adapter.
			      The value 'unknown' will be used for other 
			      module types."
	::= { mdlBRGEntry 7 }

mdlBRGBypassSw  OBJECT-TYPE   
      SYNTAX  INTEGER {  
	   unknown(1),
	   off(2), 
	   on(3)
      }
      MAX-ACCESS  read-only    
      STATUS  current
      DESCRIPTION
       "This entry is applicable only for FTB-D/FO module.
        It describes the status of the Bypass Switch. 
        The value UNKNOWN will be used for all other modules where 
        this characteristic is not applicable"
	 ::= { mdlBRGEntry 8}



-- Special "WAN" modules that are within the RadRing hub
--

mdlMMTable OBJECT-TYPE
	       SYNTAX SEQUENCE OF MdlMMEntry
	       MAX-ACCESS not-accessible
	       STATUS current
	       DESCRIPTION
		   "Special 'WAN' modules that are within the RadRing hub"
	       ::= { moduleRR 4 }

mdlMMEntry OBJECT-TYPE
	       SYNTAX MdlMMEntry
	       MAX-ACCESS not-accessible
	       STATUS current
	       DESCRIPTION
		   "An entry in table mdlMMTable."
	       INDEX { mdlMMid}
	       ::= { mdlMMTable 1}

MdlMMEntry ::= 
	    SEQUENCE {
	  mdlMMid
	      Integer32,
	   mdlMMBertCmd
	      INTEGER
	 }

mdlMMid OBJECT-TYPE
	   SYNTAX  Integer32  (1..20)
	   MAX-ACCESS  read-only
	   STATUS  current
	   DESCRIPTION
	   "Unique number to identify the module. It indicates the slot
	    number the module is inserted in."
	 ::= { mdlMMEntry 1}

mdlMMBertCmd OBJECT-TYPE
	   SYNTAX  INTEGER {
	     unknown(1),
		 off(2),
		 on(3)
		     }
	   MAX-ACCESS  read-write
	   STATUS  current
	   DESCRIPTION
	   "Setting this Object to ON, will start BERT test on all the channels that are currently in               
	     Remote Loop. If the value of mdlRRMngState is disabled, this parameter is read-only
		     and  reflects the module jumper setting. "
	   ::= { mdlMMEntry 2}

-- "Ethernet" modules that are within the hub
--

mdlETTable OBJECT-TYPE
	       SYNTAX SEQUENCE OF MdlETEntry
	       MAX-ACCESS not-accessible
	       STATUS current
		   DESCRIPTION
		   "'Ethernet' modules that are within the hub"
	       ::= { moduleRR 5 }

mdlETEntry OBJECT-TYPE
	       SYNTAX MdlETEntry
	       MAX-ACCESS not-accessible
	       STATUS current
		   DESCRIPTION
		   "An entry in table mdlETTable."
	       INDEX { mdlMMid }
	       ::= { mdlETTable 1}

MdlETEntry ::= 
	    SEQUENCE {
       mdlETid
	      Integer32,
	   mdlETSAmode
	      INTEGER
	 }

mdlETid OBJECT-TYPE
	   SYNTAX  Integer32  (1..20)
	   MAX-ACCESS  read-only
	   STATUS  current
	   DESCRIPTION
	   "Unique number to identify the module. It indicates the slot
	    number the module is inserted in. It is the same
		as rptrGroupIndex in the Repeater MIB"
	 ::= { mdlETEntry 1}

mdlETSAmode       OBJECT-TYPE
      SYNTAX   INTEGER {
	       unknown(1),
	       off(2),
	       on(3)
}
      MAX-ACCESS  read-write
      STATUS  current
      DESCRIPTION
      "Setting this Object to ON, will change the mode of operation 
       of the Ethernet card to a stand alone operation mode. It will 
       disconnect the card from the repeater bus. The rptrGroupOperStatus 
	   parameter in the Repeater MIB is changed to other(1). 
	   The parameter is read-only when the value of  mdlRRMngState 
	   is disabled"
	 ::= { mdlETEntry 2 }

--
--RADRing specific port information
--

prtRRTable OBJECT-TYPE
      SYNTAX SEQUENCE OF PrtRREntry
      MAX-ACCESS not-accessible
      STATUS current
      DESCRIPTION
	  "RADRing specific port information"
      ::= { prtRR 1 }

prtRREntry OBJECT-TYPE
      SYNTAX    PrtRREntry
      MAX-ACCESS    not-accessible
      STATUS    current
      DESCRIPTION
	  "An entry in table prtRRTable."
      INDEX     { prtRRmdlID, prtRRID }
      ::= { prtRRTable 1 }
 
PrtRREntry ::=
      SEQUENCE {
	  prtRRmdlID
	     Integer32,
	  prtRRID
	     Integer32,
	  prtRRSecurityState
	      INTEGER,
	  prtRRSecurityEnable
	      INTEGER,
	  prtRRSecurityMask  
	     MacAddress,
	  prtRRSecurityPattern
	     MacAddress,
	  prtRRJitterAttenEnable 
	     INTEGER,
	  prtRRConfigMsg
	      OCTET STRING,
	  prtRRFlipAutoDisable
	     INTEGER,
	  prtRRSecurityMask2
	     MacAddress,
	  prtRRSecurityPattern2
	     MacAddress,
	  prtRRMode
	      INTEGER,
	   prtRRAttachment
	      INTEGER
		 }

prtRRmdlID OBJECT-TYPE  
      SYNTAX  Integer32   
      MAX-ACCESS  read-only
      STATUS  current
      DESCRIPTION
      "A unique identifier of the module,(slot no.),this port is attached to."
      ::= { prtRREntry 1 }

prtRRID OBJECT-TYPE  
      SYNTAX  Integer32   
      MAX-ACCESS  read-only
      STATUS  current
      DESCRIPTION
      "A unique identifier of the port within its module."
      ::= { prtRREntry 2 }

prtRRSecurityState OBJECT-TYPE
	   SYNTAX  INTEGER {
		 notactive(1),
		 active(2)
		     }
	   MAX-ACCESS  read-only
	   STATUS  current
	   DESCRIPTION
	   "This entry indicates whether a security check can be performed on 
	    the specific port. This value is directly related to the
	    presence of an inband module in the segment where the port
	    belongs to and to activation of the correlation process."
	   ::= {  prtRREntry 3 }

prtRRSecurityEnable OBJECT-TYPE
      SYNTAX  INTEGER 
	{
	    off(2),
	    on(3)
	}
      MAX-ACCESS  read-write
      STATUS  current
      DESCRIPTION
      "This value indicates whether a security check should be performed.
       Setting this value to ON(3) will activate the security mechanism
       if and only if, the value of  prtRRSecurityState is ACTIVE."
      ::= { prtRREntry 4 }


prtRRSecurityMask OBJECT-TYPE
      SYNTAX  MacAddress
      MAX-ACCESS  read-write
      STATUS  current
      DESCRIPTION
      "Mask of the allowed MAC address that can be connected through 
      this port. The security of the individual port overwrites  the
       security of the segment where the port belongs to"
      ::= { prtRREntry 5 }

prtRRSecurityPattern   OBJECT-TYPE
      SYNTAX  MacAddress
      MAX-ACCESS  read-write
      STATUS  current
      DESCRIPTION
      "A six-octet(48 bit) pattern, where the masked bits of prtRRSecurityMask
       should match the MAC address."
      ::= { prtRREntry 6}

prtRRJitterAttenEnable OBJECT-TYPE
      SYNTAX  INTEGER {
	   unknown(1),
	   off(2),    
	   on(3)    
      }
      MAX-ACCESS  read-write
      STATUS  current
      DESCRIPTION
      "The value of this attribute determines activation of the
      jitters Attenuation mechanism of  repeater's port ."
      ::= { prtRREntry 7 }

 prtRRConfigMsg OBJECT-TYPE   
      SYNTAX  OCTET STRING
      MAX-ACCESS  read-only
      STATUS  current
      DESCRIPTION
      "Full configuration message  coded in internal RAD application format.
      This entry describes  port' configuration. "
      ::= { prtRREntry  8 }

prtRRFlipAutoDisable OBJECT-TYPE   
      SYNTAX   INTEGER {
		noApplicable(1),
		off(2),
		on(3)
	}
      MAX-ACCESS  read-write
      STATUS  current
      DESCRIPTION
      "Attribute describing the control on the flipping mechanism of a lobe . 
	Value ON indicates  the ability of the lobe to  auto disable itself when flipping occur. 
	Value   OFF indicates  that  the auto disable mechanism should not be activated and the 
	lobe should stay in a flipping state. 
       This attribute applies on selected lobes (tl-2/f, or tl-2/fsat)"
      ::= { prtRREntry  9 }

prtRRSecurityMask2 OBJECT-TYPE
      SYNTAX  MacAddress
      MAX-ACCESS  read-write
      STATUS  current
      DESCRIPTION
      "Mask of the allowed MAC address that can be connected through 
      this port. The security of the individual port overwrites  the
       security of the segment where the port belongs to"
      ::= { prtRREntry 10 }

prtRRSecurityPattern2   OBJECT-TYPE
      SYNTAX  MacAddress
      MAX-ACCESS  read-write
      STATUS  current
      DESCRIPTION
      "A six-octet(48 bit) pattern: where the masked bits of prtRRSecurityMask2
       should match the MAC address."
      ::= { prtRREntry 11 }

prtRRMode  OBJECT-TYPE
      SYNTAX  INTEGER
{
		noApplicable (1),
		smart-port   (2),
		port         (3),
		interRptrPort(4),
		multiConnPort(5)
}
      MAX-ACCESS  read-write
      STATUS  current
      DESCRIPTION
     "Indicates the port status of rr-sat card after the communication
      is broken. When configured to smart-port, the port disables itself
      when there is no management communication with attachment.
      interRptrPort - this port is used to connect an external 
                      repeater. No security can be set for this port.
                      MAC Address is set to 0. No traps 'MAC Address changed'
                      are generated.
      multiConnPort - this port is used for connection of external
                      4 port repeater. 8 securities per port exist.
                      MAC Address is set to 0. No traps 'MAC Address changed'
                      are generated. "
      ::= { prtRREntry 12 }

prtRRAttachment  OBJECT-TYPE
      SYNTAX  INTEGER
{
		none(1),
		station(2),
		sLau2(3),
		sLau4(4)
}
      MAX-ACCESS  read-only
      STATUS  current
      DESCRIPTION
     "Indicates the type of the port attachment. Smart attachment types
      are applicable for rr-sat card only"
      ::= { prtRREntry 13 }
    
--
--RADRing specific WAN modules port information 
--

prtMMTable OBJECT-TYPE
      SYNTAX SEQUENCE OF PrtMMEntry
      MAX-ACCESS not-accessible
      STATUS current
      DESCRIPTION
	  "RADRing specific WAN modules port information."
      ::= { prtRR 2 }

prtMMEntry OBJECT-TYPE
      SYNTAX    PrtMMEntry
      MAX-ACCESS    not-accessible
      STATUS    current
      DESCRIPTION
	  "An entry in table prtMMTable."
      INDEX     { prtMMmdlID, prtMMID  }
      ::= { prtMMTable 1 }
 
PrtMMEntry ::=
      SEQUENCE {
	  prtMMmdlID
	     Integer32,
	  prtMMID
	     Integer32,
      prtMMAdminCmd
	     INTEGER,
      prtMMOperStatus
	     INTEGER,
      prtMMTestStatus
	     INTEGER,
      prtMMBertResult
	     INTEGER,
      prtMMTrapMaskEnable
	     INTEGER
      }

prtMMmdlID OBJECT-TYPE  
      SYNTAX  Integer32   
      MAX-ACCESS  read-only
      STATUS  current
      DESCRIPTION
      "A unique identifier of the module(slot no.)this port is attached to."
      ::= { prtMMEntry 1 }

prtMMID OBJECT-TYPE  
      SYNTAX  Integer32   
      MAX-ACCESS  read-only
      STATUS  current
      DESCRIPTION
      "A unique identifier of the port (link) within its module."
      ::= { prtMMEntry 2 }

prtMMAdminCmd  OBJECT-TYPE
      SYNTAX  INTEGER {
	   normal(1),
	   locLoop(2),    
	   remLoop(3)    
}            
      MAX-ACCESS  read-write
      STATUS  current
      DESCRIPTION
      "Setting the object to locLoop(2) or remLoop(3) will activate the corresponding test.
	  Value remLoop(3) activates the BERT test on the related link if mdlMMBertCmd
	  is set to on(3). Setting parameter to normal(1), restores the normal operation
	  of the link. The parameter is read-only when value of mdlRRMngState is disable"
      ::= { prtMMEntry 3 }

prtMMOperStatus OBJECT-TYPE
      SYNTAX  INTEGER {
	   operational(1),
	   locSyncLoss(2),    
	   remSyncLoss(3)
}            
      MAX-ACCESS  read-only
      STATUS  current
      DESCRIPTION
	  "Reflects the Synchronization status. "
      ::= { prtMMEntry 4 }

prtMMTestStatus OBJECT-TYPE
      SYNTAX  INTEGER {
	   normal(1),
	   locLoop(2),    
	   remLoop(3),
	   bert(4)    
}            
      MAX-ACCESS  read-only
      STATUS  current
      DESCRIPTION
	  "Reflects the link status. When the object is set to the value of bert(4),
      it means that the remote loopback is active too. "
      ::= { prtMMEntry 5 }

prtMMBertResult  OBJECT-TYPE
      SYNTAX  INTEGER {
	   unknown(1),
	   fault(2),    
	   ok(3)    
}            
      MAX-ACCESS  read-only
      STATUS  current
      DESCRIPTION
	  "The value of this object indicates the status of the last BERT test."
      ::= { prtMMEntry 6 }

prtMMTrapMaskEnable OBJECT-TYPE
	   SYNTAX  INTEGER {
	   off(2),
	   on(3)
      }
      MAX-ACCESS  read-write    
      STATUS  current
      DESCRIPTION
      "When this object is set to OFF by the management console, the 
       agent starts sending the unmasked traps related to this module. 
       Otherwise, no traps are sent by this module."
	   ::= { prtMMEntry 7 }



--
--RADRing specific Ethernet port information
--

prtETTable OBJECT-TYPE
      SYNTAX SEQUENCE OF PrtETEntry
      MAX-ACCESS not-accessible
      STATUS current
      DESCRIPTION
	  "RADRing specific Ethernet port information"
      ::= { prtRR 3 }

prtETEntry OBJECT-TYPE
      SYNTAX    PrtETEntry
      MAX-ACCESS    not-accessible
      STATUS    current
      DESCRIPTION
	  "An entry in table prtETTable."
      INDEX     { prtETmdlID, prtETID }
      ::= { prtETTable 1 }
 
PrtETEntry ::=
      SEQUENCE {
	  prtETmdlID
	     Integer32,
	  prtETID
	     Integer32,
	  prtETTrapMaskEnable
	      INTEGER
		}

prtETmdlID OBJECT-TYPE
      SYNTAX  Integer32   
      MAX-ACCESS  read-only
      STATUS  current
      DESCRIPTION
      "A unique identifier of the module, (slot no.), this port is attached to."
      ::= { prtETEntry 1 }

prtETID OBJECT-TYPE
      SYNTAX  Integer32   
      MAX-ACCESS  read-only
      STATUS  current
      DESCRIPTION
      "A unique identifier of the port within its module."
      ::= { prtETEntry 2 }

prtETTrapMaskEnable OBJECT-TYPE
      SYNTAX  INTEGER {  
	   off(2),
	   on(3)
      }
      MAX-ACCESS  read-write    
      STATUS  current
      DESCRIPTION
      "When this attribute is set to OFF by the management console, the 
       agent starts sending the unmasked traps related to this port. 
       Otherwise, no traps are sent by this port."
      ::= { prtETEntry 3 }

--
-- RR Port Security Table (10.08.95)
--
prtRRSecTable OBJECT-TYPE
      SYNTAX SEQUENCE OF PrtRRSecEntry
      MAX-ACCESS not-accessible
      STATUS current
      DESCRIPTION
	  "RR Port Security Table (10.08.95)"
      ::= { prtRR 4 }

prtRRSecEntry OBJECT-TYPE
      SYNTAX    PrtRRSecEntry
      MAX-ACCESS    not-accessible
      STATUS    current
      DESCRIPTION
	  "An entry in table prtRRSecTable."
      INDEX     { prtRRSecmdlID, prtRRSecPrtID, prtRRSecID }
      ::= { prtRRSecTable 1 }
 
PrtRRSecEntry ::=
      SEQUENCE {
	  prtRRSecmdlID
	     Integer32,
	  prtRRSecPrtID
	     Integer32,
	  prtRRSecID
	     Integer32,
	  prtRRSecMask  
	     MacAddress,
	  prtRRSecPattern
	     MacAddress
	  }

prtRRSecmdlID OBJECT-TYPE  
      SYNTAX  Integer32   
      MAX-ACCESS  read-only
      STATUS  current
      DESCRIPTION
      "A unique identifier of the module,(slot no.),this port is 
       attached to."
      ::= { prtRRSecEntry 1 }

prtRRSecPrtID OBJECT-TYPE  
      SYNTAX  Integer32   
      MAX-ACCESS  read-only
      STATUS  current
      DESCRIPTION
      "A unique identifier of the port within its module."
      ::= { prtRRSecEntry 2 }

prtRRSecID OBJECT-TYPE  
      SYNTAX  Integer32   
      MAX-ACCESS  read-only
      STATUS  current
      DESCRIPTION
      "A unique identifier of the security number within the port."
      ::= { prtRRSecEntry 3 }

prtRRSecMask OBJECT-TYPE
      SYNTAX  MacAddress
      MAX-ACCESS  read-write
      STATUS  current
      DESCRIPTION
      "Mask of the allowed MAC address that can be connected through 
       this port. The security of the individual port overwrites the
       security of the segment,  the port belongs to"
      ::= { prtRRSecEntry 4 }

prtRRSecPattern   OBJECT-TYPE
      SYNTAX  MacAddress
      MAX-ACCESS  read-write
      STATUS  current
      DESCRIPTION
      "A six-octet(48 bit) pattern, where the masked bits of 
       prtRRSecMask	should match the MAC address."
      ::= { prtRRSecEntry 5}
	









































-- 
-- file :v:\doc\rdv\mib\Before~1\fdx.txt
-- 


--Title:    FDX   MIB
--Version:   2.1...
--Date:   16.10.94              
--By:        Dan.R.
--File:       FDX.TXT

--Comments: The FDX agent also supports the following Public MIBs:
--              MIB-II (RFC1213)
--              FDDI MIB (RFC  1285)
--       relevant parts of Lannet-60 MIB.

-- the RAD Station Group
-- Implementation of the Station group is current
-- for all manageable systems which support RAD Stations


radFddiStation OBJECT IDENTIFIER ::= { radFddi 1 }

radFddiStationsNumber  OBJECT-TYPE
      SYNTAX  Integer32 (0..65535)      
      MAX-ACCESS  read-only
      STATUS  current
      DESCRIPTION
      "The number of manageable Stations implemented in the box."
      ::= { radFddiStation 1 }
      
-- the FDDI concentrator table

radFddiStationTable OBJECT-TYPE
      SYNTAX  SEQUENCE OF RadFddiStationEntry
      MAX-ACCESS  not-accessible
      STATUS current
      DESCRIPTION
      "A list of FddiStation entries. The number of entries is 
      given by the value of radFddiStationsNumber. "
      ::= { radFddiStation 2 }

radFddiStationEntry OBJECT-TYPE
      SYNTAX  RadFddiStationEntry
      MAX-ACCESS  not-accessible
      STATUS  current
      DESCRIPTION
	  "An entry in table radFddiStationTable."
      INDEX   { radFddiStationIndex }
      ::= { radFddiStationTable 1 }

RadFddiStationEntry ::=
   SEQUENCE {
      radFddiStationIndex
	 Integer32,
      radFddiStationType
	 INTEGER,
      radFddiStationBus1TestResult
	 INTEGER,
      radFddiStationBus2TestResult
	 INTEGER,
      radFddiStationTempDeInsertAction
	 INTEGER,
      radFddiStationPerformTest
	 INTEGER,
      radFddiStationOpticalSwitchStatus  -- was radFddiStationOpticalSwitchBypass
	 INTEGER
 }

 
radFddiStationIndex OBJECT-TYPE  
      SYNTAX  Integer32 (1..65535)
      MAX-ACCESS  read-only 
      STATUS  current
      DESCRIPTION
      "A unique value for each Station. Its value ranges 
      between 1 and the value ofradFddiStationNumber."
      ::= { radFddiStationEntry 1 }



radFddiStationType OBJECT-TYPE  
      SYNTAX  INTEGER {
	other(1),
	singleAttachedStation(2),
	dualAttachedStation(3),
	singleAttachedConcentrator(4),
	dualAttachedConcentrator(5),
	nullAttachedConcentrator(6)
      }
      MAX-ACCESS  read-only
      STATUS  current
      DESCRIPTION
      " Indicates the type of the station." 
      ::= { radFddiStationEntry 2 }


radFddiStationBus1TestResult OBJECT-TYPE  
      SYNTAX  INTEGER {
	ok(1),
	faulty(2)
      }
      MAX-ACCESS  read-only
      STATUS  current
      DESCRIPTION
      " Indicates the result of a test performed on Bus1." 
      ::= { radFddiStationEntry 3 }


radFddiStationBus2TestResult OBJECT-TYPE  
      SYNTAX  INTEGER {
	ok(1),
	faulty(2)
      }
      MAX-ACCESS  read-only
      STATUS  current
      DESCRIPTION
      " Indicates the result of a test performed on Bus2." 
      ::= { radFddiStationEntry 4 }



radFddiStationTempDeInsertAction OBJECT-TYPE  
      SYNTAX  INTEGER 
      MAX-ACCESS  read-write
      STATUS  current
      DESCRIPTION
      "This action provides temporary deinsertion of the root
      station from the ring. Expressed in milliseconds."
      ::= { radFddiStationEntry 5 }



radFddiStationPerformTest OBJECT-TYPE  
      SYNTAX  INTEGER {
	on(1),
	off(2) 
      }
      MAX-ACCESS  read-write
      STATUS  current
      DESCRIPTION
      "A value ON of this attribute indicates that a test should be 
      performed upon the Station." 
      ::= { radFddiStationEntry 6 }


radFddiStationOpticalSwitchStatus OBJECT-TYPE
      SYNTAX  INTEGER {
	on(1),
	off(2),
	notSupported(255) 
      }
      MAX-ACCESS  read-only
      STATUS  current
      DESCRIPTION
      "A value ON of this attribute indicates that the Station 
      is in bypass mode." 
      ::= { radFddiStationEntry 7 }



-- the RAD FDDI SMT table



radFddiSMTTable OBJECT-TYPE
      SYNTAX  SEQUENCE OF RadFddiSMTEntry
      MAX-ACCESS  not-accessible
      STATUS current
      DESCRIPTION
      "A list of FddiSMT entries. The number of entries is 
      given by the value of snmpFddiSMTNumber. "
      ::= { radFddi 2 }


radFddiSMTEntry OBJECT-TYPE
      SYNTAX  RadFddiSMTEntry
      MAX-ACCESS  not-accessible
      STATUS  current
      DESCRIPTION
	  "An entry in table radFddiSMTTable."
      INDEX   { radFddiSMTIndex }
      ::= { radFddiSMTTable 1 }


RadFddiSMTEntry ::=
   SEQUENCE {
      radFddiSMTIndex
	 Integer32,
      radFddiSMTStation
	 Integer32,
      radFddiSMTCFState
	 INTEGER,
      radFddiSMTLeftSlot
	 Integer32,
      radFddiSMTRightSlot
	 Integer32
      }
	
radFddiSMTIndex OBJECT-TYPE  
      SYNTAX  Integer32 (1..65535)
      MAX-ACCESS  read-only 
      STATUS  current
      DESCRIPTION
      "A unique value for each SMT. Its value ranges 
      between 1 and the value of snmpFddiSMTNumber."
      ::= { radFddiSMTEntry 1 }



radFddiSMTStation OBJECT-TYPE  
      SYNTAX  Integer32 (1..65535)
      MAX-ACCESS  read-only 
      STATUS  current
      DESCRIPTION
      "Indicates the Station inside the box to which the
      current SMT belongs. Its value ranges 
      between 1 and the value of radFddiStationNumber."
      ::= { radFddiSMTEntry 2 }



radFddiSMTCFState OBJECT-TYPE  
      SYNTAX  INTEGER {
	isolated(1),
	localA(2),
	localB(3),
	localAB(4),
	localS(5),
	wrapA(6),
	wrapB(7),
	wrapAB(8),
	wrapS(9),
	cWrapA(10),
	cWrapB(11),
	cWrapS(12),
	thru(13)
      }      
      MAX-ACCESS  read-only 
      STATUS  obsolete
      DESCRIPTION
      "The attachement configuration for the Station. Extends the
      range of values provided by the SNMP variable snmpFddiSMTCFState
      from the SNMP FDDI MIB."
      ::= { radFddiSMTEntry 3 }



radFddiSMTLeftSlot OBJECT-TYPE
	SYNTAX  Integer32
	MAX-ACCESS  read-only
	STATUS  current
	DESCRIPTION
	"Indicates the slot number of the leftmost card on the concentrator
	implemented inside the box and managed by the agent MAC."
	::= { radFddiSMTEntry 4 }



radFddiSMTRightSlot OBJECT-TYPE
	SYNTAX  Integer32
	MAX-ACCESS  read-only
	STATUS  current
	DESCRIPTION
	"Indicates the slot number of the rightmost card on the concentrator
	implemented inside the box and managed by the agent MAC. Note that
	the MAC-agent card itself is not taken into consideration."
	::= { radFddiSMTEntry 5 }



-- the RAD FDDI MAC table



radFddiMACTable OBJECT-TYPE
      SYNTAX  SEQUENCE OF RadFddiMACEntry
      MAX-ACCESS  not-accessible
      STATUS current
      DESCRIPTION
      "A list of FddiMAC entries. The number of entries is 
      given by the value of snmpFddiMACNumber. "
      ::= { radFddi 3 }



radFddiMACEntry OBJECT-TYPE
      SYNTAX  RadFddiMACEntry
      MAX-ACCESS  not-accessible
      STATUS  current
      DESCRIPTION
	  "An entry in table radFddiMACTable."
      INDEX   { radFddiMACSMTIndex, radFddiMACIndex }
      ::= { radFddiMACTable 1 }


RadFddiMACEntry ::=
   SEQUENCE {
      radFddiMACSMTIndex
	 Integer32,
      radFddiMACIndex
	 Integer32,
      radFddiMACStation
	 Integer32,
      radFddiMACTestResult
	 Integer32,
      radFddiMACTokenCt
	 Counter32,
      radFddiMACRingLoad
	 Integer32,            
      radFddiMACRingLoadBuffer
	 OCTET STRING,            
      radFddiMACRingLoadTrsh 
	 Integer32,
      radFddiMACRingLoadPeak 
	 Integer32,
      radFddiMACDownstreamNbr
	 OCTET STRING,
      radFddiMACRingStatus
	 INTEGER,
      radFddiMACRingUtilization
	 Integer32,
      radFddiMACRingPeakUtilization
	 Integer32
      }

 

radFddiMACSMTIndex OBJECT-TYPE  
      SYNTAX  Integer32 (1..65535)
      MAX-ACCESS  read-only 
      STATUS  current
      DESCRIPTION
      "The value of the SMT index associated with this MAC."
      ::= { radFddiMACEntry 1 }



radFddiMACIndex OBJECT-TYPE  
      SYNTAX  Integer32 (1..65535)
      MAX-ACCESS  read-only 
      STATUS  current
      DESCRIPTION
      "A unique value for each MAC. Its value ranges 
      between 1 and the value of snmpFddiMACNumber."
      ::= { radFddiMACEntry 2 }


radFddiMACStation OBJECT-TYPE  
      SYNTAX  Integer32 (1..65535)
      MAX-ACCESS  read-only 
      STATUS  current
      DESCRIPTION
      "Indicates the Station inside the box to which the
      current MAC belongs. Its value ranges 
      between 1 and the value of radFddiStationNumber."
      ::= { radFddiMACEntry 3 }

radFddiMACTestResult OBJECT-TYPE  
      SYNTAX  Integer32 
      MAX-ACCESS  read-only
      STATUS  current
      DESCRIPTION
      " Indicates the result of a test performed on MAC.
      The value is a sum. It takes the value 0 if the result of the
      test is OK and if faults occur, 2 raised to a power is added 
      to the sum. The powers are according to the following table:
	     Fault       Power
      cardConfigError     0
      GeneralError        1
      MACError            2 "
      ::= { radFddiMACEntry 4 }

radFddiMACTokenCt OBJECT-TYPE
      SYNTAX Counter32
      MAX-ACCESS read-only
      STATUS current
      DESCRIPTION
      "Token Counts - Refer to ANSI MAC {73}."
      ::= { radFddiMACEntry 5 }
      
radFddiMACRingLoad OBJECT-TYPE 
      SYNTAX  Integer32             
      MAX-ACCESS  read-only
      STATUS  current
      DESCRIPTION
      "Current traffic value. The
       traffic is expressed in percents of the maximum FDDI traffic 
       in the range 1..20, expressed on a log(10) 
      scale ( value = 10*log10(percent) )."
      ::= { radFddiMACEntry 6 }

radFddiMACRingLoadBuffer OBJECT-TYPE
      SYNTAX  OCTET STRING
      MAX-ACCESS  read-only
      STATUS  current
      DESCRIPTION
      "Record of traffic for the last second with a resolution of 100 msec. The
       traffic is expressed in percents of the maximum FDDI traffic and each
      record contains 10 readings, in the range 1..20, expressed on a log(10) 
      scale ( value = 10*log10(percent) )."
      ::= { radFddiMACEntry 7 }

radFddiMACRingLoadTrsh OBJECT-TYPE 
      SYNTAX  Integer32               
      MAX-ACCESS  read-write
      STATUS  current
      DESCRIPTION
      "Traffic threshold value. When exceeded, a trap is send to the management
      console. Expressed in percents of the maximum FDDI traffic, in the 
      range 1..20, expressed on a log(10) scale."
      ::= { radFddiMACEntry 8 }

radFddiMACRingLoadPeak OBJECT-TYPE 
      SYNTAX  Integer32              
      MAX-ACCESS  read-only
      STATUS  current
      DESCRIPTION
      "Maximal traffic value since last reset of hub or relay. Expressed in per-
      cents of the maximum FDDI traffic, in the range 1..20, 
      expressed on log(10) scale."
      ::= { radFddiMACEntry 9 }

radFddiMACDownstreamNbr OBJECT-TYPE 
      SYNTAX  OCTET STRING  (SIZE (6))             
      MAX-ACCESS  read-only
      STATUS  current
      DESCRIPTION
      "The MAC's downstream neighbor's long individual MAC address. The value
      shall be reported as '00 00 00 00 00 00' if it is unknown."
      ::= { radFddiMACEntry 10 }

radFddiMACRingStatus OBJECT-TYPE 
      SYNTAX  INTEGER {
	ringUp(1),
	ringDown(2)
      }      
      MAX-ACCESS  read-only
      STATUS  current
      DESCRIPTION
      "Attribute which summs the status of the ring controlled by the current
      MAC."
      ::= { radFddiMACEntry 11 }

radFddiMACRingUtilization OBJECT-TYPE
     SYNTAX  Integer32
     MAX-ACCESS  read-only
     STATUS  current
     DESCRIPTION
     "Current traffic value. The traffic is expressed in percents of the maximum FDDI traffic." 
      ::= { radFddiMACEntry 12 }

radFddiMACRingPeakUtilization OBJECT-TYPE
     SYNTAX  Integer32
     MAX-ACCESS  read-only
     STATUS  current
     DESCRIPTION
     "Peak traffic value since las reset of the hub or relay. The traffic is expressed
     in percents of the maximum FDDI traffic." 
      ::= { radFddiMACEntry 13 }

-- the RAD FDDI Group table

radFddiGroupTable OBJECT-TYPE
      SYNTAX  SEQUENCE OF RadFddiGroupEntry
      MAX-ACCESS  not-accessible
      STATUS current
      DESCRIPTION
      "A list of FddiGroup entries. The number of entries is 
      given by the value of snmpFddiGroupNumber. "
      ::= { radFddi 4 }

radFddiGroupEntry OBJECT-TYPE
      SYNTAX  RadFddiGroupEntry
      MAX-ACCESS  not-accessible
      STATUS  current
      DESCRIPTION
	  "An entry in table radFddiGroupTable."
      INDEX   { radFddiGroupId }
      ::= { radFddiGroupTable 1 }

RadFddiGroupEntry ::=
   SEQUENCE {
      radFddiGroupId                    
	 Integer32,
      radFddiGroupRedundancy
	 INTEGER,
      radFddiGroupTopologyMode
	 INTEGER,
      radFddiGroupTestResult
	 INTEGER,
      radFddiGroupConfigStatus
	 INTEGER,
      radFddiGroupAutoRightLoop
	 INTEGER,
      radFddiGroupAutoLeftLoop
	 INTEGER,
      radFddiGroupManRightLoop
	 INTEGER,
      radFddiGroupManLeftLoop
	 INTEGER,
      radFddiGroupOpticalSwitchStatus
	 INTEGER
      }
      
radFddiGroupId OBJECT-TYPE  
      SYNTAX  Integer32         
      MAX-ACCESS  read-only
      STATUS  current
      DESCRIPTION
      "Unique ID of the group in radFddiGroupTable. Equivalent to slot number 
      in enclosures."
      ::= { radFddiGroupEntry 1 }

radFddiGroupRedundancy OBJECT-TYPE
      SYNTAX  INTEGER {
	none(1),
	double-bandwidth(2),
	backup(3)
	}
      MAX-ACCESS  read-write
      STATUS  current
      DESCRIPTION
      "This attribute shows the usage of the A/B pair of ports in Tree mode.
      If the redundancy conditions are not fulfilled, value none(1) will be
      returned.
      If backup mode port A is a standby backup of port B, otherwise each of
      them is connected to a separate bus."
      ::= { radFddiGroupEntry 2 }

radFddiGroupTopologyMode OBJECT-TYPE
      SYNTAX  INTEGER {
	none(1), 
	tree(2),
	ring(3)
	}
      MAX-ACCESS  read-only
      STATUS  current
      DESCRIPTION
      "Defines the topology mode of the FDDI PHY card."
      ::= { radFddiGroupEntry 3 }

radFddiGroupTestResult OBJECT-TYPE  
      SYNTAX  INTEGER {
	ok(1),
	faulty(2)
      }
      MAX-ACCESS  read-only
      STATUS  current
      DESCRIPTION
      "Result of test performed upon an FDDI group. A value of faulty (1)
      indicates a CPU or communication at module level."
      ::= { radFddiGroupEntry 4 }

radFddiGroupConfigStatus OBJECT-TYPE  
      SYNTAX  INTEGER {
	ok(1),
	cardConfigErrorAB(2),
	cardConfigErrorS(3),
	switchTopologyError(4)
      } 
      MAX-ACCESS  read-only
      STATUS  current
      DESCRIPTION
      " Indicates the configuration status of the module (group)."
      ::= { radFddiGroupEntry 5 }

radFddiGroupAutoRightLoop OBJECT-TYPE 
      SYNTAX  INTEGER {
	on(1),
	off(2) 
      }
      MAX-ACCESS  read-only
      STATUS  current
     DESCRIPTION
     "Value ON of this attribute signifies that a hardware loop was 
      automatically created on a FDDI module which does not sense 
      the existence of another FDDI group on the right hand side."
      ::= { radFddiGroupEntry 6 }

radFddiGroupAutoLeftLoop OBJECT-TYPE 
      SYNTAX  INTEGER {
	on(1),
	off(2) 
      }
      MAX-ACCESS  read-only
      STATUS  current
     DESCRIPTION
     "Value ON of this attribute signifies that a hardware loop was 
      automatically created on a FDDI module which does not sense 
      the existence of another FDDI group on the left hand side."
      ::= { radFddiGroupEntry 7 }


radFddiGroupManRightLoop OBJECT-TYPE 
      SYNTAX  INTEGER {
	on(1),
	off(2) 
      }
      MAX-ACCESS  read-write
      STATUS  current
     DESCRIPTION
     "Setting this attribute to ON signifies a command to the hardware 
     to create a loop on the FDDI module which isolates the ring
     from the right hand side."
      ::= { radFddiGroupEntry 8 }

radFddiGroupManLeftLoop OBJECT-TYPE 
      SYNTAX  INTEGER {
	on(1),
	off(2) 
      }
      MAX-ACCESS  read-write
      STATUS  current
     DESCRIPTION
     "Setting this attribute to ON signifies a command to the hardware 
     to create a loop on the FDDI module which isolates the ring
     from the left hand side."
      ::= { radFddiGroupEntry 9 }


radFddiGroupOpticalSwitchStatus OBJECT-TYPE  
      SYNTAX  INTEGER {
	not-present(1),
	inserted(2),
	not-inserted(3),
	present(4)
      }
      MAX-ACCESS  read-only
      STATUS  current
      DESCRIPTION
      "This attribute describes the presence of the optical switch
      and for existing optical switches describes the possibility of 
      auto-reconfiguration of path resources (MACs and
      M-ports) in the case of bus fault or connection
      disabling. If merge(2), resources will try to move 
      to another bus, if non-merge(1) resources are left
      on their dedicated bus."
      ::= { radFddiGroupEntry 10 }




radFddiPortTable OBJECT-TYPE
      SYNTAX SEQUENCE OF RadFddiPortEntry
      MAX-ACCESS not-accessible
      STATUS current 
	  DESCRIPTION
	  "."
      ::= { radFddi 5 }


radFddiPortEntry OBJECT-TYPE
      SYNTAX  RadFddiPortEntry
      MAX-ACCESS  not-accessible
      STATUS  current
      DESCRIPTION
	  "An entry in table radFddiPortTable."
      INDEX   { radFddiPortGroupID, radFddiPortID }
      ::= { radFddiPortTable 1 }

RadFddiPortEntry ::= SEQUENCE {
      radFddiPortGroupID
	 Integer32,
      radFddiPortID  
	 Integer32,
      radFddiPortTestResult
	 INTEGER,
      radFddiPortNumberOfConnectedStations
	 Integer32,
      radFddiPortConnectedStations
	 OCTET STRING,
      radFddiPortCurrentPath
	 INTEGER,
      radFddiPortFunctionalStatus
	 INTEGER
      }

radFddiPortGroupID OBJECT-TYPE
      SYNTAX  Integer32
      MAX-ACCESS  read-only
      STATUS  current
      DESCRIPTION
      "ID of group to which the FDDI card belongs."
      ::= { radFddiPortEntry 1 }

radFddiPortID OBJECT-TYPE   
      SYNTAX  Integer32
      MAX-ACCESS  read-only
      STATUS  current
      DESCRIPTION
      "Unique Id of the port in the radFddiPortEntry."
      ::= { radFddiPortEntry 2 }

radFddiPortTestResult OBJECT-TYPE  
      SYNTAX  INTEGER {
	ok(1),
	faulty(2)
      }
      MAX-ACCESS  read-only
      STATUS  current
      DESCRIPTION
      "Indicates the result of a test performed on a port." 
      ::= { radFddiPortEntry 4 }

radFddiPortNumberOfConnectedStations OBJECT-TYPE  
      SYNTAX  Integer32 
      MAX-ACCESS  read-only
      STATUS  current
      DESCRIPTION
      "Number of stations connected to the port." 
      ::= { radFddiPortEntry 5 }

radFddiPortConnectedStations OBJECT-TYPE  
      SYNTAX  OCTET STRING 
      MAX-ACCESS  read-only
      STATUS  current
      DESCRIPTION
      "This attribute displays the configuration of the stations connected 
      to the port.The FDDI addresses of the stations are displayed in ring 
      order, starting with the address of the first station connected to the
      port. The length of the string is equal to the value of
      radFddiPortNumberOfConnectedStations multiplied by 8 (length of
      FddiSMTStationIdType)." 
      ::= { radFddiPortEntry 6 }

radFddiPortCurrentPath OBJECT-TYPE
      SYNTAX INTEGER{
	isolated(1),
	local(2),
	secondary(3),
	primary(4),
	concatenated(5),
	thru(6)
	}
      MAX-ACCESS read-write
      STATUS obsolete 
      DESCRIPTION
      "Current Path in FDDI port on PHY cards."
      ::= { radFddiPortEntry 8 }
      
radFddiPortFunctionalStatus OBJECT-TYPE
      SYNTAX INTEGER{
	ok(1),
	lerAlarm(2),
	lerCutoff(3)
	}
      MAX-ACCESS read-write
      STATUS current
      DESCRIPTION
      "Fubctional status of the port according to value of link error
      estimate relative to thresholds of alarm and cutoff."
      ::= { radFddiPortEntry 9 }
      

radFddiAgn OBJECT IDENTIFIER ::= { radFddi 6 }

-- the RAD Agent Group
-- Implementation of the Agent group is current
-- for all manageable systems which support RAD Stations     
      
radFddiAgnPriSwDesc  OBJECT-TYPE    
      SYNTAX  DisplayString
      MAX-ACCESS  read-only
      STATUS  current
      DESCRIPTION
      "ASCII string for description and display of the Fddi agent software version."
      ::= { radFddiAgn 1 }



















-- 
-- file :v:\doc\rdv\mib\ver485\brggen.txt
-- 
  

--Version:   4.0
--Date:   16.10.94              
--By:       Debby Koren &  Orly Nicklass
--File:       BRGgen.txt

--Last Updated by Ilana Schvetz 09-Jan-2002.

genBridge      OBJECT IDENTIFIER ::= {radBridges 1 }

-- At the end of the MIB there is a definition of all RAD general traps for bridges. 

radBridgeAction OBJECT-TYPE
    SYNTAX  INTEGER {
       reset(1),
       sendNetworkTab(2),
       deleteNetworkTab(3),
       sendRoutingTab(4),    -- Level II
       deleteRoutinTab(5),
       sendLanTab(6),
       deleteLanTab(7),
       deleteArpTab(8),
       sendArpTab(9),
       deleteRouteTab(10),   -- Level III
       sendRouteTab(11),
       deactivateAllMasks(12),
       saveAllActiveMasks(13),
       loadAndActivateAllMasksFromNVRAM(14),
       clearAllMasksFromNVRAM(15),
	   defaultConfig(16),
	   resetNVRAM(17),
	   clearIPNVRAM(18),
	noOp(255)
     }
    MAX-ACCESS  read-write
    STATUS  current
    DESCRIPTION
	"This variable enables the operator to perform one of the
	specified actions on the tables maintained by the network device.
	Send actions are not currently implemented.  Not all actions can 
	be performed on all bridges."
   ::= { genBridge 1  }

radBridgeInactiveArpTimeOut OBJECT-TYPE
    SYNTAX Integer32
    MAX-ACCESS  read-write
    STATUS  current
    DESCRIPTION
	"This variable defines the maximum time period that can pass
	between ARP requests concerning an entry in the ARP table.
	After this time period, the entry is deleted from the table."
    ::= { genBridge 2  }


-- radBridgeMaskTab defines the format of  RAD Bridge OLD masking tables

radBridgeMaskTable    OBJECT-TYPE
    SYNTAX  SEQUENCE  OF RadBridgeMaskEntry
    MAX-ACCESS  not-accessible
    STATUS  current
    DESCRIPTION
	"Mask tables enable definition of forwarding restrictions and 
	control of message flow in the internetwork. Each entry
	in this table defines a mask statement consisting of up to 
	three mask definitions and an action defined by 
	radBridgeMaskOper. Different types of mask entries are supported, 
	as defined by radBridgeMaskType."
    ::=  { genBridge 3 }

radBridgeMaskEntry OBJECT-TYPE
    SYNTAX  RadBridgeMaskEntry
    MAX-ACCESS  not-accessible
    STATUS  current
    DESCRIPTION
    "An entry in table radBridgeMaskTable."
    INDEX   { radBridgeMaskType, radBridgeMaskIfIndex, radBridgeMaskNum  }
    ::=  { radBridgeMaskTable 1  }

RadBridgeMaskEntry ::= SEQUENCE {
    radBridgeMaskType
     INTEGER,
    radBridgeMaskIfIndex
     Integer32,   
    radBridgeMaskNum
     Integer32,
    radBridgeMaskDest
     INTEGER,
    radBridgeMaskPat1
     OCTET STRING,
    radBridgeMaskActiveBit1
     OCTET STRING,
    radBridgeMaskFrom1
     INTEGER,
    radBridgeMaskOffset1
     Integer32,
    radBridgeMaskCond1
     INTEGER,
    radBridgeMaskPat2
     OCTET STRING,
    radBridgeMaskActiveBit2
     OCTET STRING,
    radBridgeMaskFrom2
     INTEGER,
    radBridgeMaskOffset2
     Integer32,
    radBridgeMaskCond2
     INTEGER,
    radBridgeMaskPat3
     OCTET STRING,
    radBridgeMaskActiveBit3
     OCTET STRING,
    radBridgeMaskFrom3
     INTEGER,
    radBridgeMaskOffset3
     Integer32,
    radBridgeMaskCond3
     INTEGER,
    radBridgeMaskOper
     INTEGER
    }

radBridgeMaskType  OBJECT-TYPE
    SYNTAX INTEGER {
       tx(1),
       rx(2),
       compress(3),
       priority(4),
       loadSharing(5),
       facs(6),
       codConnect(7),
	   codDisconnect(8)
      }
    MAX-ACCESS  read-write
    STATUS  current
    DESCRIPTION
	"Defines the type of mask entry."
    ::= { radBridgeMaskEntry 1  }

radBridgeMaskIfIndex  OBJECT-TYPE
    SYNTAX Integer32
    MAX-ACCESS  read-write
    STATUS  current
    DESCRIPTION 
	"Specifies the if Index of the interface to which the mask is applied."
   ::= { radBridgeMaskEntry 2  }

radBridgeMaskNum  OBJECT-TYPE
    SYNTAX Integer32
    MAX-ACCESS  read-write
    STATUS  current
    DESCRIPTION
	"The Mask entry number, defined by its line number in the mask
	table."
   ::= {  radBridgeMaskEntry 3  }

radBridgeMaskDest  OBJECT-TYPE
    SYNTAX INTEGER {
       unassigned-cond (1),
       broadcast-msge (2),
       multicast-msge (3),
       all-msge(4),
   none(5)
    }

    MAX-ACCESS  read-write
    STATUS  current
    DESCRIPTION 
	"Specifies the type of destination address carried by the frame
	to which the mask will be applied. Unassigned-condition 
	deactivates the mask entry."
    ::= {  radBridgeMaskEntry 4   }


radBridgeMaskPat1 OBJECT-TYPE
    SYNTAX OCTET STRING  -- (SIZE (2))
    MAX-ACCESS  read-write
    STATUS  current
    DESCRIPTION
	"Describes the mask field which is either a 16 bit binary pattern,
	or four digit hexadecimal pattern."
    ::= { radBridgeMaskEntry 5  }

radBridgeMaskActiveBit1  OBJECT-TYPE
    SYNTAX OCTET STRING  -- (SIZE (2))
    MAX-ACCESS  read-write
    STATUS  current
    DESCRIPTION
	"Specifies the positions of the wild card characters (*) 
	in the radBridgeMaskPat1 field."
    ::= { radBridgeMaskEntry 6  }

radBridgeMaskFrom1  OBJECT-TYPE
    SYNTAX INTEGER {
       mac(1),
       llc(2),
	   net(3)
    }
    MAX-ACCESS  read-write
    STATUS  current
    DESCRIPTION
	"Offset base of radBridgeMaskPat1 within the frame.
	 Net can be in some cases the data start point."
    ::= { radBridgeMaskEntry 7  }

radBridgeMaskOffset1  OBJECT-TYPE
    SYNTAX Integer32
    MAX-ACCESS  read-write
    STATUS  current
    DESCRIPTION
	"Specifies the radBridgeMaskPat1 offset within the frame (in bytes) from 
	the base defined in by radBridgeMaskForm1.The mask offset is an even
	decimal number in the range of 0 to 1518." 
    ::= { radBridgeMaskEntry 8  }

radBridgeMaskCond1 OBJECT-TYPE
    SYNTAX INTEGER {
       false (1),
       true (2)
    }
    MAX-ACCESS  read-write
    STATUS  current
    DESCRIPTION
	"Specifies the logical condition of the mask pattern:

	true  - Condition is valid if at the position specified by 
		radBridgeMaskOffset1 the packet contains data that matches
		the content of radBridgeMaskPat1.

	false - Condition is valid if at the position specified by 
		radBridgeMaskOffset1 the packet contains data that does not
		match the content of radBridgeMaskPat1."
    ::= {  radBridgeMaskEntry 9  }

radBridgeMaskPat2  OBJECT-TYPE
    SYNTAX OCTET STRING  --   (SIZE (2))
    MAX-ACCESS  read-write
    STATUS  current
    DESCRIPTION
	"Describes the mask field which is either a 16 bit binary pattern,
	 or four digit hexadecimal pattern."
    ::= {  radBridgeMaskEntry 10  }

radBridgeMaskActiveBit2  OBJECT-TYPE
    SYNTAX OCTET STRING  --   (SIZE (2))
    MAX-ACCESS  read-write
    STATUS  current
    DESCRIPTION
	"Specifies the positions of the wild card characters (*) 
	in the radBridgeMaskPat2 field."
    ::= {  radBridgeMaskEntry 11  }

radBridgeMaskFrom2  OBJECT-TYPE
    SYNTAX INTEGER { 
       mac (1),
       llc (2),
	   net(3)
    }
    MAX-ACCESS  read-write
    STATUS  current
    DESCRIPTION
	"Offset base of radBridgeMaskPat2 within the frame.
	 Net can be in some cases the data start point."
    ::= {  radBridgeMaskEntry 12  }

radBridgeMaskOffset2  OBJECT-TYPE
    SYNTAX Integer32
    MAX-ACCESS  read-write
    STATUS  current
    DESCRIPTION
	"Specifies the radBridgeMaskPat2 offset within the frame (in bytes) from 
	the base defined in by radBridgeMaskForm2.The mask offset is an even
	decimal number in the range of 0 to 1518." 
    ::= {  radBridgeMaskEntry 13  }

radBridgeMaskCond2 OBJECT-TYPE
    SYNTAX INTEGER { 
       false (1),
       true (2)
    }
    MAX-ACCESS  read-write
    STATUS  current
    DESCRIPTION
	"Specifies the logical condition of the mask pattern:

	true  - Condition is valid if at the position specified by 
		radBridgeMaskOffset2 the packet contains data that matches
		the content of radBridgeMaskPat2.

	false - Condition is valid if at the position specified by 
		radBridgeMaskOffset2 the packet contains data that does not
		match the content of radBridgeMaskPat2."
    ::= {  radBridgeMaskEntry 14  }

radBridgeMaskPat3 OBJECT-TYPE
    SYNTAX OCTET STRING  --   (SIZE (2))
    MAX-ACCESS  read-write
    STATUS  current
    DESCRIPTION
	"Describes the mask field which is either a 16 bit binary pattern,
	or four digit hexadecimal pattern."
    ::= {  radBridgeMaskEntry 15  }

radBridgeMaskActiveBit3 OBJECT-TYPE
    SYNTAX OCTET STRING  --   (SIZE (2))
    MAX-ACCESS  read-write
    STATUS  current
    DESCRIPTION
	"Specifies the positions of the wild card characters (*) 
	in the radBridgeMaskPat3 field."
    ::= {  radBridgeMaskEntry 16  }

radBridgeMaskFrom3 OBJECT-TYPE
    SYNTAX INTEGER { 
       mac (1),
       llc (2),
	   net (3)
    }
    MAX-ACCESS  read-write
    STATUS  current
    DESCRIPTION
	"Offset base of radBridgeMaskPat3 within the frame.
	 Net can be in some cases the data start point."
    ::= {  radBridgeMaskEntry 17  }

radBridgeMaskOffset3 OBJECT-TYPE
    SYNTAX Integer32
    MAX-ACCESS  read-write
    STATUS  current
    DESCRIPTION
	"Specifies the radBridgeMaskPat3 offset within the frame (in bytes) from 
	the base defined in by radBridgeMaskForm3. The mask offset is an even
	decimal number in the range of 0 to 1518." 
    ::= {  radBridgeMaskEntry 18  }

radBridgeMaskCond3 OBJECT-TYPE
   SYNTAX INTEGER { 
       false (1),
       true (2)
    }
    MAX-ACCESS  read-write
    STATUS  current
    DESCRIPTION
	"Specifies the logical condition of the mask pattern:

	true  - Condition is valid if at the position specified by 
		radBridgeMaskOffset3 the packet contains data that matches
		the content of radBridgeMaskPat3

	false - Condition is valid if at the position specified by 
		radBridgeMaskOffset3 the packet contains data that does not
		match the content of radBridgeMaskPat3."
    ::= {  radBridgeMaskEntry 19  }

radBridgeMaskOper OBJECT-TYPE
    SYNTAX INTEGER { 
       block (1),
       forward (2),
       route (3),
       forward-route (4),
       high-priority (5),
       noOp(6),
       delete(7)
     }
   
   
    MAX-ACCESS read-write
    STATUS current
    DESCRIPTION
	"The type of action to be taken if the frame meets the 
     conditions of the mask.
     noOp = disabled (mask remains on list, but is not active) 
	 delete = mask is removed from the list. "
    ::= {  radBridgeMaskEntry 20 }

radBridgeCOD      OBJECT IDENTIFIER ::= {genBridge 4 }

radBridgeCODParamTable OBJECT-TYPE
	SYNTAX  SEQUENCE OF RadBridgeCODEntry
	MAX-ACCESS  not-accessible
	STATUS  current
	DESCRIPTION
	       "The table of COD parameters "
	::= { radBridgeCOD 1}


radBridgeCODEntry OBJECT-TYPE
	SYNTAX RadBridgeCODEntry
	MAX-ACCESS  not-accessible
	STATUS  current
	DESCRIPTION
	       "Each radBridgeCODEntry consists of the following parameters"
	INDEX   {radBridgeCODIfIndex}
	::= { radBridgeCODParamTable 1 }


RadBridgeCODEntry ::= SEQUENCE {
	  radBridgeCODIfIndex
		Integer32,
	  radBridgeCODManualConnect
		INTEGER,
	  radBridgeCODMode
		INTEGER,
	  radBridgeCODConnectDelay
		Integer32,
	  radBridgeCODisConnectDelay
		Integer32,
	  radBridgeCODImplicitSwitch
		INTEGER,
	  radBridgeCODNumAccess
		Counter32,
	  radBridgeCODTotalConnecTime
		Integer32
 }

radBridgeCODIfIndex OBJECT-TYPE
	SYNTAX  Integer32 
	MAX-ACCESS  read-only
	STATUS  current
	DESCRIPTION
	       "The interface to which this COD entry is applicable."
	::= { radBridgeCODEntry 1 }

radBridgeCODManualConnect OBJECT-TYPE
	SYNTAX  INTEGER {
		connect(1),
		disconnect(2)
	     }
	MAX-ACCESS  read-write
	STATUS  current
	DESCRIPTION
	       "The management station can start connection manually
		by setting this parameter"
	::= { radBridgeCODEntry 2 }


radBridgeCODMode OBJECT-TYPE
	SYNTAX  INTEGER {
		answer(1),
		originate(2),
		disable(3),
	    answerAndOriginate(4)
	     }
	MAX-ACCESS  read-write
	STATUS  current
	DESCRIPTION
	     "In answer mode only one incoming call may be accepted at a time. Other nodes
	      attempting to access the local modem will receive a busy signal until the
	      connection is terminated. (Answer mode has no difficulty supporting multiple
	      remote connections to one local port, as blocking multiple incoming calls is
	      just a modem function. Originate mode, on the other
	      hand will only support a single local port to remote port connection).
	      The disable parameter disables the COD utility for this interface. 
	      Choosing any other mode will enable the COD utility."
	::= { radBridgeCODEntry 3 }

radBridgeCODConnectDelay OBJECT-TYPE
	SYNTAX  Integer32
	MAX-ACCESS  read-write
	STATUS  current
	DESCRIPTION
     "The connect delay defines the minimum time period that 
      the link must stay disconnected, between 2 succesive 
      connections (in seconds)."
	::= { radBridgeCODEntry 4 }

radBridgeCODisConnectDelay OBJECT-TYPE
	SYNTAX  Integer32
	MAX-ACCESS  read-write
	STATUS  current
	DESCRIPTION
		"The disconnect delay defines the minimum time period
		 the link must stay connected, between 2 succesive
		 disconnections (in seconds)."
	::= { radBridgeCODEntry 5 }


radBridgeCODImplicitSwitch  OBJECT-TYPE
	SYNTAX  INTEGER  {
	      enable(1),
	      disable(2)
	}
	MAX-ACCESS  read-write
	STATUS  current
	DESCRIPTION
	     "The inplicit switch allows the user to ignore implicit triggers  provided 
	      by the COD software."
--      DEFVAL  { 1 }
	::= { radBridgeCODEntry 6 }


radBridgeCODNumAccess  OBJECT-TYPE
	SYNTAX Counter32
	MAX-ACCESS read-only
	STATUS  current
	DESCRIPTION
	     "The number of successful connections that have been established since 
	      the COD has been reset."
	::= { radBridgeCODEntry 7}

radBridgeCODTotalConnecTime  OBJECT-TYPE
	SYNTAX Integer32
	MAX-ACCESS read-only
	STATUS  current
	DESCRIPTION
	     "The sum of all the connect time intervals since the COD was reset."
	::= { radBridgeCODEntry 8}




 
radBridgeCODTimeTriggerTable OBJECT-TYPE
	SYNTAX  SEQUENCE OF RadBridgeCODTimeTriggerEntry
	MAX-ACCESS  not-accessible
	STATUS  current
	DESCRIPTION
		     "The table of COD parameters "
	::= { radBridgeCOD 2 }

radBridgeCODTimeTriggerEntry  OBJECT-TYPE
	SYNTAX RadBridgeCODTimeTriggerEntry
	MAX-ACCESS not-accessible
	STATUS current
	DESCRIPTION
	      "Each radBridgeCODTimeTriggerEntry consists of the following parameters"
	INDEX   { radBridgeCODTimeIfIndex, radBridgeCODDay, radBridgeCODTimeTriggerNum }
	::= { radBridgeCODTimeTriggerTable 1 }

RadBridgeCODTimeTriggerEntry ::= SEQUENCE {
	radBridgeCODTimeIfIndex
	      Integer32,
	radBridgeCODDay
	      INTEGER,
	radBridgeCODTimeTriggerNum
	      Integer32,
	radBridgeCODTimeTriggerFrom
	      DisplayString,
	radBridgeCODTimeTriggerTo
	      DisplayString,
	radBridgeCODTimeTriggerStatus
	      INTEGER
	}

radBridgeCODTimeIfIndex OBJECT-TYPE
    SYNTAX Integer32
    MAX-ACCESS read-only
    STATUS current
    DESCRIPTION
	       "The interface to which this COD  Time Trigger  entry is applicable."
	    ::= { radBridgeCODTimeTriggerEntry 1}

radBridgeCODDay  OBJECT-TYPE
    SYNTAX  INTEGER {
	  mon(1),
	  tue(2),
	  wed(3),
	  thu(4),
	  fri(5),
	  sat(6),
	  sun(7)
	 }
    MAX-ACCESS read-only
    STATUS current
    DESCRIPTION
       " The  day of the week in which  the dial up connection operates."
    ::= { radBridgeCODTimeTriggerEntry 2 }

radBridgeCODTimeTriggerNum  OBJECT-TYPE
    SYNTAX  Integer32  (1..3)
    MAX-ACCESS read-only
    STATUS current
    DESCRIPTION
       " Every day of the week the user can configure 3 dial up connections."
   ::= { radBridgeCODTimeTriggerEntry 3 }

radBridgeCODTimeTriggerFrom  OBJECT-TYPE
    SYNTAX DisplayString
    MAX-ACCESS read-write
    STATUS current
    DESCRIPTION
       "Time to start Dial Up connection, in format hh:mm."
    ::= {radBridgeCODTimeTriggerEntry 4 }

radBridgeCODTimeTriggerTo  OBJECT-TYPE
    SYNTAX DisplayString
    MAX-ACCESS read-write
    STATUS current
    DESCRIPTION
       "Time to terminate Dial Up connection, in format HH:MM."
 ::= {radBridgeCODTimeTriggerEntry 5 }

radBridgeCODTimeTriggerStatus OBJECT-TYPE
	     SYNTAX  INTEGER {
		  valid(1),
		  invalid(2)           
	    }
	     MAX-ACCESS  read-write
	     STATUS  current
	     DESCRIPTION
	       "The status of a table entry."
   ::= { radBridgeCODTimeTriggerEntry  6 }

radBridgeCODTraffic  OBJECT IDENTIFIER ::= { radBridgeCOD 3}

radBridgeCODTrafficTable OBJECT-TYPE
	SYNTAX  SEQUENCE OF RadBridgeCODTrafficEntry
	MAX-ACCESS  not-accessible
	STATUS  current
	DESCRIPTION
	       "The table of COD Traffic trigger "
	::= { radBridgeCODTraffic 1 }

radBridgeCODTrafficEntry OBJECT-TYPE
	SYNTAX RadBridgeCODTrafficEntry
	MAX-ACCESS  not-accessible
	STATUS  current
	DESCRIPTION
	       "Each radBridgeCODTrafficEntry consists of the following parameters."
	INDEX {radBridgeCODProtocolType}
	::= { radBridgeCODTrafficTable 1}


RadBridgeCODTrafficEntry ::= SEQUENCE {
	  radBridgeCODProtocolType
		INTEGER,
	  radBridgeCODTrafficTriggerStatus
		INTEGER }


radBridgeCODProtocolType OBJECT-TYPE
	SYNTAX INTEGER {
		ip(1),
		ipx(2),
		other(3)
}                                   
 
	MAX-ACCESS  read-write
	STATUS  current
	DESCRIPTION
		"The Protocol Type of the Traffic Table"
	::= { radBridgeCODTrafficEntry 1 }


radBridgeCODTrafficTriggerStatus OBJECT-TYPE
	SYNTAX INTEGER {
		enable(1),
		disable(2) 
}
	MAX-ACCESS  read-write
	STATUS  current
	DESCRIPTION
		"Command of Status of the Protocol Traffic Trigger"
	::= { radBridgeCODTrafficEntry 2 }


radBridgeCODRemoteIPAddr  OBJECT-TYPE
	SYNTAX IpAddress
	MAX-ACCESS  read-write
	STATUS  current
	DESCRIPTION
		" This is the Remote IP Address"
	::= { radBridgeCODTraffic 2 }


radBridgeCODIPMask  OBJECT-TYPE
	SYNTAX IpAddress
	MAX-ACCESS  read-write
	STATUS  current
	DESCRIPTION
		" This is the Mask of the Remote IP Address"
	::= { radBridgeCODTraffic 3 }

radBridgeCODTrafficTriggerProtType OBJECT-TYPE
	SYNTAX  OCTET STRING
	MAX-ACCESS  read-write
	STATUS  current
	DESCRIPTION
		"Protocol Type for the User Defined Protocol Traffic Trigger (3)."
	::= { radBridgeCODTraffic 4 }


--COD Condition table

radBridgeCODCondTable OBJECT-TYPE
	SYNTAX  SEQUENCE OF RadBridgeCODCondEntry
	MAX-ACCESS  not-accessible
	STATUS  current
	DESCRIPTION
	       "The table of COD Condition parameters "
	::= { radBridgeCOD 4}


radBridgeCODCondEntry OBJECT-TYPE
	SYNTAX RadBridgeCODCondEntry
	MAX-ACCESS  not-accessible
	STATUS  current
	DESCRIPTION
	       "Each radBridgeCODCondEntry consists of the following parameters"
	INDEX   {radBridgeCODCondIfIndex}
	::= { radBridgeCODCondTable 1 }


RadBridgeCODCondEntry ::= SEQUENCE {
	  radBridgeCODCondIfIndex 
	  	Integer32, 
	  radBridgeCODOriginateConnectCondition 
	  	INTEGER, 
	  radBridgeCODOriginateDisConnectCondition
	  	INTEGER,
	  radBridgeCODOriginateDisConnectDelay
	  	Integer32, 
	  radBridgeCODAnswerConnectCondition
	  	INTEGER, 
      radBridgeCODSpecificOnTrafficOIDCondition
        OBJECT IDENTIFIER, 
      radBridgeCODDisConnectMinimunFramesNumber
        Integer32 



  }


radBridgeCODCondIfIndex OBJECT-TYPE
	SYNTAX  Integer32 
	MAX-ACCESS  read-only
	STATUS  current
	DESCRIPTION
	"The interface, this COD entry is applicable to."
	::= { radBridgeCODCondEntry 1 }
   
radBridgeCODOriginateConnectCondition OBJECT-TYPE
	SYNTAX  INTEGER {
               onPowerOn           (1),
               whenAnyStationOnLan (2),
               onTraffic           (3),
               onManualConnect     (4)
               }
	MAX-ACCESS  read-write
	STATUS  current
	DESCRIPTION
	     " This condition, allows the user to specify the 
	       condition under which the link is connected.
           The options are
                  onPowerOn           - On power on.
                  whenAnyStationOnLan - When any station on lan.
                  onTraffic           - On traffic. The user can specify the 
                                        condition/s for connection.
                                        The connection will be defined in
                                        CODSpecificOnTrafficConditionOID .
                  onManualConnect     - depends on radBridgeCODManualConnect 
                                        OBJECT-TYPE (=connect).
                  "
	::= { radBridgeCODCondEntry 2 }
   
radBridgeCODOriginateDisConnectCondition OBJECT-TYPE
	SYNTAX  INTEGER {
               noStationOnLan                 (1),
               onTraffic                      (2),
               onDelayFromConnectionOnRequest (3),
               onManualDisConnect             (4)
               }
	MAX-ACCESS  read-write
	STATUS  current
	DESCRIPTION
	     "This condition allows the user to specify the 
	      condition under which the link is disconnected.
          The options are: 
                  noStationOnLan - When there is no station on lan.
                                   Counts 15 minutes from the point the last 
                                   frame from lan has been received. If no 
                                   frame have been transmitted on lan by the 
                                   end of this period, disconnect the connection.
                  onTraffic      - On traffic. The user can specify the 
                                   condition/s for disconnection.
                                   The disconnection will be defined in
                                   CODSpecificOnTrafficConditionOID .
                  onDelayFromConnectionOnRequest - 
                                   On Delay From Connection On Request .
                                   The delay time period will be defined in
                                   CODOriginateDisConnectDelay . 
                  onManualDisConnect - depends on radBridgeCODManualConnect 
                                    OBJECT-TYPE (=disconnect).
                  "
	::= { radBridgeCODCondEntry 3 }

radBridgeCODOriginateDisConnectDelay OBJECT-TYPE
	SYNTAX  Integer32 
	MAX-ACCESS  read-write
	STATUS  current
	DESCRIPTION
             "Delay time in seconds. "
	::= { radBridgeCODCondEntry 4 }

radBridgeCODAnswerConnectCondition OBJECT-TYPE
	SYNTAX  INTEGER {
               onPowerOn           (1),
               whenAnyStationOnLan (2),
               onTraffic           (3),
               onManualConnect     (4)
               }
	MAX-ACCESS  read-write
	STATUS  current
	DESCRIPTION
	     "CODCondAnswerConnect allows the user to specify 
	      the condition under which the link is connected.
          The options are: 
                  onPowerOn           - On power on.
                  whenAnyStationOnLan - When any station on lan.
                  onTraffic           - On traffic. The user can specify the 
                                        condition/s for connection.
                                        The connection will be defined in
                                        CODSpecificOnTrafficConditionOID .
                  onManualConnect     - depends on radBridgeCODManualConnect 
                                        OBJECT-TYPE .
             "     
	::= { radBridgeCODCondEntry 5 }


radBridgeCODSpecificOnTrafficOIDCondition OBJECT-TYPE
        SYNTAX  OBJECT IDENTIFIER
        MAX-ACCESS  read-only
        STATUS  current
        DESCRIPTION
             "A reference to a specific entry in the
			  radBridgeMaskTable, which describes the 
              particular COD condition .
              If Connect or Disconnect Conditions are not 
              onTraffic, its value should be set to the 
              OBJECT IDENTIFIER { 0 0 }. "
	::= { radBridgeCODCondEntry 6 }


radBridgeCODDisConnectMinimunFramesNumber OBJECT-TYPE
        SYNTAX Integer32
        MAX-ACCESS  read-write
        STATUS  current
        DESCRIPTION
             "Frames rate."
	::= { radBridgeCODCondEntry 7 }

--The IPX following objects define the Spoofing 

radBridgeIPX      OBJECT IDENTIFIER ::= {genBridge 5 }


radBridgeIPXdriver      OBJECT IDENTIFIER ::=  {radBridgeIPX 1 }
radBridgeIPXRip          OBJECT IDENTIFIER ::=  {radBridgeIPX 2 }
radBridgeIPXSap         OBJECT IDENTIFIER ::=  {radBridgeIPX 3 }

radBridgeIPXForwarding OBJECT-TYPE
    SYNTAX  INTEGER {
	forwarding(1),
       not-forwarding(2)
       }
    MAX-ACCESS  read-write      
    STATUS  current
    DESCRIPTION
       "The indication of whether this entity is acting as an IPX
       gateway in respect to the forwarding of datagrams received by,
       but not addressed to, this entity.  IPX gateways forward
       datagrams.  IPX hosts do not.  Note that changing this parameter 
       requiers RESET of the router."
--      DEFVAL  { 1 }
    ::= { radBridgeIPXdriver 1 }

radBridgeIPXRipOutPackets OBJECT-TYPE
    SYNTAX  Counter32
    MAX-ACCESS  read-only
    STATUS  current
    DESCRIPTION
       "The total number of packets transmitted by RIP."
    ::= { radBridgeIPXRip 1 }
    
radBridgeIPXRipInPackets OBJECT-TYPE
    SYNTAX  Counter32
    MAX-ACCESS  read-only
    STATUS  current
    DESCRIPTION
       "The total number of packets received by RIP.  This will include
       any packets that are subsequently discarded."
    ::= { radBridgeIPXRip 2 }
    
radBridgeIPXRipInDiscards OBJECT-TYPE
    SYNTAX  Counter32
    MAX-ACCESS  read-only
    STATUS  current
    DESCRIPTION
       "The number of received packets discarded by RIP."
    ::= { radBridgeIPXRip 3 }
    
radBridgeIPXRipTblNoOfEntries OBJECT-TYPE
    SYNTAX  Integer32
    MAX-ACCESS  read-only
    STATUS  current
    DESCRIPTION
       "The max number of entries that exist in the RIP routing table."
    ::= { radBridgeIPXRip 4 }
    
radBridgeIPXRipTblBcastTrigUpdateInterval OBJECT-TYPE
    SYNTAX  Integer32
    MAX-ACCESS  read-write
    STATUS  current
    DESCRIPTION
       "The default time interval (in seconds)between triggered RIP updates on 
       a broadcast type interface.  A triggered update occurs when a change is 
       detected in the routing database.  This time interval delays the 
       broadcasting of these updates so that changes on the network will 
       not result in a lot of triggered updates."
    ::= { radBridgeIPXRip 5 }
  

 
radBridgeIPXRipTable OBJECT-TYPE
    SYNTAX  SEQUENCE OF RadBridgeIPXRipTableEntry
    MAX-ACCESS  not-accessible
    STATUS  current
    DESCRIPTION
       "The routing table used by RIP to calculate routes to remote
       desination networks."
    ::= { radBridgeIPXRip 6 }
    
radBridgeIPXRipTableEntry OBJECT-TYPE
    SYNTAX  RadBridgeIPXRipTableEntry
    MAX-ACCESS  not-accessible
    STATUS  current
    DESCRIPTION
       "The routing information for one of this entity's destination networks."
    INDEX   { radBridgeIPXRipDestNetwork, 
	      radBridgeIPXRipPolicy }
    ::= { radBridgeIPXRipTable 1 }
    
RadBridgeIPXRipTableEntry ::= SEQUENCE {
radBridgeIPXRipDestNetwork
     OCTET STRING (SIZE(4)),
radBridgeIPXRipPolicy
     INTEGER,
radBridgeIPXRipForwardingRouter
     OCTET STRING (SIZE(6)),
radBridgeIPXRipNIC
     Integer32,
radBridgeIPXRipTickMetric
     Integer32,
radBridgeIPXRipHopMetric
     Integer32,
radBridgeIPXRipAgingTime
     TimeTicks,
radBridgeIPXRipValueStatus
     INTEGER,
radBridgeIPXRipForwardType
     INTEGER
}

radBridgeIPXRipDestNetwork OBJECT-TYPE
    SYNTAX  OCTET STRING (SIZE(4))
    MAX-ACCESS  read-only
    STATUS  current
    DESCRIPTION
	 "The destination network address to which this entry's
	  routing information pertains."
    ::= {radBridgeIPXRipTableEntry 1 }
    
radBridgeIPXRipPolicy OBJECT-TYPE
    SYNTAX  INTEGER  {
	main(1),
	alternate(2)
    }
    MAX-ACCESS  read-only
    STATUS  current
    DESCRIPTION
       "A value specifying the precidence of the route.  A value of
       zero means that the route is the best route, a value of one
       means that the route is the second best route and so on."
    ::= { radBridgeIPXRipTableEntry 2 }
    
radBridgeIPXRipForwardingRouter OBJECT-TYPE
    SYNTAX  OCTET STRING (SIZE(6))
    MAX-ACCESS  read-write
    STATUS  current
    DESCRIPTION
       "The IPX node address of the next hop (router) for the
       entry's associated destination network."
    ::= { radBridgeIPXRipTableEntry 3 }
    
radBridgeIPXRipNIC OBJECT-TYPE
    SYNTAX  Integer32 
    MAX-ACCESS  read-write
    STATUS  current
    DESCRIPTION
       "An interface identifier specifying what IPX interface the
       next hop can be found on."
    ::= { radBridgeIPXRipTableEntry 4 }
    
radBridgeIPXRipTickMetric OBJECT-TYPE
    SYNTAX  Integer32
    MAX-ACCESS  read-write
    STATUS  current
    DESCRIPTION
       "The metric, in terms of transit time, associated with the route
       given by the entry.  This time is in terms of 1/18ths of a
       second."
    ::= { radBridgeIPXRipTableEntry 5 }
    
radBridgeIPXRipHopMetric OBJECT-TYPE
    SYNTAX  Integer32
    MAX-ACCESS  read-write
    STATUS  current
    DESCRIPTION
       "The metric, in terms of distance , associated with the route
	given by the entry."
    ::= { radBridgeIPXRipTableEntry 6 }
    
    
radBridgeIPXRipAgingTime OBJECT-TYPE
    SYNTAX  TimeTicks
    MAX-ACCESS  read-only
    STATUS  current
    DESCRIPTION
      "The last time that the entry was updated.  The time will be
       provided in terms of the MIB-I object sysUpTime."
    ::= {radBridgeIPXRipTableEntry 7 }
    
radBridgeIPXRipValueStatus OBJECT-TYPE
    SYNTAX  INTEGER {
	static(1),
	dynamic(2),
	invalid(3),
	semiDynamic(4)
    }
    MAX-ACCESS  read-write
    STATUS  current
    DESCRIPTION
       "The entry status value; whether the entry is permanent (added
	statically), reachable or unreachable.  In the latter two cases
       it would be added by RIP. A semiDynamic entry is an entry
       enterd manualy by the user and can be updated by the router."
    ::= { radBridgeIPXRipTableEntry 8 }
    
radBridgeIPXRipForwardType  OBJECT-TYPE
    SYNTAX  INTEGER {
	 other    (1), -- not specified by this MIB
	 local    (2), -- local interface
	 remote   (3)  -- remote destination
     }
     MAX-ACCESS   read-write
     STATUS   current
     DESCRIPTION
	"The type of route. Note that local(2) refers to a route for which the 
	 next hop is the final destination; remote(3) refers to  a  route  
	 for which  the next  hop is not the final destination."
    ::= {radBridgeIPXRipTableEntry 9 }
    
	  
    
radBridgeIPXRipInfTable OBJECT-TYPE
     SYNTAX  SEQUENCE OF RadBridgeIPXRipInfEntry
     MAX-ACCESS  not-accessible
     STATUS  current
     DESCRIPTION
     "The RIP interface table."
     ::= { radBridgeIPXRip 7 }
    
radBridgeIPXRipInfEntry OBJECT-TYPE
     SYNTAX  RadBridgeIPXRipInfEntry
     MAX-ACCESS  not-accessible
     STATUS  current
     DESCRIPTION
	  "Each entry corresponds to one ifindex."
     INDEX   { radBridgeIPXRipInfIfIndex}
     ::= { radBridgeIPXRipInfTable 1 }
    
RadBridgeIPXRipInfEntry ::= SEQUENCE {
     radBridgeIPXRipInfIfIndex
     Integer32,
     radBridgeIPXRipInfBcastUpdate
     Integer32,
     radBridgeIPXRipInfAgeMultiplier
     Integer32
     }
    
radBridgeIPXRipInfIfIndex OBJECT-TYPE
     SYNTAX  Integer32
     MAX-ACCESS  read-only
     STATUS  current
     DESCRIPTION
	  "This value of Ifindex is same as radBridgeIPXIfIndex in the
	   IPX Interface Table."
     ::= { radBridgeIPXRipInfEntry 1 }
    
radBridgeIPXRipInfBcastUpdate OBJECT-TYPE
     SYNTAX  Integer32
     MAX-ACCESS  read-write
     STATUS  current
     DESCRIPTION
	    "The RIP periodic update interval, in seconds. Zero value
	     corresponds to infinite interval."
--     DEFVAL {60}
     ::= { radBridgeIPXRipInfEntry 2 }
    
radBridgeIPXRipInfAgeMultiplier OBJECT-TYPE
     SYNTAX  Integer32
     MAX-ACCESS  read-write
     STATUS  current
     DESCRIPTION
       "The holding multiplier for information received in RIP
       periodic updates. Zero value corresponds to infinite aging time."
--     DEFVAL {3}
     ::= { radBridgeIPXRipInfEntry 3 }

radBridgeIPXSapOutPackets OBJECT-TYPE
    SYNTAX  Counter32
    MAX-ACCESS  read-only
    STATUS  current
    DESCRIPTION
	   "The total number of packets transmitted by SAP."
    ::= { radBridgeIPXSap 1 }
    
radBridgeIPXSapInPackets OBJECT-TYPE
    SYNTAX  Counter32
    MAX-ACCESS  read-only
    STATUS  current
    DESCRIPTION
      "The total number of packets received by SAP.  This will include
       any packets that are subsequently discarded."
    ::= { radBridgeIPXSap 2 }
    
radBridgeIPXSapInDiscards OBJECT-TYPE
    SYNTAX  Counter32
    MAX-ACCESS  read-only
    STATUS  current
    DESCRIPTION
	   "The number of received packets discarded by SAP."
    ::= { radBridgeIPXSap 3 }
    
    
radBridgeIPXSapTblNoOfEntries OBJECT-TYPE
    SYNTAX  Integer32
    MAX-ACCESS  read-only
    STATUS  current
    DESCRIPTION
	   "The max number of entries that exist in the SAP Server
    Information table."
    ::= { radBridgeIPXSap 4 }
    
radBridgeIPXSapTblBcastTrigUpdateInterval OBJECT-TYPE
    SYNTAX  Integer32
    MAX-ACCESS  read-write
    STATUS  current
    DESCRIPTION
       "The default time interval (in seconds) between triggered SAP updates on a
	broadcast style interface.  A triggered update occurs when a
	change is detected in the service database.  This time interval
	delays the transmission of these updates so that changes on the
	network will not result in a lot of triggered updates."
    ::= { radBridgeIPXSap 5 }
        
    
   
radBridgeIPXSapTable OBJECT-TYPE
    SYNTAX  SEQUENCE OF RadBridgeIPXSapTableEntry
    MAX-ACCESS  not-accessible
    STATUS  current
    DESCRIPTION
	   "The Server Information table is used by SAP to store information
	   of services which are available on the internetwork."
    ::= { radBridgeIPXSap 6 }
    
radBridgeIPXSapTableEntry OBJECT-TYPE
    SYNTAX  RadBridgeIPXSapTableEntry
    MAX-ACCESS  not-accessible
    STATUS  current
    DESCRIPTION
       "The server information for one of this entity's server entries."
    INDEX   { radBridgeIPXSapServerType,
	  radBridgeIPXSapName }
    ::= { radBridgeIPXSapTable 1 }

RadBridgeIPXSapTableEntry ::= SEQUENCE {
    radBridgeIPXSapServerType
	Integer32,
    radBridgeIPXSapName
	DisplayString (SIZE(48)),
    radBridgeIPXSapNetwork
	OCTET STRING (SIZE(4)),
    radBridgeIPXSapNode
	OCTET STRING (SIZE(6)),
    radBridgeIPXSapSocket
	Integer32,
    radBridgeIPXSapHopsToServer
	Integer32,
    radBridgeIPXSapNIC
	Integer32,
    radBridgeIPXSapAgingTime
	TimeTicks,
   radBridgeIPXSapStatus
	INTEGER 
    }
    
radBridgeIPXSapServerType OBJECT-TYPE
    SYNTAX  Integer32
    MAX-ACCESS  read-only
    STATUS  current
    DESCRIPTION
	   "The type of the server for which this entry pertains."
    ::= { radBridgeIPXSapTableEntry 1 }
    
radBridgeIPXSapName OBJECT-TYPE
    SYNTAX  DisplayString (SIZE(48))
    MAX-ACCESS  read-only
    STATUS  current
    DESCRIPTION
	   "The name of the server for which this entry pertains."
    ::= { radBridgeIPXSapTableEntry 2 }
    
radBridgeIPXSapNetwork OBJECT-TYPE
    SYNTAX  OCTET STRING (SIZE(4))
    MAX-ACCESS  read-write
    STATUS  current
    DESCRIPTION
	   "The IPX network address of the host on which this server exists."
    ::= { radBridgeIPXSapTableEntry 3 }
    
radBridgeIPXSapNode OBJECT-TYPE
    SYNTAX  OCTET STRING (SIZE(6))
    MAX-ACCESS  read-write
    STATUS  current
    DESCRIPTION
	   "The IPX node address of the host on which this server exists."
    ::= { radBridgeIPXSapTableEntry 4 }
    
radBridgeIPXSapSocket OBJECT-TYPE
    SYNTAX  Integer32
    MAX-ACCESS  read-write
    STATUS  current
    DESCRIPTION
	   "The IPX socket number that is being used by the server to
	   which this entry pertains."
    ::= { radBridgeIPXSapTableEntry 5 }
    
radBridgeIPXSapHopsToServer OBJECT-TYPE
    SYNTAX  Integer32 (1..16)
    MAX-ACCESS  read-write
    STATUS  current
    DESCRIPTION
       "The number of hops to the entity on which this server exists."
    ::= { radBridgeIPXSapTableEntry 6 }
    
radBridgeIPXSapNIC OBJECT-TYPE
    SYNTAX  Integer32 
    MAX-ACCESS  read-write
    STATUS  current
    DESCRIPTION
       "An Network Interface Card identifier specifying what IPX 
	interface the next hop can be found on."
    ::= { radBridgeIPXSapTableEntry 7 }
    
radBridgeIPXSapAgingTime OBJECT-TYPE
    SYNTAX  TimeTicks
    MAX-ACCESS  read-only
    STATUS  current
    DESCRIPTION
       "The last time that the entry was updated.  The time will be
	provided in terms of the MIB-I object sysUpTime."
    ::= { radBridgeIPXSapTableEntry 8 }
    
radBridgeIPXSapStatus OBJECT-TYPE
    SYNTAX  INTEGER {
    permanent(1),
    dynamic(2),
    invalid(3),
    semiDynamic(4)
    }
    MAX-ACCESS  read-write
    STATUS  current
    DESCRIPTION
       "The status of the entry."
    ::= { radBridgeIPXSapTableEntry 9 }
   
  

radBridgeIPXSapInfTable OBJECT-TYPE
    SYNTAX  SEQUENCE OF RadBridgeIPXSapInfEntry
    MAX-ACCESS  not-accessible
    STATUS  current
    DESCRIPTION
    "The Sap interface table."
    ::= { radBridgeIPXSap 7 }
    
radBridgeIPXSapInfEntry OBJECT-TYPE
    SYNTAX  RadBridgeIPXSapInfEntry
    MAX-ACCESS  not-accessible
    STATUS  current
    DESCRIPTION
	 "Each entry corresponds to one ifindex."
    INDEX   {radBridgeIPXSapInfIfIndex}
    ::= { radBridgeIPXSapInfTable 1 }
    
RadBridgeIPXSapInfEntry ::= SEQUENCE {
    radBridgeIPXSapInfIfIndex
    Integer32,
    radBridgeIPXSapInfBcastUpdate
    Integer32,
    radBridgeIPXSapInfAgeMultiplier
    Integer32
    }
    
radBridgeIPXSapInfIfIndex OBJECT-TYPE
    SYNTAX  Integer32
    MAX-ACCESS  read-only
    STATUS  current
    DESCRIPTION
	 "This value of Ifindex is same as radBridgeIPXIfIndex in the
	  IPX Interface Table."
    ::= { radBridgeIPXSapInfEntry 1 }
    
radBridgeIPXSapInfBcastUpdate OBJECT-TYPE
    SYNTAX  Integer32
    MAX-ACCESS  read-write
    STATUS  current
    DESCRIPTION
       "The SAP periodic update interval, in seconds. Zero value
       corresponds to infinite interval."
--    DEFVAL {60}
    ::= { radBridgeIPXSapInfEntry 2 }
    
radBridgeIPXSapInfAgeMultiplier OBJECT-TYPE
    SYNTAX  Integer32
    MAX-ACCESS  read-write
    STATUS  current
    DESCRIPTION
       "The holding multiplier for information received in SAP
       periodic updates. Zero value corresponds to infinite aging time."
--    DEFVAL {3}
    ::= { radBridgeIPXSapInfEntry 3 }


-- radMaskingTab defines the new format of RAD Bridge masking tables


GenAddress ::= OCTET STRING (SIZE(12))

newMasking     OBJECT IDENTIFIER ::= {genBridge 6 }

maskingMaxEntries OBJECT-TYPE
    SYNTAX  Integer32
    MAX-ACCESS  read-only
    STATUS  current
    DESCRIPTION
        "The maximum number of entries in the masking table."
    ::=  { newMasking 1 }


maskingCurrentEntries OBJECT-TYPE
    SYNTAX  Integer32
    MAX-ACCESS  read-only
    STATUS  current
    DESCRIPTION
        "The number of entries in the mask table."
    ::=  { newMasking 2 }

maskingTable    OBJECT-TYPE
    SYNTAX  SEQUENCE  OF MaskingEntry
    MAX-ACCESS  not-accessible
    STATUS  current
    DESCRIPTION
	    "This is the new masking scheme. 
	    Mask tables enable definition of forwarding restrictions and 
	    control of message flow in the internetwork. Each entry
	    in this table defines a mask statement and an action defined by 
	    maskingOperation."
    ::=  { newMasking 3 }
    
maskingEntry OBJECT-TYPE
    SYNTAX  MaskingEntry
    MAX-ACCESS  not-accessible
    STATUS  current
    DESCRIPTION
	    "Defines the contents of each line in the mask table."
    INDEX  { maskingType, maskingIfIndex, maskingIndex }
    ::=  { maskingTable 1 }

MaskingEntry ::= SEQUENCE {
                     maskingType
					  INTEGER,
                     maskingIfIndex
                      Integer32,
                     maskingIndex
                      Integer32,
                     maskingProtocolType
                      INTEGER,
					 maskingSmartMaskOID
					  OBJECT IDENTIFIER,
                     maskingFrameType
                      INTEGER,
                     maskingFrameTypeCondition
                      INTEGER,
                     maskingSourceAddress
                      GenAddress,
                     maskingSourceActiveBits
                      GenAddress,
                     maskingSourceMacOrNet
                        INTEGER,
                     maskingSourceCondition
                      INTEGER,
                     maskingDestAddress
                      GenAddress,
                     maskingDestActiveBits
                      GenAddress,
                     maskingDestMacOrNet
                        INTEGER,
                     maskingDestCondition
                      INTEGER,
                     maskingLowLevelProt
                      INTEGER,
                     maskingLowLevelProtCondition
                      INTEGER,
                     maskingHighLevelProt
                      Integer32,
                     maskingHighLevelProtCondition
                      INTEGER,
                     maskingPortNum
                      Integer32,
                     maskingPortNumCondition
                      INTEGER,
                     maskingOperation
                      INTEGER,
                     maskingSrcPortNum 
                      Integer32,
                     maskingSrcPortNumCondition 
                      INTEGER
                       }

   maskingType OBJECT-TYPE
    SYNTAX  INTEGER {
	  tx            (1),
	  rx            (2),
      compress(3),
      priority(4),
      loadSharing(5),
      facs(6),
      codConnect(7),
      codDisconnect(8)
     }
    MAX-ACCESS  read-write
    STATUS  current
    DESCRIPTION
        "Defines the type of mask entry. "
    ::= {    maskingEntry 1  }


   maskingIfIndex  OBJECT-TYPE
    SYNTAX Integer32
    MAX-ACCESS  read-write
    STATUS  current
    DESCRIPTION 
	"Specifies the ifIndex of the interface to which the mask is applied."
	::= {    maskingEntry 2  }
   

                  
   maskingIndex OBJECT-TYPE
    SYNTAX  Integer32
    MAX-ACCESS  read-write
    STATUS  current
    DESCRIPTION
        "An index to the masking table. This number should not be greater than maskingMaxEntries"
    ::= {    maskingEntry 3  }
                  
            
                
        
   maskingProtocolType OBJECT-TYPE
    SYNTAX  INTEGER {
    unknown     (1),
    ip          (2),
	ipx         (3),
	sna         (4),
	netbios     (5),
              apple      (6),
              dec         (7),
    all         (255)
    }			
    MAX-ACCESS  read-write
    STATUS  current
    DESCRIPTION
         "The base protocol for masking. IPX, IP, others."
    ::= {    maskingEntry 4  }


    maskingSmartMaskOID OBJECT-TYPE
	 SYNTAX  OBJECT IDENTIFIER
	 MAX-ACCESS  read-only
	 STATUS  current
	 DESCRIPTION
	      "A reference to a specific Smart mask table (old radBridgeMaskTable)
	       which enables a more specific mask type.
		   If this information is not available, its value 
		   should be set to the OBJECT IDENTIFIER { 0 0 }. "
     ::= {  maskingEntry 5  }		    

         
    maskingFrameType OBJECT-TYPE
    SYNTAX  INTEGER {
    unknown     (1),
    all         (2),
    broadcast   (3),
    multicast   (4)
    }
    MAX-ACCESS  read-write
    STATUS  current
    DESCRIPTION
        "Enables the user to decide about frame type 
          * all frame 
          * just broadcast 
          * just multicast."
    ::= {    maskingEntry 6  }

   maskingFrameTypeCondition OBJECT-TYPE
    SYNTAX  INTEGER {
    false      (1),
    true       (2)
    }
    MAX-ACCESS  read-write
    STATUS  current
    DESCRIPTION
	"Specifies the logical condition of the mask pattern:

	true  - Condition is valid if at the position specified by 
   		   maskingFrameType the packet contains data that matches
  	the content of maskingFrameType.

	fa    lse - Condition is valid if at the position specified by 
		   maskingFrameType the packet contains data that does not
    		match the content of maskingFrameType."
    ::= {    maskingEntry 7  }

   maskingSourceAddress OBJECT-TYPE
    SYNTAX  GenAddress
    MAX-ACCESS  read-write
    STATUS  current
    DESCRIPTION
       "The source address is according to the maskingMacOrNet and 
        maskingProtocolType variables. 
        In case of 'MAC' enter 6 bytes (48 bit) of source address.
        In case of 'NET' 
            if the    maskingProtocolType is IP, this is the IP address
            if the    maskingProtocolType is IPX, this is the IPX address 
                 (nnnnmmmmmmss)
                                nnnn   - IPX net address
                                mmmmmm - Node address (Mac)
                                ss     - IPX socket
        In case of 'Apple' 
                                nn - net address (4 nibbles) 
                                ss - socket (4 nibbles)."   
    ::= {    maskingEntry 8  }

   maskingSourceActiveBits OBJECT-TYPE
    SYNTAX  GenAddress
    MAX-ACCESS  read-write
    STATUS  current
    DESCRIPTION
	   "Specifies the positions of the wild card characters (*) 
	    in the    maskingSourceAddress field. Only the 1's bit will be taken in 
        considerations."
    ::= {    maskingEntry 9  }

   maskingSourceMacOrNet OBJECT-TYPE
    SYNTAX  INTEGER {
    macAddress  (1),
    netAddress  (2),
    ipRange     (3),
    appleAddress(4)
    }
    MAX-ACCESS  read-write
    STATUS  current
    DESCRIPTION
	"The variable maskingSourceAddress and maskingSourceActiveBits 
	 will be treated as MAC, or NET address.
	 -  If maskingProtocolType = 'all', 'sna', 'netbios', dec or 
		'unknown', the maskingSourceMacOrNet can be macAddress only!
	 -  If maskingProtocolType = 'ip' the 
		maskingSourceMacOrNet can be  macAddress or netAddress or 
		appleAddress. 
	 -  If maskingProtocolType = 'ipx', the 
		maskingSourceMacOrNet can be either macAddress or netAddress. 
	 -  If maskingProtocolType = 'apple', the 
		maskingSourceMacOrNet can be either macAddress or appleAddress." 
    ::= {    maskingEntry 10  }
    
   maskingSourceCondition OBJECT-TYPE
    SYNTAX  INTEGER {
    false (1),
    true (2)
    }
    MAX-ACCESS  read-write
    STATUS  current
    DESCRIPTION
	"Specifies the logical condition of the mask pattern:

	true  - Condition is valid if at the position specified by 
	           maskingSourceAddress (in conjunction with maskingSourceActiveBits) 
	        the packet contains data that matches the content of maskingSourceAddress.

	false - Condition is valid if at the position specified by 
		   maskingSourceAddress (in conjunction with maskingSourceActiveBits) 
	    	the packet contains data that does not match the content of
	        maskingSourceAddress."
    ::= {    maskingEntry 11 }
    
   maskingDestAddress OBJECT-TYPE
    SYNTAX  GenAddress
    MAX-ACCESS  read-write
    STATUS  current
    DESCRIPTION
       "If maskingFrameType = broadcast or multicast, this object
	    is NOT APPLICABLE.
	    If maskingFrameType = all or unknown, this object is 
	    applicable.
        The destination address is according to the maskingMacOrNet and maskingProtocolType variables. 
        In case of 'MAC' enter 6 bytes (48 bit) of source address.
        In case of 'NET' 
            if the    maskingProtocolType is IP, this is the IP address
            if the    maskingProtocolType is IPX, this is the IPX address 
                 (nnnnmmmmmmss)
                                nnnn   - IPX net address
                                mmmmmm - Node address (Mac)
                                ss     - IPX socket.
        In case of 'Apple' 
                                nn - net address (4 nibbles) 
                                ss - socket (4 nibbles).
        The IPX socket entered here has priority over the value of
        maskingLowLevelProt, when it is ipxRip, ipxSap or ipxSpx, 
        unless the entered IPX socket is don't care. "   
    ::= {    maskingEntry 12  }

   maskingDestActiveBits OBJECT-TYPE
    SYNTAX  GenAddress
    MAX-ACCESS  read-write
    STATUS  current
    DESCRIPTION
	   "If maskingFrameType = broadcast or multicast, this object
	    is NOT APPLICABLE.
	    If maskingFrameType = all or unknown, this object is 
	    applicable.
	    Specifies the positions of the wild card characters (*) 
	    in the    maskingDestAddress field. Only the 1's bit will be taken in 
        considerations."
    ::= {    maskingEntry 13   }

   maskingDestMacOrNet OBJECT-TYPE
    SYNTAX  INTEGER {
    macAddress  (1),
    netAddress  (2),
    ipRange     (3),
    appleAddress(4)
    }
    MAX-ACCESS  read-write
    STATUS  current
    DESCRIPTION
	"If maskingFrameType = broadcast or multicast, this object
	 is NOT APPLICABLE.
	 If maskingFrameType = all or unknown, this object is 
	 applicable.
	 -  If maskingProtocolType = 'all', 'sna', 'netbios', dec or 
		'unknown', the maskingDestMacOrNet can be macAddress only!
	 -  If maskingProtocolType = 'ip' the 
		maskingDestMacOrNet can be  macAddress or netAddress or 
		appleAddress. 
	 -  If maskingProtocolType = 'ipx', the 
		maskingDestMacOrNet can be either macAddress or netAddress. 
	 -  If maskingProtocolType = 'apple', the 
		maskingDestMacOrNet can be either macAddress or appleAddress. 
     The variable maskingDestAddress and maskingDestActiveBits will 
	 be treated as MAC, or NET address.	"
    ::= {    maskingEntry 14  }

   maskingDestCondition OBJECT-TYPE
    SYNTAX  INTEGER {
    false (1),
    true (2)
    }
    MAX-ACCESS  read-write
    STATUS  current
    DESCRIPTION
	"If maskingFrameType = broadcast or multicast, this object
	 is NOT APPLICABLE.
	 If maskingFrameType = all or unknown, this object is 
	 applicable.
	Specifies the logical condition of the mask pattern:

	true  - Condition is valid if at the position specified by 
	           maskingDestAddress (in conjunction with maskingDestActiveBits) 
	        the packet contains data that matches the content of maskingDestAddress.

	false - Condition is valid if at the position specified by 
		   maskingDestAddress (in conjunction with maskingDestActiveBits) 
		the packet contains data that does not match the content of maskingDestAddress."
    ::= {    maskingEntry 15  }

   maskingLowLevelProt OBJECT-TYPE
    SYNTAX  INTEGER {
      unknown (1), -- don't care
      ipxRip  (2), -- 0x51
      ipxSap  (3), -- 0x52
      ipxSpx  (4), -- 0x53
      ipUdp   (5), -- 0x54
      ipTcp   (6), -- 0x55
      ipIcmp  (7), -- 0x56
	ipxNcp  (8), -- 0x57
	ipxWan  (9), -- 0x58
	ipxEco (10), -- 0x59
	ipxErr (11), -- 0x5a
	ipxPep (12)  -- 0x5b 
    }
    MAX-ACCESS  read-write
    STATUS  current
    DESCRIPTION
         "This field is set in conjunction with the maskingProtocolType variable.
          This variable specifies the low level protocol.
          The IPX socket entered in maskingDestAddress has priority 
          over the value of maskingLowLevelProt, when it is ipxRip, 
          ipxSap or ipxSpx, unless the entered IPX socket is don't 
          care."
    ::= {    maskingEntry 16  }

   maskingLowLevelProtCondition OBJECT-TYPE
    SYNTAX  INTEGER {
    false  (1),
    true (2)
    }
    MAX-ACCESS  read-write
    STATUS  current
    DESCRIPTION
	"Specifies the logical condition of the mask pattern:

	true  - Condition is valid if at the position specified by 
    	   maskingLowLevelProt the packet contains data that matches
		the content of maskingLowLevelProt.

	false - Condition is valid if at the position specified by 
		   maskingLowLevelProt the packet contains data that does not
		match the content of maskingLowLevelProt."
    ::= {    maskingEntry 17  }

   maskingHighLevelProt OBJECT-TYPE
    SYNTAX  Integer32 
    MAX-ACCESS  read-write
    STATUS  current
    DESCRIPTION
         "This field is set in connection to the maskingProtocolType variable.
          This variable specifies the high level protocols (application).
          As for today it supports just IP protocol stack.
          The object's value is a sum of the following instances values 
          (selected by user):  
                     none     (0), -- don't care
    			   ftp      (1), 
    			   ftpC     (2), 
    			   telnet   (4), 
    			   smtp     (8),
    			   tftp     (16),
    			   snmp     (32),
    			   snmpTrap (64),
			       ipRip    (128),
			       www      (256),
			       email    (512),
			       dns      (1024),
                     
                     For Apple Protocol only:
                     rtmp     (2048), 
                     nbp      (4096), 
                     atp      (8192), 
                     aep      (16384), 
                     zip      (32768), 
                     adsp     (65536),
					 pap      (131072),
					 asp      (262144)
 
          Example: if ftp(1), snmp(32) and snmpTrap(64) instances 
                   were selected, the value should be 97 (=1+32+64)."
    ::= {    maskingEntry 18  }

   maskingHighLevelProtCondition OBJECT-TYPE
    SYNTAX  INTEGER {
    false  (1),
    true (2)
    }
    MAX-ACCESS  read-write
    STATUS  current
    DESCRIPTION
	"Specifies the logical condition of the mask pattern:

	true  - Condition is valid if at the position specified by 
		   maskingHighLevelProt the packet contains data that matches
		the content of    maskingHighLevelProt.

	false - Condition is valid if at the position specified by 
		   maskingHighLevelProt the packet contains data that does not
		match the content of    maskingHighLevelProt."
    ::= {    maskingEntry 19  }

   maskingPortNum OBJECT-TYPE
    SYNTAX  Integer32
    MAX-ACCESS  read-write
    STATUS  current
    DESCRIPTION
        "The port number is the same as in high level protocol. It 
         specifies the dest. port in IP case or the dest. socket 
         in case of IPX & apple protocols.
		 IP  -  This object is applicable only if none (0) value was selected in
		        maskingHighLevelProt.
         IPX -  This object is applicable only if the socket 
                entered in maskingDestAddress is 'don't care'(00) AND
			    maskingLowLevelProt is NOT ipxRip or ipxSap.
	     Apple - This option is applicable only if the socket 
                entered in maskingDestAddress is 'don't care'(00)."
    ::= {    maskingEntry 20  }

   maskingPortNumCondition OBJECT-TYPE
    SYNTAX  INTEGER  {
    false  (1),
    true (2)
    }
    MAX-ACCESS  read-write
    STATUS  current
    DESCRIPTION
	"Specifies the logical condition of the mask pattern:

	true  - Condition is valid if at the position specified by 
		   maskingPortNum the packet contains data that matches
		the content of    maskingPortNum.

	false - Condition is valid if at the position specified by 
		   maskingPortNum the packet contains data that does not
		match the content of    maskingPortNum.
	 This object is applicable only when maskingPortNum is applicable."
    ::= {    maskingEntry 21  }

 
maskingOperation OBJECT-TYPE
    SYNTAX INTEGER { 
       block         (1),
       forward       (2),
       route         (3),
       forward-route (4),
       high-priority (5),
       noOp          (6),
       delete        (7),
       smartMask     (8)
}
    MAX-ACCESS read-write
    STATUS current
    DESCRIPTION
	"The type of action to be taken if the frame meets the 
     conditions of the mask.
       noOp = disabled (mask remains on list, but is not active) 
	 delete = mask is removed from the list.
	 smartMask = the operation and destination of the mask will
	             be determined by the objects of the Smart Table 
	             (old masking table: radBridgeMaskTable). 
     If maskingType is codConnect, the 'block' value is NOT 
     allowed. 
     If maskingType is codDisconnect, the 'forward' value is NOT 
     allowed."     
     ::= {  maskingEntry 22 }    

maskingSrcPortNum OBJECT-TYPE
    SYNTAX  Integer32
    MAX-ACCESS  read-write
    STATUS  current
    DESCRIPTION
        "The source port number.
         For IP:   No Condition.
         For IPX:  This object is applicable only if the socket entered in
                   maskingSourceAddress is don't care (00) and maskingLowLevelProt
                   is NOT ipxRip or ipxSap.
         For Apple:This object is applicable only if the socket entered in
                   maskingSourceAddress is don't care (00). "
    ::= {    maskingEntry 23  }

maskingSrcPortNumCondition OBJECT-TYPE
    SYNTAX  INTEGER  {
    false  (1),
    true (2)
    }
    MAX-ACCESS  read-write
    STATUS  current
    DESCRIPTION
	"The same as 'maskingPortNumCondition'.
       Relates to source port."
    ::= {  maskingEntry 24  }
 

radBridgePerformance      OBJECT IDENTIFIER ::= {genBridge 7 }

          -- The RAD Bridge current table contains statistics being
          -- collected for the current 15 minute interval.

          radBridgeCurrentTable OBJECT-TYPE
              SYNTAX  SEQUENCE OF RadBridgeCurrentEntry
              MAX-ACCESS  not-accessible
              STATUS  current
              DESCRIPTION
                      "The RAD Bridge Current table."
              ::= { radBridgePerformance 1 }

          radBridgeCurrentEntry OBJECT-TYPE
              SYNTAX  RadBridgeCurrentEntry
              MAX-ACCESS  not-accessible
              STATUS  current
              DESCRIPTION
                      "An entry in the RAD Bridge Current table."
              INDEX   { radBridgeCurrentIndex }
              ::= { radBridgeCurrentTable 1 }

          RadBridgeCurrentEntry ::=
              SEQUENCE {
	           radBridgeCurrentIndex	  
	     	          Integer32,
               radBridgeCurrentIngressFilteringDiscardedFrames
                      Gauge32,
               radBridgeCurrentFrameTypeDiscardedFrames
                      Gauge32
					  }

radBridgeCurrentIndex OBJECT-TYPE
    SYNTAX      Integer32
    MAX-ACCESS  read-only
    STATUS      current
    DESCRIPTION
        "The index of the Bridge interface. 
        It may be ifIndex."
    ::= { radBridgeCurrentEntry 1 }

radBridgeCurrentIngressFilteringDiscardedFrames OBJECT-TYPE
    SYNTAX      Gauge32
    MAX-ACCESS  read-only
    STATUS      current
    DESCRIPTION
        "The counter associated with the number of Discarded 
        Frames upon Ingress Filtering, encountered by a Bridge
        interface in the current 15 minute interval."
    ::= { radBridgeCurrentEntry 2 }

radBridgeCurrentFrameTypeDiscardedFrames OBJECT-TYPE
    SYNTAX      Gauge32
    MAX-ACCESS  read-only
    STATUS      current
    DESCRIPTION
        "The counter associated with the number of Discarded 
        Frames upon Frame Type and Tagging Mismatch, encountered 
        by a Bridge interface in the current 15 minute interval."
    ::= { radBridgeCurrentEntry 3 }



--Interval Table

          -- The RAD Bridge Interval table contains statistics being
          -- collected by each Interface over the previous 24
          -- hours of operation.  The past 24 hours are broken into 96
          -- completed 15 minute intervals.

          radBridgeIntervalTable OBJECT-TYPE
              SYNTAX  SEQUENCE OF RadBridgeIntervalEntry
              MAX-ACCESS  not-accessible
              STATUS  current
              DESCRIPTION
                      "The RAD Bridge Interval table."
              ::= { radBridgePerformance 2 }

          radBridgeIntervalEntry OBJECT-TYPE
              SYNTAX  RadBridgeIntervalEntry
              MAX-ACCESS  not-accessible
              STATUS  current
              DESCRIPTION
                      "An entry in the RAD Bridge Interval table."
              INDEX   { radBridgeIntervalIndex, radBridgeIntervalNumber }
              ::= { radBridgeIntervalTable 1 }

          RadBridgeIntervalEntry ::=
              SEQUENCE {
	           radBridgeIntervalIndex	  
	     	          Integer32,
               radBridgeIntervalNumber
			          Integer32,
               radBridgeIntervalIngressFilteringDiscardedFrames
                      Gauge32,
               radBridgeIntervalFrameTypeDiscardedFrames
                      Gauge32
					  }

radBridgeIntervalIndex OBJECT-TYPE
    SYNTAX      Integer32
    MAX-ACCESS  read-only
    STATUS      current
    DESCRIPTION
        "The index of the bridge interface. 
        It may be ifIndex."
    ::= { radBridgeIntervalEntry 1 }

radBridgeIntervalNumber OBJECT-TYPE
    SYNTAX  Integer32 (1..96)
    MAX-ACCESS  read-only
    STATUS  current
    DESCRIPTION
        "A number between 1 and 96, where 1 is the most
         recently completed 15 minute interval and 96 is
         the least recently completed 15 minutes interval
         (assuming that all 96 intervals exist)."
    ::= { radBridgeIntervalEntry 2 }

radBridgeIntervalIngressFilteringDiscardedFrames OBJECT-TYPE
    SYNTAX      Gauge32
    MAX-ACCESS  read-only
    STATUS      current
    DESCRIPTION
        "The counter associated with the number of Discarded 
        Frames upon Ingress Filtering, encountered by a 
        Bridge interface in one of the previous 96, individual 
        15 minute, intervals."
    ::= { radBridgeIntervalEntry 3 }

radBridgeIntervalFrameTypeDiscardedFrames OBJECT-TYPE
    SYNTAX      Gauge32
    MAX-ACCESS  read-only
    STATUS      current
    DESCRIPTION
        "The counter associated with the number of Discarded 
        Frames upon Frame Type and Tagging Mismatch, encountered 
        by a Bridge interface in one of the previous 96, individual 
        15 minute, intervals."
    ::= { radBridgeIntervalEntry 4 }
-- 
-- file :v:\doc\rdv\mib\Before~1\trim.txt
-- 
--Title:         TrimBridge MIB
--Version:   3.0
--Last revision: 9.10.94
--By:            Debby Koren & Orly Nicklass
--File:          trim.txt                                    
											 

  
-- Objects in this section are arranged into groups:
--   trimInterface  -  Interface table and RS232 interface parameters
--   trimBackup     -  Backup feature, Dial-up parameters.
--   trimTR - Token Ring interface management
--   trimTrapInfo - parameters that provide information on traps sent


--Comments: The Trimbridge-16 agent also supports the following Public MIBs:
--              MIB-II (RFC1213)
--              dot5 ( RFC1231-MIB, updated by RFC1239 ) except for the optional Timers-table
--	 bridge (RFC 1493)
--Comments: The Trimbridge-10 agent also supports the following Public MIBs:
--              MIB-II (RFC1213)
--	 bridge (RFC 1493)


-- the trimInterface group defines the Trimbridge interface table and parameters for 
-- RS232 interface


trim OBJECT IDENTIFIER ::= {radBridges 3 }
trimInterface OBJECT IDENTIFIER ::= { trim 1  }

trimIfTable  OBJECT-TYPE
    SYNTAX SEQUENCE OF  TrimIfEntry 
    MAX-ACCESS  not-accessible
    STATUS  current
    DESCRIPTION
	"RAD-specific interface table. "
    ::= {  trimInterface 1  }
		   
trimIfEntry  OBJECT-TYPE
    SYNTAX TrimIfEntry 
    MAX-ACCESS  not-accessible
    STATUS  current
	DESCRIPTION
	"An entry in table trimIfTable."
    INDEX   { trimIfIndex  }
    ::= {  trimIfTable 1  }


TrimIfEntry ::= SEQUENCE { 
  trimIfIndex  
     Integer32,
  trimIfBoardNum  
     Integer32,
  trimIfNetAddress
     IpAddress,
  trimIfStatus    
     INTEGER,
  trimIfClockType  
     INTEGER,
  trimIfBaudRate
     Integer32,
  trimIfCost
     Integer32,
  trimIfCompression
     INTEGER,
  trimIfCompressionStatus
     INTEGER,
  trimIfCompressionRate
     Integer32,
  trimIfLATCompression
     INTEGER,
  trimIfCompressionType
     INTEGER,
  trimIfFilterMode
     INTEGER,
  trimIfConType
     INTEGER,
  trimIfRemAddress
     DisplayString,
  trimIfLocSubAddress
     DisplayString,
  trimIfRemSubAddress
     DisplayString,
  trimIfCLIVerification
     INTEGER

  }


trimIfIndex OBJECT-TYPE
    SYNTAX   Integer32  
    MAX-ACCESS  read-only
    STATUS  current
    DESCRIPTION
	"Index to the Trimbridge Interface Table. The interface defined by a 
	particular value of this index is the same interface as 
	identified by the same value of ifIndex (MIB II)."
    ::= {  trimIfEntry 1  }


trimIfBoardNum OBJECT-TYPE
    SYNTAX   Integer32  
    MAX-ACCESS  read-only
    STATUS  current
    DESCRIPTION
	"Reserved for possible future use.  Not currently applicable to Trimbridge."
    ::= {  trimIfEntry 2  }


trimIfNetAddress OBJECT-TYPE
    SYNTAX   IpAddress  
    MAX-ACCESS  read-only
    STATUS  current
    DESCRIPTION
	"The IP address of the interface defined by the particular value of 
	trimIfIndex."
    ::= {  trimIfEntry 3  }


trimIfStatus  OBJECT-TYPE
    SYNTAX   INTEGER  {
       ok (1),
       okSingleBrg(2),
       okMultiBrg(3),
       connctFault(4),
       rxFault(5),
       txFault(6),
       channelLoopback(7),
       rxClockFault(8),
       t1Alarm(9)
    }
    MAX-ACCESS  read-only
    STATUS  current
    DESCRIPTION
	"The current status of the interface.  Some of these status values are not applicable to Trimbridge."
     ::= {  trimIfEntry 4  }


trimIfClockType   OBJECT-TYPE 
    SYNTAX  INTEGER { 
       external(1),
       internal(2),
       t1(3),
       g703(4)
    }
    MAX-ACCESS  read-write
    STATUS  current
    DESCRIPTION
	"trimIfClockType defines the type of clock each interface
	uses: internal or external."
    ::= {  trimIfEntry 5  }


trimIfBaudRate    OBJECT-TYPE          -- Level II routing
    SYNTAX   Integer32   -- word
    MAX-ACCESS  read-write
    STATUS  current
    DESCRIPTION
	" Defines the baud rate in use by the interface. The valid
	 rates are determined by the type of the media for which this
	 baud rate is defined."
    ::= { trimIfEntry 6  }


trimIfCost    OBJECT-TYPE          -- Level II routing
    SYNTAX   Integer32   -- word 
    MAX-ACCESS  read-write
    STATUS  current
    DESCRIPTION
	"This object is inapplicable to Trimbridge."
    ::= { trimIfEntry 7  }


trimIfCompression   OBJECT-TYPE
    SYNTAX  INTEGER {
       enable(1),
       disable(2)
    }
    MAX-ACCESS  read-write
    STATUS  current
    DESCRIPTION
       "Defines whether data compression is enabled or disabled for the 
       interface."
    ::= {  trimIfEntry 8  }


  trimIfCompressionStatus  OBJECT-TYPE
  SYNTAX  INTEGER {
       not-inserted(1),
       active(2),
       not-active(3),
       disable(4)
    }
    MAX-ACCESS  read-only
    STATUS  current
    DESCRIPTION
	  "Defines the status of the compression component: 
	  not-inserted - compression component is not in the device
	  active - compression is enabled and operates correctly
	  not-active - compression is enables but does not operate. 
		       The reason may be that there is no 
		       compression component on the device connected 
		       to this interface.
	  disabled - compression was disabled by management, using 
		       variable trimCompression."
    ::= {  trimIfEntry 9  }
  

  trimIfCompressionRate  OBJECT-TYPE
    SYNTAX  Integer32
    MAX-ACCESS  read-only
    STATUS  current
    DESCRIPTION
	  "Percentage of compression. This variable applies only 
	  if trimCompressionStatus is active."
    ::= {  trimIfEntry 10  }


  trimIfLATCompression  OBJECT-TYPE
    SYNTAX  INTEGER {
       enable(1),
       disable(2)
    }
    MAX-ACCESS  read-write
    STATUS  current
    DESCRIPTION
	  "Enable/Disable the LAT Compression." 
    ::= {  trimIfEntry 11  }


  trimIfCompressionType  OBJECT-TYPE
    SYNTAX  INTEGER {
       none(1),
       lowSpeed(2),
       highSpeed(3)
    }
    MAX-ACCESS  read-only
    STATUS  current
    DESCRIPTION
	  "This parameter indicates the type of compression option available in
	   the device. 
	     `None(1)           - indicates that there is no compression option in the device
	      lowSpeed(2)   - indicates a compression option which is  operational up 
					 to line speed sof 64 kbps.
	      highSpeed(3) - indicates a compression option which is  operational up
					 to line speeds of 2 Mbps."
    ::= {  trimIfEntry 12  }



trimIfFilterMode  OBJECT-TYPE
    SYNTAX  INTEGER {
       destinationOnly(1),
       sourceAndDestination(2)
    }
    MAX-ACCESS  read-write
    STATUS  current
    DESCRIPTION
	"This parameter indicates the type of filtering in the device. "
    ::= {  trimIfEntry 13 }

trimIfConType  OBJECT-TYPE
    SYNTAX  INTEGER {
       unknown(1),
	   none(2),
       x21Old(3),
	   x21(4),
	   v35Old(5),
	   v35(6),
	   rs530Old(7),
	   rs530(8),
	   rs232Old(9),
	   rs232(10),
	   spsV35(11),
	   spsRS530(12),
	   spsRS232(13),
	   spsX21(14),
	   isdn(15)
    }
    MAX-ACCESS  read-only
    STATUS  current
    DESCRIPTION
	"This parameter indicates the connector type of an interface. "
    ::= {  trimIfEntry 14 }



trimIfRemAddress OBJECT-TYPE
    SYNTAX   DisplayString (SIZE(1..17))
    MAX-ACCESS  read-write
    STATUS  current
    DESCRIPTION
	"         "
    ::= {  trimIfEntry 15  }



trimIfLocSubAddress OBJECT-TYPE
    SYNTAX   DisplayString (SIZE(1..6))
    MAX-ACCESS  read-write
    STATUS  current
    DESCRIPTION
	"Space is not valid. If the string includes a space,
	 the whole entry is considered not valid."
    ::= {  trimIfEntry 16  }



trimIfRemSubAddress OBJECT-TYPE
    SYNTAX   DisplayString (SIZE(1..6))
    MAX-ACCESS  read-write
    STATUS  current
    DESCRIPTION
	"Space is not valid. If the string includes a space,
	 the whole entry is considered not valid."
    ::= {  trimIfEntry 17  }



trimIfCLIVerification OBJECT-TYPE
    SYNTAX  INTEGER {
	enable(1),
	disable(2)
	}
	MAX-ACCESS  read-write
	STATUS  current
	DESCRIPTION
	"Enables/Disables verification of Control Line Identification (CLI)"
	::= {  trimIfEntry 18  }


--    The variables in this group define the RS232 management interface 


trimRS232Conf        OBJECT IDENTIFIER ::= { trimInterface 2  }

trimBaudRate OBJECT-TYPE
    SYNTAX INTEGER { 
       br300(1),
       br1200(2),
       br2400(5),
       br4800(7),
       br9600(9),
       br19200(10)
    }
    MAX-ACCESS  read-write
    STATUS  current
    DESCRIPTION
	"Selects the baud rate used by the RS232 management interface. The 
	default selection is 1200 bits/second."
    ::= { trimRS232Conf 1  }


trimParity OBJECT-TYPE
    SYNTAX INTEGER { 
       noParity(1),
       oddParity(2),
       evenParity(3)
    }
    MAX-ACCESS  read-write
    STATUS  current
    DESCRIPTION
	"Determines whether the parity bit will be used and determines 
	its type."
    ::= { trimRS232Conf 2  }


trimStopBit OBJECT-TYPE
    SYNTAX INTEGER {
       oneStopBit(1),
       twoStopBit(2)
    }
    MAX-ACCESS  read-write
    STATUS  current
    DESCRIPTION
	"Selects the number of stop bits appended to the end of 
	each data word."
    ::= { trimRS232Conf 3  }


trimThresholdRep    OBJECT IDENTIFIER ::= { trimInterface 3}
trimIfThresholdRepTable   OBJECT-TYPE
    SYNTAX  SEQUENCE  OF TrimIfThresholdRepEntry
    MAX-ACCESS  not-accessible
    STATUS  current
    DESCRIPTION
	"    ....."
    ::=  {trimThresholdRep 1}


trimIfThresholdRepEntry  OBJECT-TYPE
    SYNTAX TrimIfThresholdRepEntry
    MAX-ACCESS  not-accessible
    STATUS  current
	DESCRIPTION
	"An entry in table trimIfThresholdRepTable."
    INDEX  { trimIfThreRepId,trimIfThreRepCounterId }
    ::=  { trimIfThresholdRepTable 1}



TrimIfThresholdRepEntry  ::= SEQUENCE {
     trimIfThreRepId
	  Integer32,
     trimIfThreRepCounterId
	  INTEGER,
     trimThresholdValue
	  Integer32,
     trimIfThreRepSampleRate
	  Integer32,
     trimIfThreRepTrapRate
	  Integer32
      }
trimIfThreRepId OBJECT-TYPE
    SYNTAX   Integer32
    MAX-ACCESS  read-only
    STATUS  current
    DESCRIPTION
	"The Interface number serves as an index to the Threshold Reoprt Table."
     ::= { trimIfThresholdRepEntry 1  }


trimIfThreRepCounterId OBJECT-TYPE
    SYNTAX   INTEGER{
	  vot(1)
	}
    MAX-ACCESS  read-only
    STATUS  current
    DESCRIPTION
	"The Counter ID  serves as an index to the Threshold Reoprt Table, and identify the counter for which 
	 to pot the threshold."
     ::= {  trimIfThresholdRepEntry 2  }



trimThresholdValue OBJECT-TYPE
    SYNTAX   Integer32
    MAX-ACCESS  read-write
    STATUS  current
    DESCRIPTION
	"The Threshold value , this is the maximum rate of counter increments  before the element issue trap."  
     ::= {  trimIfThresholdRepEntry 3  }


trimIfThreRepSampleRate OBJECT-TYPE
    SYNTAX   Integer32
    MAX-ACCESS  read-write
    STATUS  current
    DESCRIPTION
	   "The network object  will sample the counter atthis  interval. When this  parameter 
	    is set to 0, the treshold comparison is disable."
--      DEFVAL  { 10 }
     ::= {  trimIfThresholdRepEntry 4}
   

trimIfThreRepTrapRate  OBJECT-TYPE
    SYNTAX   Integer32
    MAX-ACCESS  read-write
    STATUS  current
    DESCRIPTION
	  " The network object  will issue a trap according to this interval. Note that the trape 
	    interval nust be equal or larger then trimIfThreRepSampleRate."
--      DEFVAL  { 30 }
     ::= {  trimIfThresholdRepEntry 5}

-- trimBackup group defines the parameters for the backup feature

trimBackup    OBJECT IDENTIFIER ::= { trim 2 }

trimBackupState OBJECT-TYPE
    SYNTAX  INTEGER {
      main(1),
      backup(2)
    }
    MAX-ACCESS  read-only
    STATUS current 
    DESCRIPTION
	"If main - the bridge is connected via the main physical link. 
	If backup - the automatic backup feature was enabled 
	and the bridge is connected via the backup physical link."
    ::= { trimBackup 1 }

   trimDialUpStatus  OBJECT-TYPE
    SYNTAX  INTEGER {
      enable(1),
      disable(2)
      }
    MAX-ACCESS  read-write
    STATUS  current
    DESCRIPTION
	"This parameter controls the operation of dial-up backup function.
	  If status is disable(2), dial-up backup will not be initiated when the 
	  main link fails or exceeds the specified error limit.
	   If status is enable(1), the dial-up backup will be initiated if the main
	  link fails or if the error rate on the main link exceeds the limit specified
	  by variable trimDialUp ErrorThreshold."
    ::= { trimBackup 2 }

trimBackLinkType  OBJECT-TYPE
    SYNTAX  INTEGER {
	dialUp(1),
	leased (2)
	}
    MAX-ACCESS  read-write
    STATUS  current
    DESCRIPTION
	"This variable specifies the type of the backup link. If the type is leased(2), 
	  Trimbridge will reroute traffic to the backup link, when main link fails.
	  If the value is dialUp(1), then the backup dial-up procedure is initiated
	  when the main link fails."
    ::= { trimBackup 3 }



trimDialUpMode  OBJECT-TYPE
    SYNTAX  INTEGER {
      originate(1),
      answer(2)
      }
    MAX-ACCESS  read-write
    STATUS  current
    DESCRIPTION
	"If the mode is originate(1), Trimbridge initiates the backup procedure when the
	  main link fails. if the mode is answer(2), it expects that the bridge on the 
	 other end of the link will initiate the backup procedure. Note that only one 
	 bridge in a pair should be set to mode originate(1). "
    ::= { trimBackup 4 }

trimDialUpErrorThreshold  OBJECT-TYPE
    SYNTAX  INTEGER {
	none(1),
	low(2),
	medium(3),
	high(4)
	    }
    MAX-ACCESS   read-write
     STATUS  current
    DESCRIPTION
	"Error rate on main link at which Backup will be enabled.
	    low    - 1*10-5
	    medium - 5*10-4
	    high   - 1*10-3 
	  If none(1) is selected, then backup is not invoked when there are errors
	  on the main link, but only when the main link is down."
    ::= { trimBackup 5 }

trimDialUpRedialTimeout  OBJECT-TYPE
    SYNTAX  Integer32
    MAX-ACCESS  read-write
    STATUS  current
    DESCRIPTION
	  "If an attempt to dial up failed for the specified time, a new redial attempt
	    will be initiated."
       ::= { trimBackup 6}

trimDialUpRedialNum   OBJECT-TYPE
    SYNTAX  Integer32
    MAX-ACCESS   read-write
    STATUS  current
    DESCRIPTION
	"This variable specifies the number of times to initiate the dial-up procedure.
	  If the number of redials is set to zero (0), then the number of redials will be 
	  unlimited. Any other value will cause the dial-up procedure to terminate after 
	 the specified number of re-dial attempts fail. Resetting this variable to any value
	  will re-initiate the dial-up procedure."
       ::= { trimBackup 7 }

trimBackUpConnectDelay OBJECT-TYPE
	SYNTAX  Integer32
	MAX-ACCESS  read-write
	STATUS  current
	DESCRIPTION
     "The connect delay defines the minimum time period that the link must be disconnected."
	::= { trimBackup 8 }

trimBackUpDisConnectDelay OBJECT-TYPE
	SYNTAX  Integer32
	MAX-ACCESS  read-write
	STATUS  current
	DESCRIPTION
		"The disconnect delay defines the delay between the last valid traffic trigger
		  and link disconnection."
	::= { trimBackup 9 }


trimBackUpScheduleTable OBJECT-TYPE
		SYNTAX  SEQUENCE  OF TrimBackUpEntry
		MAX-ACCESS  not-accessible
		STATUS  current
		DESCRIPTION
		       "This is a table that contains the reroute shedule for the backup link.  The index 
			is the day of the week, starting with 1 for Sunday, ending with 7 for 
			Saturday."
	       ::=  { trimBackup 10 }

trimBackUpEntry    OBJECT-TYPE
		SYNTAX  TrimBackUpEntry
		MAX-ACCESS  not-accessible
		STATUS  current
		DESCRIPTION
		"An entry in table trimBackUpScheduleTable."
		INDEX  { trimBackUpDay }
		::=  { trimBackUpScheduleTable 1 }

TrimBackUpEntry ::= SEQUENCE {
		 trimBackUpDay
		 Integer32,
		 trimBackUpFromTo
		 DisplayString
				      }

trimBackUpDay OBJECT-TYPE
		SYNTAX   Integer32
		MAX-ACCESS  read-only
		STATUS  current
		DESCRIPTION
		       "The day of the week for which the entry applies.  The days are numbered from 
		1 to  7, representing Monday through Sunday."
		::= {  trimBackUpEntry 1  }

trimBackUpFromTo OBJECT-TYPE
		SYNTAX  DisplayString
		MAX-ACCESS  read-write
		STATUS  current
		DESCRIPTION
			"This is the time  during which backup should be disabled, expressed
			 as xx:xx-yy:yy, where x's reflect the time from and y's reflect the time 
			to.  The first two digits, in x and in y, are the hour and the second two 
			digits are the minutes.  The pairs of digits are separated by a colon, and the 
			x is separated from the y by a dash."
		::= {  trimBackUpEntry 2  }



trimBackUpDelayAfterFailure OBJECT-TYPE
	SYNTAX  Integer32
	MAX-ACCESS  read-write
	STATUS  current
	DESCRIPTION
		"This entry defines the delay between the last @@@@"
	::= { trimBackup 11 }

-- The trimTR group defines parameters for Token Ring interface management, in addition to parameters
-- defined in the Public Token Ring MIB (RFC 1231).

trimTR    OBJECT IDENTIFIER ::= { trim 3 }

trimTRIfTable  OBJECT-TYPE
    SYNTAX  SEQUENCE  OF TrimTRIfEntry
    MAX-ACCESS  not-accessible
    STATUS  current
    DESCRIPTION
	"This table defines configuration parameters for Token Ring interfaces in the Trimbridge-16."
      ::=  { trimTR 1  }

trimTRIfEntry    OBJECT-TYPE
    SYNTAX  TrimTRIfEntry
    MAX-ACCESS  not-accessible
    STATUS  current
	DESCRIPTION
	"An entry in table trimTRIfTable."
    INDEX  { trimTRIfIndex }
    ::=  { trimTRIfTable 1  }

TrimTRIfEntry ::= SEQUENCE {
    trimTRIfIndex
     Integer32,
    trimTREarlyTokenRelease
     INTEGER,
    trimTRLocalAdminAddress
     MacAddress,
    trimTRLocalAdminAddressStatus
      INTEGER
	  }


trimTRIfIndex OBJECT-TYPE
    SYNTAX   Integer32
    MAX-ACCESS  read-only
    STATUS  current
    DESCRIPTION
	"Index to the Token Ring  Interface Table. The interface defined by a
	particular value of this index is the same interface as
	identified by the same value of ifIndex (MIBII)."
    ::= {  trimTRIfEntry 1  }

trimTREarlyTokenRelease OBJECT-TYPE
    SYNTAX  INTEGER {
       enable(1),
       disable(2)
    }
    MAX-ACCESS  read-write
    STATUS  current
    DESCRIPTION
	 "This parameter controls the early token release. This paramenter
	  is applicable only to 16 Mbps rings."
    ::= {  trimTRIfEntry 2  }

trimTRLocalAdminAddress  OBJECT-TYPE
    SYNTAX MacAddress
    MAX-ACCESS  read-write
    STATUS  current
    DESCRIPTION
	"A locally administered MAC Address of this interface."
    ::= {  trimTRIfEntry 3  }

trimTRLocalAdminAddressStatus OBJECT-TYPE
    SYNTAX  INTEGER {
       enable(1),
       disable(2)
    }
    MAX-ACCESS  read-write
    STATUS  current
    DESCRIPTION
	 "This parameter controls whether the bridge uses the locally administered MAC 
	 Address defined for this interface, when enable(1),  or not ,  when disable(2)."
    ::= {  trimTRIfEntry 4  }
	 
-- The trimTrapInfo group provides information on traps sent from Trimbridge

trimTrapInfo OBJECT IDENTIFIER ::= {trim 4}

trimErrorDesc OBJECT-TYPE
    SYNTAX DisplayString
    MAX-ACCESS  read-only
    STATUS  current
    DESCRIPTION
	"A textual description of the enterprise-specific trap sent
	to the Network Management Station by Trimbridge."
    ::= { trimTrapInfo 1  }

trimErrorSeverity OBJECT-TYPE
    SYNTAX INTEGER {
		  information(1),
		  warning(2),
		  error(3),
		  fatal(4)}
    MAX-ACCESS  read-only
    STATUS  current
    DESCRIPTION
	"The severity type of the enterprise-specific trap sent to the
	Network Management Station by Trimbridge."
    ::= { trimTrapInfo  2  }



-- 
-- file :v:\doc\rdv\mib\ver485\lanrger4.txt
-- 
--Version:   1.0
--Date:   16.10.94              
--By:       Debby Koren & Orly Nicklass
--File:      v:\doc\rdv\mib\ver485\Lanrger4.txt
--

--Last Update: Smadar Tauber 07-July-2002

-- Comments:  The LANRANger also supports the following Public MIBs:
--              - MIB-II  ( RFC1213 )
--              - Token Ring MIB (RFC 1231) or Ethernet MIB (RFC 1398), according to the LAN 
--                 interface
--      - RS-232 MIB (RFC 1317)

 lanranger     OBJECT IDENTIFIER ::= {radBridges 2 }
--   Objects in this MIB are arranged into groups:
--   lanrangerConfig - LANRANger-specific configurable parameters
--   lanrangerInterface  -  LANRANger-specific interface table 
--   lanrangerStation - Tables containing the list of remote workstations and related information
-- and static entries

-- At the end of the MIB there is a definition of all LANRANger-specific traps. 

-- the lanrangerConfig group defines configurable parameters that are specific to the LANRANger
-- product line

lanrangerConfig OBJECT IDENTIFIER ::= { lanranger 1 }

lanrangerLoc   OBJECT-TYPE 
    SYNTAX  INTEGER { 
       main(1),
       remote(2)
    }
    MAX-ACCESS  read-only
    STATUS  current
    DESCRIPTION
	"lanrangerLoc is set to main if the LANRANger is located on the main LAN and it is set to
		 remote if it is located on a LAN at a remote site."
    ::= {  lanrangerConfig 1  }

lanrangerBurnAddress   OBJECT-TYPE 
    SYNTAX  MacAddress 
    MAX-ACCESS  read-only
    STATUS  current
    DESCRIPTION
	"This is the burned-in MacAddress on the LANRANger."
    ::= {  lanrangerConfig 2  }

lanrangerLocAddress   OBJECT-TYPE 
    SYNTAX  MacAddress 
    MAX-ACCESS  read-write
    STATUS  current
    DESCRIPTION
	"This is a locally administered address.  If a zero value appears, the network administrator 
	did  not set a locally administered address."
    ::= {  lanrangerConfig 3 }

lanrangerActiveAddress OBJECT-TYPE
     SYNTAX INTEGER {burnedIn(1), locallyAdministered(2) }
     MAX-ACCESS read-write
     STATUS current
     DESCRIPTION
	 "The MAC address that is in use on the LANRANger. 
	  The address selected will appear in ifPhysAddress."
     ::= { lanrangerConfig 4 }


lanrangerLearningStationTopology OBJECT-TYPE
     SYNTAX INTEGER { dynamic             (1),
                      permanent           (2),
                      permanentAndDynamic (3)
                    }
     MAX-ACCESS read-write
     STATUS current
     DESCRIPTION
         "The Learning station topology defines for the 
          LANRANger which type of station will be inserted 
          in the station list. 
          The default value is permanentAndDynamic(3).
 
             dynamic(1)   - Learning lan station only. 
             permanent(2) - 
             permanentAndDynamic(3)-
             
          Setting this parameter will reset the LANRANger . 
                                      -----                "
     ::= { lanrangerConfig 5 }


lanrangerIpRouterInfo OBJECT IDENTIFIER
     ::= { lanrangerConfig 6 }

  lanrangerIpDefaultLink  OBJECT-TYPE
       SYNTAX Integer32 
       MAX-ACCESS read-write
       STATUS current
       DESCRIPTION
        "The default selected link, having the numbering system of ifIndex. 
         The valid values range is: 1..ifIndex.
         The value must remain constant at least from one
         re-initialization of the network management agent to
         the next.
         notSupported = 255 "
       ::= { lanrangerIpRouterInfo 1 }

  lanrangerIpFastReTxLevel  OBJECT-TYPE
       SYNTAX Integer32 
       MAX-ACCESS read-write
       STATUS current
       DESCRIPTION
         " The maximum buffer depth (queue length) for which lanranger 
           will accept retransmission (for each station; the level
           is the same for all the stations).
           The valid values range is: 1..255 .    "
       ::= { lanrangerIpRouterInfo 2 }

  lanrangerIpAgingTimeout OBJECT-TYPE
      SYNTAX  Integer32
      MAX-ACCESS  read-write
      STATUS  current
      DESCRIPTION
         " Ip aging time for a station - in min. "
       ::= { lanrangerIpRouterInfo 3 }

--BOOT-P parameters; are relevant only for routers 

   lanrangerIpBootP OBJECT IDENTIFIER
       ::= { lanrangerIpRouterInfo 4 }

    lanrangerBootPAction  OBJECT-TYPE
       SYNTAX INTEGER { 
       disable (2),
       enable (3)
       }
       MAX-ACCESS read-write
       STATUS current
       DESCRIPTION
           "Activating (disable/enable) the BootP operation."
       ::= { lanrangerIpBootP 1 }

    lanrangerBootPAvailableEntries OBJECT-TYPE
       SYNTAX  Integer32
       MAX-ACCESS  read-only
       STATUS  current
       DESCRIPTION
         "The number of available entries in the BootP table."
       ::= { lanrangerIpBootP 2 }

    lanrangerBootPCurrentEntries OBJECT-TYPE
       SYNTAX  Integer32
       MAX-ACCESS  read-only
       STATUS  current
       DESCRIPTION
         "The current number of BootP entries in the BootP table."
       ::= { lanrangerIpBootP 3 }

    lanrangerBootPTable OBJECT-TYPE
       SYNTAX SEQUENCE OF LanrangerBootPEntry
       MAX-ACCESS not-accessible
       STATUS current
       DESCRIPTION
          "A list of BootP entries.  The number of entries is up to
           BootP current entries, according to the LANRANger model."
       ::= { lanrangerIpBootP 4 }

    lanrangerBootPEntry OBJECT-TYPE
       SYNTAX  LanrangerBootPEntry
       MAX-ACCESS  not-accessible
       STATUS  current
       DESCRIPTION
           "BootP parameters per entry of the BootP table."
       INDEX   { lanrangerBootPIpAddress }
       ::= { lanrangerBootPTable 1 }

    LanrangerBootPEntry ::=
       SEQUENCE {
              lanrangerBootPIpAddress
                 IpAddress,
              lanrangerBootPIfIndex
                 INTEGER,
              lanrangerBootPOperation
                 INTEGER
          }

    lanrangerBootPIpAddress OBJECT-TYPE
        SYNTAX  IpAddress
        MAX-ACCESS  read-write
        STATUS  current
        DESCRIPTION
             "BootP Ip Address."
        ::= { lanrangerBootPEntry 1 }

    lanrangerBootPIfIndex OBJECT-TYPE
        SYNTAX  INTEGER	 {notAllocated (255)}
        MAX-ACCESS  read-write
        STATUS  current
        DESCRIPTION
             "The number is the same as the ifIndex of the link."
        ::= { lanrangerBootPEntry 2 }

   lanrangerBootPOperation OBJECT-TYPE
      SYNTAX  INTEGER {
                     active (1),
                     delete (2)
             }
      MAX-ACCESS  read-write
      STATUS  current
      DESCRIPTION
             "This object indicates the status of this entry.
                active(1) - this entry is currently in use
                            and will remain so even after the next
                            reset of the LANRANger.
                delete(2) - writing this value to the object,
                            removes the corresponding entry from the
                            table. "
      ::= { lanrangerBootPEntry 3 }


lanrangerSpoofingInfo OBJECT IDENTIFIER
     ::= { lanrangerConfig 7 }

  lanrangerSpoofingAction  OBJECT-TYPE
       SYNTAX Integer32 
       MAX-ACCESS read-write
       STATUS current
       DESCRIPTION
	"Spoofing action is applied by bit code:
         enable        :  bit 0 set (disable: bit 0 is 0)
         keepAlive     :  bit 1
            ...        :  bit 2
         and so on.
         For the above example, to set spoofing to keepAlive action,
         the object's value will be 3 = [ 2**0 + 2**1 ] 
         Only the Remote LANRANger will accept this object !
                  -------                                  "
       ::= { lanrangerSpoofingInfo 1 }

  lanrangerSpoofingAgingStation  OBJECT-TYPE
       SYNTAX Integer32 
       MAX-ACCESS read-write
       STATUS current
       DESCRIPTION
         " Aging time of stations list, in min. The agent 'translates'
           the time entered in minutes, to 10 min. resolution, as
		   follows: 
		   1..10  min - 10 min
		   11..20 min - 20 min
		   and so on...
		   0 is not a valid value.
           Only the Remote LANRANger will accept this object !
                    ----------------                          "
       ::= { lanrangerSpoofingInfo 2 }



--    The variables in the lanrangerInterface group define LANRANger-specific and other 
--    link parameters and information

lanrangerInterface OBJECT IDENTIFIER ::= { lanranger 2 }

lanrangerLinkTable OBJECT-TYPE
      SYNTAX SEQUENCE OF LanrangerLinkEntry
      MAX-ACCESS not-accessible
      STATUS current
      DESCRIPTION
	  "A list of link entries.  The number of entries is
	   up to 8, according to the LANRANger model."
      ::= { lanrangerInterface 1 }

lanrangerLinkEntry OBJECT-TYPE
    SYNTAX LanrangerLinkEntry
    MAX-ACCESS not-accessible
    STATUS current
    DESCRIPTION
	"LANRANger-specific parameter values for a link."
    INDEX {lanrangerLinkIndex }
    ::= { lanrangerLinkTable 1 }

LanrangerLinkEntry ::=
    SEQUENCE {
	lanrangerLinkIndex
	    Integer32,
	lanrangerLinkType
	    INTEGER ,
	lanrangerLinkState
	    INTEGER,
	lanrangerLinkDTRMode
	    INTEGER,
	lanrangerLinkStatus
	    INTEGER,
	lanrangerLinkConnectionStatus
	    INTEGER,
	lanrangerLinkNumOfLogLinks
	    Integer32,
	lanrangerLinkReset
	    INTEGER,
    lanrangerLinkRxMaskedFrames
	    Counter32,
    lanrangerLinkLayer2Type
        INTEGER,
    lanrangerLinkLayer3Type
        INTEGER,
	lanrangerBackupLink
	    Integer32,
    wrWanThrottle
        Integer32
    }

lanrangerLinkIndex OBJECT-TYPE
    SYNTAX Integer32
    MAX-ACCESS read-only
    STATUS current
    DESCRIPTION
	"A unique value for each link, equal to the value of ifIndex. 
	 The value for each link must remain constant at least 
	 from one re-initialization of the network management agent to
	 the next."
    ::= { lanrangerLinkEntry 1 }

lanrangerLinkType OBJECT-TYPE
     SYNTAX INTEGER { 
         synchronous    (1),
         asynchronous   (2),
         x25FRconfig    (3),
         x25FRchannel   (4),
         isdn           (5),
         frameRelay     (6),
         pcmcia         (7),
         dm2wire        (8),
         notExist       (254),
		 unknown        (255)
         }
     MAX-ACCESS read-write
     STATUS current
     DESCRIPTION
	 "The link type ."
     ::= { lanrangerLinkEntry 2 }

lanrangerLinkState OBJECT-TYPE
     SYNTAX INTEGER {      
     disable(2),
     enable (3),
	 backup (4)
      }
     MAX-ACCESS read-write
     STATUS current
     DESCRIPTION
	 "The link is  disabled, enabled or backup."
     ::= { lanrangerLinkEntry 3 }

lanrangerLinkDTRMode OBJECT-TYPE
     SYNTAX INTEGER {  off(2), on(3), unknown(255)  }
     MAX-ACCESS read-only
     STATUS current
     DESCRIPTION
	 "The link DTR mode."
     ::= { lanrangerLinkEntry 4 }

lanrangerLinkStatus OBJECT-TYPE
     SYNTAX INTEGER { 
     ok         (1), 
     fail       (2), 
     rxNoClock  (3), 
     txProblem  (4),
     noCarrierD (5),
	 unknown    (255)
      }
     MAX-ACCESS read-only
     STATUS current
     DESCRIPTION
	 "The link  physical status ."
     ::= { lanrangerLinkEntry 5 }

lanrangerLinkConnectionStatus OBJECT-TYPE
     SYNTAX INTEGER { 
     fail      (1), 
     disconnect(2), 
     connect   (3),
     wait      (4),
     down      (5),
	 trying    (6),
	 testing   (7),
	 unknown   (255)
     }
     MAX-ACCESS read-only
     STATUS current
     DESCRIPTION
	 "The link connection status."
     ::= { lanrangerLinkEntry 6 }

lanrangerLinkNumOfLogLinks OBJECT-TYPE
     SYNTAX Integer32	
     MAX-ACCESS read-only
     STATUS current
     DESCRIPTION
	 "The number of logical links on this physical link.
	  0 = noLogicalLink "
     ::= { lanrangerLinkEntry 7 }

lanrangerLinkReset OBJECT-TYPE
     SYNTAX   INTEGER {     
     off(2),
     on (3)  
     }
     MAX-ACCESS read-write
     STATUS current
     DESCRIPTION
	 "Setting this attribute to ON will reset the link . Upon completion the value will be set to OFF"
     ::= { lanrangerLinkEntry 8 }

lanrangerLinkRxMaskedFrames OBJECT-TYPE
     SYNTAX  Counter32
     MAX-ACCESS read-only
     STATUS current
     DESCRIPTION
	 "The number of masked frames received on this physical link."
     ::= { lanrangerLinkEntry 9 }

lanrangerLinkLayer2Type OBJECT-TYPE
     SYNTAX INTEGER {
              unknown         (1),
              bridge          (2),
              ipRouter        (3),
              ipxRouter       (4),
              ipAndIpxRouter  (5),
              bRouter         (6),
			  ipBrouter       (7),
			  ipxBrouter      (8),
			  ipAndIpxBrouter (9),
			  bridgeAndStp    (10)
              }
     MAX-ACCESS read-write
     STATUS current
     DESCRIPTION
         "The link layer 2 type indicates whether the link is Bridge 
          or Router	and specifies the Router's type."
     ::= { lanrangerLinkEntry 10 }

lanrangerLinkLayer3Type OBJECT-TYPE
     SYNTAX INTEGER {
              unknown        (1),
              proprietary    (2),
			  terminalServer (3),
              slip          (30),
              cSlip         (31),
              ppp           (40),
			  rfc1490       (41),
			  hdlcFraming   (42),
			  mlPpp         (43)
              }
     MAX-ACCESS read-write
     STATUS current
     DESCRIPTION
         "The link layer 3 type indicates the protocol type."
     ::= { lanrangerLinkEntry 11 }

lanrangerBackupLink OBJECT-TYPE
     SYNTAX   Integer32
     MAX-ACCESS read-write
     STATUS current
     DESCRIPTION
	 "The backup link interface index located in the two LSB bytes. 
	  If the link is FR type, the two MSB will contain a DLCi number. 
	  For other link types the two MSB will equal to 0."
     ::= { lanrangerLinkEntry 12 }

wrWanThrottle OBJECT-TYPE
     SYNTAX   Integer32
     MAX-ACCESS read-write
     STATUS current
     DESCRIPTION
	 "Throttle controls the baud rate of the WAN.
      For example if we have a WAN rate of 2M but we want only 1/2 M as 
      the baud rate we set the Wan Throttle to 512k.
      
      These are the values:
      Full (2),
      1M (3),
      512k (4),
      128k (5),
      64k (6)
      
      Full throttle option (2) means  the LAN rate."
     ::= { lanrangerLinkEntry 13 }


--Link Connections

lanrangerLinkConnection OBJECT IDENTIFIER
     ::= { lanrangerInterface 2 }

   lanrangerConnMaxEntries OBJECT-TYPE
      SYNTAX  Integer32
      MAX-ACCESS  read-only
      STATUS  current
      DESCRIPTION
        "The maximum number of entries in the Connection table."
      ::= { lanrangerLinkConnection 1 }

   lanrangerConnCurrentEntries OBJECT-TYPE
      SYNTAX  Integer32
      MAX-ACCESS  read-only
      STATUS  current
      DESCRIPTION
        "The current number of entries in the Connection table."
      ::= { lanrangerLinkConnection 2 }

   lanrangerLinkConnTable OBJECT-TYPE
      SYNTAX SEQUENCE OF LanrangerLinkConnEntry
      MAX-ACCESS not-accessible
      STATUS current
      DESCRIPTION
         "A list of Connection entries.  The number of entries is
          up to Max entries, according to the LANRANger model."
      ::= { lanrangerLinkConnection 3 }

   lanrangerLinkConnEntry OBJECT-TYPE
     SYNTAX LanrangerLinkConnEntry
     MAX-ACCESS not-accessible
     STATUS current
     DESCRIPTION
        "Information about LANRANger Connection."
     INDEX {lanrangerLinkConnPhysLink, lanrangerLinkConnAid,
            lanrangerLinkConnMacAddr }
     ::= { lanrangerLinkConnTable 1 }

   LanrangerLinkConnEntry ::=
       SEQUENCE {
           lanrangerLinkConnPhysLink
               Integer32 ,
           lanrangerLinkConnAid
               Integer32,
           lanrangerLinkConnMacAddr
               MacAddress,  
           lanrangerLinkConnStatus
               INTEGER,
           lanrangerLinkConnDeviceType
               INTEGER,
           lanrangerLinkConnDeviceName
               DisplayString,
           lanrangerLinkConnDeviceSWVer
               DisplayString,
           lanrangerLinkConnNumLanStation
               Integer32,
           lanrangerLinkSyncStatus
               INTEGER
   	}
   
   lanrangerLinkConnPhysLink OBJECT-TYPE
        SYNTAX Integer32  
        MAX-ACCESS read-only
        STATUS current
        DESCRIPTION
            "The lanrangerLinkIndex for the physical link with which this logical link is associated."
         ::= { lanrangerLinkConnEntry 1 }
           
   lanrangerLinkConnAid OBJECT-TYPE
       SYNTAX Integer32 
       MAX-ACCESS read-only
       STATUS current
       DESCRIPTION
           "A unique value for each logical link.  The maximum number 
            of logical links is 256, according to the LANRANger model.  
            The value for each logical link must remain constant at least 
            from one re-initialization of the network management agent to
            the next.  This index is the SPS address of the logical link.
            noLogicLink = 65535"
       ::= { lanrangerLinkConnEntry 2 }
   
   lanrangerLinkConnMacAddr OBJECT-TYPE
       SYNTAX  MacAddress
       MAX-ACCESS  read-only
       STATUS  current
       DESCRIPTION
           "The MAC address of the device that the logical link is connected to
            on the remote LAN."
     ::= { lanrangerLinkConnEntry 3 }
   
   lanrangerLinkConnStatus OBJECT-TYPE
     SYNTAX INTEGER { 
              unknown        (1), -- for router link
              none           (2), -- no connection
              fail           (3),
              connect        (4),
              wait           (5),
              down           (6)
             }
     MAX-ACCESS read-only
     STATUS current
     DESCRIPTION
         "The link connection status."
     ::= { lanrangerLinkConnEntry 4 }
   
   lanrangerLinkConnDeviceType OBJECT-TYPE
        SYNTAX  INTEGER {
                      tre1      (1),
                      tre8      (2),
                      tre1D     (3),
                      tre8D     (4),
                      tre8M     (5),
                      rrTre     (6),
                      rrTre1D   (7),
                      rrTre8D   (8),
                      iTre1     (9),
                      iTre2     (10),
                      mpTre8    (11),
                      kTre8     (12),
                      treRasA   (13),
                      treRasS   (14),
                      trePCAsync(15),
                      trePCSync (16),
                      mbe1      (17),
                      mbe8      (18),
                      mbe1D     (19),
                      mbe8D     (20),
                      ete8M     (21),
                      iEre1     (22),
                      iEe2      (23),
                      mpMbe8    (24),
                      kMbe8     (25),
                      mbePCAsync(26),
                      mbePCSync (27),
                      mbeRasA   (28),
                      mbeRasS   (29),
   	        other(255)  
                   }
       MAX-ACCESS  read-only
       STATUS  current
       DESCRIPTION
               "The type of device that the logical link is connected to on the remote LAN."
       ::= { lanrangerLinkConnEntry 5 }
   
   lanrangerLinkConnDeviceName  OBJECT-TYPE
       SYNTAX  DisplayString  
       MAX-ACCESS  read-only
       STATUS  current
       DESCRIPTION
            "The logical name of the device that the logical link is connected to on the remote LAN."
       ::= { lanrangerLinkConnEntry 6 }

   lanrangerLinkConnDeviceSWVer  OBJECT-TYPE
       SYNTAX  DisplayString  
       MAX-ACCESS  read-only
       STATUS  current
       DESCRIPTION
            "SW Version of the device that the logical link is 
             connected to, on the remote LAN."
       ::= { lanrangerLinkConnEntry 7 }

   lanrangerLinkConnNumLanStation OBJECT-TYPE
     SYNTAX Integer32 
     MAX-ACCESS read-only
     STATUS current
     DESCRIPTION
         "The number of stations of the remote LAN."
     ::= { lanrangerLinkConnEntry 8 }

lanrangerLinkSyncStatus OBJECT-TYPE
     SYNTAX INTEGER { 
              synchronized        (1), 
              syncNotObtained     (2), 
              waitForSync         (3),
              codDisconnected     (4),
              lcp                 (5),
              ip                  (6),
              ipvj                (7),
              ipx                 (8),
              ipIpx               (9),
              ipvj-ipx            (10),
              mlPpp               (11),
              mlPpp-ip            (12),
              mlPpp-ip-ipvj       (13),
              mlPpp-ip-ipx        (14),
              mlPpp-ipvj-ipx      (15),
              mlPpp-ipx           (16),
              frUp                (17),
              frDown              (18),
              dlciUp              (19),
              dlciDown            (20),
              extLoop             (21),
              ipcp                (22),
              lcpIpcp             (23),
			  redAlarm            (24),
			  yellowAlarm         (26),
			  localSyncLoss       (27),
			  remoteSyncLoss      (28),
			  networkLoop         (29),
			  networkLoopRedAlarm (30),
			  networkLoopYelAlarm (31),
			  networkLocSyncLoss  (32),
			  networkRemSyncLoss  (33),
			  fdlLoop             (34),
			  fdlLoopRedAlarm     (35),
			  fdlLoopYellowAlarm  (36),
			  fdlLoopLocSyncLoss  (37),
			  fdlLoopRemSyncLoss  (38),
			  loopback            (39),  -- User Loop
			  loopbackLocSyncLoss (40),
			  loopbackRemSyncLoss (41)			  
             }
     MAX-ACCESS read-only
     STATUS current
     DESCRIPTION
         "The Sync link status."
     ::= { lanrangerLinkConnEntry 9 }


--Modem Table

lanrangerModemTable OBJECT-TYPE
      SYNTAX SEQUENCE OF LanrangerModemEntry
      MAX-ACCESS not-accessible
      STATUS current
      DESCRIPTION
          "A list of Modem entries.  The number of entries is
           up to ifIndex."
      ::= { lanrangerInterface 3 }

lanrangerModemEntry OBJECT-TYPE
    SYNTAX LanrangerModemEntry
    MAX-ACCESS not-accessible
    STATUS current
    DESCRIPTION
        "LANRANger-specific parameter values for a Modem."
    INDEX {lanrangerModemLinkIndex }
    ::= { lanrangerModemTable 1 }

LanrangerModemEntry ::=
    SEQUENCE {
        lanrangerModemLinkIndex
            Integer32,
        lanrangerModemName
            DisplayString,
        lanrangerModemSettingString
            DisplayString,
        lanrangerModemAutobaudingSpeed
            INTEGER,
        lanrangerModemResetBeforeSetup
            INTEGER,
        lanrangerModemAnalyzeAnswers
            INTEGER,
        lanrangerModemSpeaker
            INTEGER,
        lanrangerModemDialingNumber
            DisplayString,
        lanrangerModemDialRetries             
            Integer32,
        wrLocalDialBackNumber
            DisplayString,
        wrRingsBeforeAnswer
            Integer32
   }

lanrangerModemLinkIndex OBJECT-TYPE
    SYNTAX Integer32
    MAX-ACCESS read-write
    STATUS current
    DESCRIPTION
        "A list of asynchronous ports of the link, according to 
         ifIndex. 
         Synchronous ports will not appear in this table. Their
         port number will be skipped."
    ::= { lanrangerModemEntry 1 }


lanrangerModemName OBJECT-TYPE
    SYNTAX DisplayString
    MAX-ACCESS read-write
    STATUS current
    DESCRIPTION
        "The Modem Name identifier for MBE/TRE.
         Up to 50 characters."
    ::= { lanrangerModemEntry 2 }

lanrangerModemSettingString OBJECT-TYPE
    SYNTAX DisplayString
    MAX-ACCESS read-write
    STATUS current
    DESCRIPTION
        "Modem setting String.
         Up to 80 characters."
    ::= { lanrangerModemEntry 3 }


lanrangerModemAutobaudingSpeed OBJECT-TYPE
     SYNTAX  INTEGER {
                 disable(2),
                 enable (3)
             }
     MAX-ACCESS  read-write
     STATUS  current
     DESCRIPTION
         "Enable or disable autobauding.
          When the Autobauding feature is enabled, the MBE/TRE 
          automatically ranges over various Baud rates, starting 
          with 115.2 Kbps, until the correct Baud rate of the modem 
          is detected. "
    ::= { lanrangerModemEntry 4 }


lanrangerModemResetBeforeSetup OBJECT-TYPE
     SYNTAX  INTEGER {
                 no (2),
                 yes(3)
             }
     MAX-ACCESS  read-write
     STATUS  current
     DESCRIPTION
         "Reset the modem before setup is performed.
          It is recommended to reset the modem before  modem setup 
          session.     "
    ::= { lanrangerModemEntry 5 }


lanrangerModemAnalyzeAnswers OBJECT-TYPE
     SYNTAX  INTEGER {
                 disable(2),
                 enable (3)
             }
     MAX-ACCESS  read-write
     STATUS  current
     DESCRIPTION
         "Enable this option if a modem using non-standard answering is used.
          When this mode is enabled, the MBE/TRE awaits modem answers
          'CONNECT', 'CARRIER', or 'OK', after it transmits a modem command.
          Modem answers acknowledge, that a specific command has been executed.
          If this option is not enabled, the MBE/TRE waits for a modem answer
          for three seconds. If no answer has been received during this period,
          the MBE/TRE continues functioning as if the modem command was successfully
          executed. However, when dialing out, the MBE/TRE waits for one minute 
          for connection."
    ::= { lanrangerModemEntry 6 }

lanrangerModemSpeaker OBJECT-TYPE
     SYNTAX  INTEGER {
                 off (2),
                 on  (3)
             }
     MAX-ACCESS  read-write
     STATUS  current
     DESCRIPTION
         "Toggle the Modem Speaker On or Off . "
    ::= { lanrangerModemEntry 7 }


lanrangerModemDialingNumber OBJECT-TYPE
    SYNTAX DisplayString
    MAX-ACCESS read-write
    STATUS current
    DESCRIPTION
        " Various command switches listed in Modem Dialing Number Menu
          allows selection of tone, pulse-dialing, or various wait states.
          P - Set Pulse dialing number .
          T - Set Tone  dialing number .
          W - Wait for dialing tone before proceeding.
          ' - Pause for 2 seconds .
          @ - Wait for silence, one ring, followed by 5 sec. of silence .

          The Dialing Number will include both digits and letter/s 
          of the command switches. The order and validity will be 
          on user's responsibility.   
          The DisplayString can have up to 40 characters."
    ::= { lanrangerModemEntry 8 }


wrLocalDialBackNumber OBJECT-TYPE
    SYNTAX DisplayString
    MAX-ACCESS read-write
    STATUS current
    DESCRIPTION
        " This is the number that the Remote Modem will use to call the local
          Modem at Dial Back.

          Various command switches listed in Modem Dialing Number Menu
          allows selection of tone, pulse-dialing, or various wait states.
          P - Set Pulse dialing number .
          T - Set Tone  dialing number .
          W - Wait for dialing tone before proceeding.
          ' - Pause for 2 seconds .
          @ - Wait for silence, one ring, followed by 5 sec. of silence .

          The Dialing Number will include both digits and letter/s 
          of the command switches. The order and validity will be 
          on user's responsibility.   
          The DisplayString can have up to 40 characters."
    ::= { lanrangerModemEntry 9 }


wrRingsBeforeAnswer  OBJECT-TYPE
     SYNTAX  Integer32 
     MAX-ACCESS  read-write
     STATUS  current
     DESCRIPTION
            "Determines which ring the modem will wait to answer the
            phone on."
    ::= { lanrangerModemEntry 10 }          
                  


lanrangerModemDialRetries OBJECT-TYPE
      SYNTAX  Integer32  (0..8)
      MAX-ACCESS  read-write
      STATUS  current
      DESCRIPTION
           "The number of dialing retries requested.
            Default = 0"
      ::= { lanrangerModemEntry 11}

--Packet Switch Table

lanrangerLinkPktSwTable OBJECT-TYPE
      SYNTAX SEQUENCE OF LanrangerLinkPktSwEntry
      MAX-ACCESS not-accessible
      STATUS current
      DESCRIPTION
          "A list of X.25/FR modules entries.  The number of entries is
           up to ifIndex."
      ::= { lanrangerInterface 4 }

lanrangerLinkPktSwEntry OBJECT-TYPE
    SYNTAX LanrangerLinkPktSwEntry
    MAX-ACCESS not-accessible
    STATUS current
    DESCRIPTION
        "LANRANger-specific parameter values for  X.25/FR modules."
    INDEX {lanrangerLinkPktSwIndex }
    ::= { lanrangerLinkPktSwTable 1 }

LanrangerLinkPktSwEntry ::=
    SEQUENCE {
        lanrangerLinkPktSwIndex
            Integer32,
        lanrangerLinkPktSwType
            INTEGER,
        lanrangerLinkPktSwControlSignal
            INTEGER,
        lanrangerLinkPktSwSpeed
            Integer32,
        lanrangerLinkPktSwConfigParity
            INTEGER,
        lanrangerLinkPktSwConfigStopBit
            INTEGER,
        lanrangerLinkPktSwResetModule
            INTEGER
       }

lanrangerLinkPktSwIndex OBJECT-TYPE
    SYNTAX Integer32
    MAX-ACCESS read-write
    STATUS current
    DESCRIPTION
        "A unique value for each X.25/FR of the link, according to 
         numbering system of ifIndex. The maximum number of links is 
         ifIndex. The value for each link must remain constant at 
         least from one re-initialization of the network management 
         agent to the next."
    ::= { lanrangerLinkPktSwEntry 1 }

lanrangerLinkPktSwType OBJECT-TYPE
    SYNTAX INTEGER {
            x25FRChannel (1),
            x25FRConfig  (2)
            }
    MAX-ACCESS read-only
    STATUS current
    DESCRIPTION
        "Packet Switch Type."
    ::= { lanrangerLinkPktSwEntry 2 }

lanrangerLinkPktSwControlSignal OBJECT-TYPE
    SYNTAX INTEGER {
            off(2),
            on (3)
            }
    MAX-ACCESS read-write
    STATUS current
    DESCRIPTION
        "Packet Switch control command. "
    ::= { lanrangerLinkPktSwEntry 3 }

lanrangerLinkPktSwSpeed OBJECT-TYPE
    SYNTAX Integer32
    MAX-ACCESS read-write
    STATUS current
    DESCRIPTION
        "The Pkt Switch  port's speed in bits per second.
         Range: 1200bps .. 1544000bps"
    ::= { lanrangerLinkPktSwEntry 4 }

lanrangerLinkPktSwConfigParity OBJECT-TYPE
    SYNTAX INTEGER { none(1), odd(2), even(3), notApplicable(255)}
    MAX-ACCESS read-write
    STATUS current
    DESCRIPTION
        "The Pkt Switch Config port's character parity bit.
         Applicable only for x25FRConfigChannel. For x25FRChannel
         the value notApplicable applies."
    ::= { lanrangerLinkPktSwEntry 5 }

lanrangerLinkPktSwConfigStopBit OBJECT-TYPE
    SYNTAX INTEGER { one(1), two(2), notApplicable(255) }
    MAX-ACCESS read-write
    STATUS current
    DESCRIPTION
        "The Pkt Switch Config port's number of stop bits.
         Applicable only for x25FRConfigChannel. For x25FRChannel
         the value notApplicable applies."
    ::= { lanrangerLinkPktSwEntry 6 }

lanrangerLinkPktSwResetModule OBJECT-TYPE
    SYNTAX INTEGER { 
    off(2),
    on (3) 
    }
    MAX-ACCESS read-write
    STATUS current
    DESCRIPTION
        "Reset command to Pkt Switch module. 
         Applicable only for x25FRChannel.
         The command will have no effect on x25FRConfigChannel."
    ::= { lanrangerLinkPktSwEntry 7 }



-- lanrangerStation group contains a list of remote workstations and related information

lanrangerStation OBJECT IDENTIFIER ::= {lanranger 3}

lanrangerStationTable OBJECT-TYPE
      SYNTAX  SEQUENCE OF LanrangerStationEntry
      MAX-ACCESS  not-accessible
      STATUS  current
      DESCRIPTION
		      "A table that contains information about the stations 
		       on the remote LAN(s).
		       A remote LANRANger contains a list of stations on its 
		       LAN, while a main LANRANger contains a list of 
		       stations at all the remote sites it is connected to."
      ::= { lanrangerStation 1 }

lanrangerStationEntry OBJECT-TYPE
     SYNTAX LanrangerStationEntry
    MAX-ACCESS  not-accessible
    STATUS  current
    DESCRIPTION
	      "Information about a specific station, that the LANRANger 
	       lists as being on a remote LAN."
 INDEX { lanrangerStationPhysLink, lanrangerStationLogLink,	lanrangerStationAddress}
    ::= { lanrangerStationTable 1 }

LanrangerStationEntry ::=
      SEQUENCE {
	lanrangerStationPhysLink
	      Integer32,
	lanrangerStationLogLink
	      Integer32,
	lanrangerStationAddress
	      MacAddress,
	lanrangerStationStatus
	      INTEGER,
	lanrangerStationSpoofingStatus
	      INTEGER
      }

lanrangerStationPhysLink OBJECT-TYPE
     SYNTAX  Integer32
    MAX-ACCESS  read-only
    STATUS  current
    DESCRIPTION
	    "The number of the physical link that is connected to the 
	     remote LAN on which the station with the associated 
	     instance of lanrangerStationAddress is located. The number 
	     is the same as the ifIndex of the link. The value will be 
	     zero on a remote LANRANger"
    ::= { lanrangerStationEntry 1 }

lanrangerStationLogLink OBJECT-TYPE
     SYNTAX  Integer32 
     MAX-ACCESS  read-only
     STATUS  current
     DESCRIPTION
	   "The number of the logical link that is connected
	    to the remote LAN on which the station with the associated 
	    instance of lanrangerStationAddress	is located.  The value 
	    will be zero on a remote LANRANger.
	    noLogicLink = 65535"
     ::= { lanrangerStationEntry 2 }

lanrangerStationAddress OBJECT-TYPE
     SYNTAX  MacAddress
     MAX-ACCESS  read-only
     STATUS  current
     DESCRIPTION
	     "The unicast MAC address  of a station that the LANRANger 
	     lists as being on a remote LAN."
     ::= { lanrangerStationEntry 3 }

lanrangerStationStatus OBJECT-TYPE
     SYNTAX  INTEGER {
		 unknown(1),
		 learned(2),
		 self   (3),
		 static (4)
	     }
     MAX-ACCESS  read-only
     STATUS  current
     DESCRIPTION
	 "The status of this entry.  The meanings of the
      values are:
		unknown(1) : 
	    learned(2) : the value of the corresponding 
		       	   instance of lanrangerStationAddress was
			       learned and is being used.

		self(3)    : the value of the corresponding
			         instance of lanrangerStationAddress
			         represents the LANRANger's address.
			           

		static(4)  : the value of the corresponding
			         instance of lanrangerStationAddress is
			         also the value of an existing
			         instance of lanrangerStaticAddress."
      ::= { lanrangerStationEntry 4 }

lanrangerStationSpoofingStatus OBJECT-TYPE
   SYNTAX  INTEGER { 
   off(2),
   on (3) 
   }
   MAX-ACCESS  read-only
   STATUS  current
   DESCRIPTION
     "The spoofing status of this entry."
     ::= { lanrangerStationEntry 5 }



lanrangerLanMaxStations OBJECT-TYPE
   SYNTAX  Integer32
   MAX-ACCESS  read-only
   STATUS  current
   DESCRIPTION
     "The maximum number of stations in the station table."
     ::= { lanrangerStation 2 }

lanrangerLanCurrentStations OBJECT-TYPE
   SYNTAX  Integer32
   MAX-ACCESS  read-only
   STATUS  current
   DESCRIPTION
     "The current number of stations in the station table."
     ::= { lanrangerStation 3 }

--Permanent Stations


lanrangerPermanentStation OBJECT IDENTIFIER
     ::= { lanrangerStation 4 }

   lanrangerPermanentMaxEntries OBJECT-TYPE
      SYNTAX  Integer32
      MAX-ACCESS  read-only
      STATUS  current
      DESCRIPTION
        "The maximum number of entries in the permanent stations table."
      ::= { lanrangerPermanentStation 1 }

   lanrangerPermanentCurrentEntries OBJECT-TYPE
      SYNTAX  Integer32
      MAX-ACCESS  read-only
      STATUS  current
      DESCRIPTION
        "The current number of entries in the permanent stations table."
      ::= { lanrangerPermanentStation 2 }


   lanrangerPermanentTable OBJECT-TYPE
      SYNTAX  SEQUENCE OF LanrangerPermanentEntry
      MAX-ACCESS  not-accessible
      STATUS  current
      DESCRIPTION
          "A table containing address information
           configured into the LANRANger by (local or network)
           management, specifying addresses on a remote LAN. 
           This table objects can be set only on a Remote LANRANger."
      ::= { lanrangerPermanentStation 3 }

   lanrangerPermanentEntry OBJECT-TYPE
      SYNTAX  LanrangerPermanentEntry
      MAX-ACCESS  not-accessible
      STATUS  current
      DESCRIPTION
            "Address information configured into the remote LANRANger
             by (local or network) management specifying addresses 
             on a remote LAN."
      INDEX   { lanrangerPermanentIfIndex, lanrangerPermanentLogLink, 
                lanrangerPermanentAddress }
      ::= { lanrangerPermanentTable 1 }

   LanrangerPermanentEntry ::=
      SEQUENCE {
        lanrangerPermanentIfIndex 
   	  	Integer32,
        lanrangerPermanentLogLink 
		Integer32,
        lanrangerPermanentAddress
        MacAddress,
        lanrangerPermanentOperation
        INTEGER
         }
   lanrangerPermanentIfIndex OBJECT-TYPE
      SYNTAX  Integer32
      MAX-ACCESS  read-only
      STATUS  current
      DESCRIPTION
            "The number of the physical link that is connected to 
             the remote LAN, on which the station with the 
             associated instance of lanrangerStationAddress is 
             located.
             The number is the same as the ifIndex of the link.
             This data is interesting for main LANRANger only."
      ::= { lanrangerPermanentEntry 1 }

   lanrangerPermanentLogLink OBJECT-TYPE
      SYNTAX  Integer32 
      MAX-ACCESS  read-only
      STATUS  current
      DESCRIPTION
           "The number of the logical link that is connected to the
            remote LAN, on which the station with the associated 
            instance of lanrangerPermanentAddress is located.
            The value will be noLogicLink on a remote LANRANger.
            This data is interesting for main LANRANger only.
            noLogicLink = 65535"
      ::= { lanrangerPermanentEntry 2 }

   lanrangerPermanentAddress OBJECT-TYPE
      SYNTAX  MacAddress
      MAX-ACCESS  read-write
      STATUS  current
      DESCRIPTION
             "The  MAC address  entered by management to this entry. 
              Only the remote LANRANger will accept Set for this object !
                       ----------------                          "
      ::= { lanrangerPermanentEntry 3 }

   lanrangerPermanentOperation OBJECT-TYPE
      SYNTAX  INTEGER {
                     active (1),
                     delete (2)
             }
      MAX-ACCESS  read-write
      STATUS  current
      DESCRIPTION
             "This object indicates the status of this entry.
                active(1) - this entry is currently in use
                            and will remain so even after the next
                            reset of the LANRANger.
                delete(2) - writing this value to the object
                            removes the corresponding entry. 
              Only the remote LANRANger will accept Set for this object !
                       ----------------               "
      ::= { lanrangerPermanentEntry 4 }


--IP Stations

lanrangerIpStation OBJECT IDENTIFIER
     ::= { lanrangerStation 5 }

   lanrangerIpPermanentAvailableEntries OBJECT-TYPE
      SYNTAX  Integer32
      MAX-ACCESS  read-only
      STATUS  current
      DESCRIPTION
        "The available number of entries in the IP permanent stations 
         table."
      ::= { lanrangerIpStation 1 }

   lanrangerIpPermanentCurrentEntries OBJECT-TYPE
      SYNTAX  Integer32
      MAX-ACCESS  read-only
      STATUS  current
      DESCRIPTION
        "The current number of entries in the IP permanent station table."
      ::= { lanrangerIpStation 2 }


-- The IP Permanent Stations table will be supported via the 
-- IP Forward table of RFC1354.MIB.


  lanrangerSpoofingStation  OBJECT IDENTIFIER
       ::= {lanrangerStation 6}

  lanrangerSpoofingMaxEntries OBJECT-TYPE
	   SYNTAX Integer32
	   MAX-ACCESS read-only
	   STATUS current
	   DESCRIPTION
	      "The maximum number of entries in the Spoofing station
		   table."
	   ::= {lanrangerSpoofingStation 1}

  lanrangerSpoofingCurrentEntries OBJECT-TYPE
	   SYNTAX Integer32
	   MAX-ACCESS read-only
	   STATUS current
	   DESCRIPTION
	      "The current number of entries in the Spoofing station
		   table."
	   ::= {lanrangerSpoofingStation 2}

  lanrangerSpoofingTable OBJECT-TYPE
       SYNTAX SEQUENCE OF LanrangerSpoofingEntry
       MAX-ACCESS not-accessible
       STATUS current
       DESCRIPTION
          "A list of Spoofing entries. The number of entries is 
           up to the current number of entries, according to the 
           LANRANger model. 
           Only the LOCAL LANRANger will show this table !
                    ---------------                          "

       ::= { lanrangerSpoofingStation 3 }

    lanrangerSpoofingEntry OBJECT-TYPE
       SYNTAX  LanrangerSpoofingEntry
       MAX-ACCESS  not-accessible
       STATUS  current
       DESCRIPTION
           "Spoofing parameters per entry of the Spoofing table."
       INDEX   {lanrangerSpoofingGroup,  lanrangerSpoofingMacAddress }
       ::= { lanrangerSpoofingTable 1 }

    LanrangerSpoofingEntry ::=
       SEQUENCE {
              lanrangerSpoofingGroup
			  Integer32,
              lanrangerSpoofingMacAddress
               MacAddress ,
              lanrangerSpoofingAging
               Integer32,
			  lanrangerSpoofingTimeLeft
			   Integer32
          }

      lanrangerSpoofingGroup   OBJECT-TYPE 
          SYNTAX  Integer32 
          MAX-ACCESS  read-only
          STATUS  current
          DESCRIPTION
             " 	The spoofing group.
                Only the LOCAL Lanranger will show this table !   "
          ::= {  lanrangerSpoofingEntry 1 }


      lanrangerSpoofingMacAddress   OBJECT-TYPE 
          SYNTAX  MacAddress 
          MAX-ACCESS  read-only
          STATUS  current
          DESCRIPTION
             " 	MAC Address of the Remote Lanrangers.
                Only the LOCAL Lanranger will show this table !   "
          ::= {  lanrangerSpoofingEntry 2 }

      lanrangerSpoofingAging OBJECT-TYPE
           SYNTAX Integer32 
           MAX-ACCESS read-only
           STATUS current
           DESCRIPTION
              " Aging time defined for a whole group, in minutes.      
                Only the LOCAL Lanranger will show this table !   "
           ::= { lanrangerSpoofingEntry 3 }

      lanrangerSpoofingTimeLeft OBJECT-TYPE
           SYNTAX Integer32 
           MAX-ACCESS read-only
           STATUS current
           DESCRIPTION
              " Time until aging expires, per station, in minutes.      
                Only the LOCAL Lanranger will show this table !   "
           ::= { lanrangerSpoofingEntry 4 }


--PPP Table for the WebRanger

wrPPPTable OBJECT-TYPE
      SYNTAX SEQUENCE OF WrPPPEntry
      MAX-ACCESS not-accessible
      STATUS current
      DESCRIPTION
          "This table contains only parameters that do not exist in the PPP
           standard MIBS.
           The table contains a list of PPP entries.  
           The number of entries is up to ifIndex."
      ::= { lanrangerInterface 5 }
      
wrPPPEntry OBJECT-TYPE
    SYNTAX WrPPPEntry
    MAX-ACCESS not-accessible
    STATUS current
    DESCRIPTION
        "LANRANger-specific parameter values for a PPP."
    INDEX {ifIndex }
    ::= { wrPPPTable 1 }

WrPPPEntry ::=
    SEQUENCE {
        wrPPPCompressionHeaderField
            INTEGER,
        wrPPPCompressionProtocolFields
            INTEGER,
        wrPPPSTACCompressionType
            INTEGER,
	    wrPPPAuthProtocol
	        INTEGER,
	    wrPPPSecurityType
	        INTEGER,
	    wrPPPUserName
	        SnmpAdminString,
	    wrPPPPassword 
	        SnmpAdminString,
	    wrPPPLinkActiveTime	
	         Integer32

   }

wrPPPCompressionHeaderField OBJECT-TYPE
    SYNTAX INTEGER
	    { compressionOff (2),
		  compressionOn (3) }
    MAX-ACCESS read-write
    STATUS current
    DESCRIPTION "This configuration option provides a method to negotiate the
                 compression of the Data Link Layer Address and Control fields.
                 This configuration option is sent to inform the peer that the
                 implementation can receive compressed Address and Control fields."
    ::= { wrPPPEntry 1 }

wrPPPCompressionProtocolFields OBJECT-TYPE
    SYNTAX INTEGER
	    { compressionOff (2),
		  compressionOn (3) }
    MAX-ACCESS read-write
    STATUS current
    DESCRIPTION "This configuration option provides a method to negotiate the
                 compression of the PPP Protocol field. This configuration option
                 is sent to inform the peer that the implementation can receive
                 such single octet Protocol fields. "
    ::= { wrPPPEntry 2 }

wrPPPSTACCompressionType OBJECT-TYPE
    SYNTAX INTEGER
	    { disable (1),
		  noHistory (2),
		  lCB (3),
		  sequence (4),
		  extended (5) }
    MAX-ACCESS read-write
    STATUS current
    DESCRIPTION "The PPP compression control protocol provides a method to negotiate
                 and utilize compression protocol over PPP encapsulated links. 
                 These are Different types of data compression algorithm for PPP
                 encapsulated packets. "
    ::= { wrPPPEntry 3 }

wrPPPAuthProtocol OBJECT-TYPE
    SYNTAX INTEGER
            { 
		noneNone (1), 
		chapNone (2), 
		chapPap (3), 
		chapChap (4), 
		papNone (5), 
		papPap (6)
		 }
    MAX-ACCESS read-write
    STATUS current
    DESCRIPTION 
	"The type of authentication protocol being used. The left parameter
         is the maximum authentication, the right parameter is minimum authentication."
    ::= { wrPPPEntry 4 }

wrPPPSecurityType OBJECT-TYPE
    SYNTAX INTEGER
            { 
		host (1),
		guest (2) 
		}
    MAX-ACCESS read-write
    STATUS current
    DESCRIPTION 
	"Type of unit."
    ::= { wrPPPEntry 5 }


wrPPPUserName OBJECT-TYPE
    SYNTAX SnmpAdminString (SIZE (0..10))
    MAX-ACCESS read-write
    STATUS current
    DESCRIPTION 
	"PPP User name."
    ::= { wrPPPEntry 6 }

wrPPPPassword OBJECT-TYPE
    SYNTAX SnmpAdminString (SIZE (0..10))
    MAX-ACCESS read-write
    STATUS current
    DESCRIPTION 
	"PPP Password ."
    ::= { wrPPPEntry 7 }

wrPPPLinkActiveTime OBJECT-TYPE
    SYNTAX Integer32 
    MAX-ACCESS read-write
    STATUS current
    DESCRIPTION 
	"PPP link active time in seconds 
	Values range: 2 - 900.
	Default value = 2     "
    ::= { wrPPPEntry 8 }



-- Traps for use by the LANRANger

--NOTIFICATIONS

lanrangerEvents OBJECT-IDENTITY
    STATUS  current
	DESCRIPTION
	"The events for the LANRANger."
	::= { lanranger 0 }

lanrangerLogLinkUp NOTIFICATION-TYPE
    OBJECTS  { lanrangerLinkConnPhysLink, lanrangerLinkConnAid }
    STATUS  current
    DESCRIPTION
            "The lanrangerLogLinkUp trap indicates that the indicated logical link is connected."
	::= { lanrangerEvents 1 }

lanrangerLogLinkDown NOTIFICATION-TYPE
    OBJECTS  { lanrangerLinkConnPhysLink, lanrangerLinkConnAid }
    STATUS  current
    DESCRIPTION
            "The lanrangerLogLinkDown trap indicates that the indicated logical link is disconnected."
	::= { lanrangerEvents 2 }

lanrangerLanTableOverflow NOTIFICATION-TYPE
    STATUS  current
    DESCRIPTION
            "The station table has the maximum number of addresses for the LANRANger."
	::= { lanrangerEvents 3 }

lanrangerStatusChanged NOTIFICATION-TYPE
    OBJECTS  { agnLed }
    STATUS  current
    DESCRIPTION
            "The trap indicates changes in the device status ."
	::= { lanrangerEvents 4 }

-- 
-- file :v:\doc\rdv\mib\Before~1\febftb.txt
-- 


-- Title:  FEB MIB   
-- Version:   1.0
-- Date:    29 August 94
-- By:       Orly Nicklass
--File:       febftb.txt
-- Comments:  This MIB is for FEBs and FTBs.  These bridges also support the following MIBs:
--              - MIB-II  ( RFC1213 )
--              - BRIDGE - MIB  ( RFC1493)
--	- FDDI MIB (RFC  1512)
-- The FDDI bridges also support the RAD General Bridge Branch, 164.4.1

--  Objects in this MIB are arranged into groups:
--   febFtbTranslation  -  Defines parameters for translation of Ethernet and Token-Ring to/from FDDI 
--   febFtbStatus    
-- At the end of the MIB there is a definition of all FDDI bridge-specific traps. 

febFtb  OBJECT IDENTIFIER ::= { radBridges 4 }
febFtbTranslation    OBJECT IDENTIFIER ::= { febFtb 1 }
febFtbStatus    OBJECT IDENTIFIER ::= { febFtb 2 }


febFtbTranslIfTable OBJECT-TYPE
    SYNTAX   SEQUENCE OF FebFtbTranslIfEntry
    MAX-ACCESS   not-accessible
    STATUS   current
    DESCRIPTION
       "The translation table defines which type of translation is required for each device interface. This is
       particularly important for WAN links, as the translating device does not have a knowledge of the 
       target LAN type."
    ::= { febFtbTranslation 1 }

febFtbTranslIfEntry  OBJECT-TYPE
    SYNTAX   FebFtbTranslIfEntry
    MAX-ACCESS   not-accessible
    STATUS   current
    DESCRIPTION
        "Entry in the translation table."
    INDEX { febFtbTranslIfIndex}
    ::= { febFtbTranslIfTable 1 }


FebFtbTranslIfEntry ::=
     SEQUENCE {
febFtbTranslIfIndex
        Integer32,
febFtbTunnelProtocol 
        OCTET STRING,
febFtbTranslIPXRawEthernet
        INTEGER
}
febFtbTranslIfIndex OBJECT-TYPE
    SYNTAX Integer32 
    MAX-ACCESS  read-only
    STATUS  current
    DESCRIPTION
          "Index to the Translation Table. The interface defined by a  particular value of this index is the 
          same interface as identified by the same value of ifIndex (MIBII)."
    ::= { febFtbTranslIfEntry 1 }

febFtbTunnelProtocol OBJECT-TYPE
    SYNTAX OCTET STRING (SIZE (2))
    MAX-ACCESS  read-write
    STATUS  current
    DESCRIPTION
          "IEEE 802.1h standard defines the tunneling for Appletalk I. This parameter enables the user
           to specify Ethertype of an additional protocol to tunnel (e.g. IPX). For IPX, Enter 8137 to
           translate Token Ring SNAP frames to Ethernet_SNAP frames (instead of Ethernet II).
           Valid range of values: 05DC to FFFF (hex)
           0000 (hex) - disables this function. "
    ::= { febFtbTranslIfEntry 2 }

febFtbTranslIPXRawEthernet OBJECT-TYPE
    SYNTAX INTEGER {
          ethernetRaw8023(1),
          ethernet8022(2)
   }
    MAX-ACCESS  read-write
    STATUS  current
    DESCRIPTION
	"This variable defines the translation mode for IPX frames in standrad Token Ring format. It is 
                applicable to Ethernet interfaces (i.e. febFtbTranslSwitch variable has value Ethernet (2). ).
                ethernetRaw8023:   translate to Raw Ethernet frames (default)
               ethernet8022:   translate to Ethernet 802.2 frames."
     ::= { febFtbTranslIfEntry 3 }

febFtbLanTable OBJECT-TYPE
    SYNTAX   SEQUENCE OF FebFtbLanTabEntry
    MAX-ACCESS   not-accessible
    STATUS   current
    DESCRIPTION
       "."
    ::= { febFtbStatus    1 }

febFtbLanTabEntry  OBJECT-TYPE
    SYNTAX   FebFtbLanTabEntry
    MAX-ACCESS   not-accessible
    STATUS   current
    DESCRIPTION
        "Entry in the LanTab table."
    INDEX { febFtbLanTabIfIndex}
    ::= { febFtbLanTable 1 }

FebFtbLanTabEntry ::=
     SEQUENCE {
febFtbLanTabIfIndex
        Integer32,
febFtbLanTabEntNumber    
        Integer32 
}


febFtbLanTabIfIndex  OBJECT-TYPE
    SYNTAX Integer32 
    MAX-ACCESS  read-only
    STATUS  current
    DESCRIPTION
	"This variable defines the related interface"
     ::= { febFtbLanTabEntry  1 }

febFtbLanTabEntNumber    OBJECT-TYPE
    SYNTAX Integer32 
    MAX-ACCESS  read-only
    STATUS  current
    DESCRIPTION
	"This variable defines the number of entries in the LAN table reletaed to the specific interface"
     ::= { febFtbLanTabEntry   2 }

febFtbFaults    OBJECT-TYPE
    SYNTAX Integer32 
    MAX-ACCESS  read-only
    STATUS  current
    DESCRIPTION
	"This variable defines the current device faults. It is a 32 bits variable, where each bit represents
	a unique fault"
     ::= { febFtbStatus    2 }

--NOTIFICATIONS

febFtbEvents OBJECT-IDENTITY
    STATUS  current
	DESCRIPTION
	"The events for FEBs and FTBs."
	::= { febFtb 0 }

lanTableOverflow NOTIFICATION-TYPE
	STATUS  current
    DESCRIPTION
            "The station table has the maximum number of addresses for the device."
	  ::= { febFtbEvents 1 }

statusChanged NOTIFICATION-TYPE
    OBJECTS  {agnLed, agnIndication }
	STATUS  current
    DESCRIPTION
            "A change occured in agent status or leds."
	  ::= { febFtbEvents 2 }

portFddiStatusChanged NOTIFICATION-TYPE
    OBJECTS {fddimibPORTPCMState, agnLed }
	STATUS  current
    DESCRIPTION
            "The Fddi port status changed. fddimibPORTPCMState
             value has become off, maint, active, connect, or exited 
             one of these states."
	  ::= { febFtbEvents 3 }


-- 
-- file :v:\doc\rdv\mib\Before~1\mlb.txt
-- 

-- Title:   RAD MLB MIB
--             
--             
-- Version: 1.0  
-- Date:    November, 20, 1994
-- By:      Ricky Yaffe
-- File:    mlb.txt

 mlb            OBJECT IDENTIFIER ::= { radBridges 5 }


--   Objects in this MIB are arranged into groups:
--   mlbConfig  -  MLB - specific configurable parameters
--   mlbAddress -  MLB - Table containing the list of ports address  .

--  At the end of the MIB there is a definition of all MLB - specific traps. 

mlbConfig OBJECT IDENTIFIER ::= { mlb 1 }

mlbMibVersion  OBJECT-TYPE 
    SYNTAX   OCTET STRING
    MAX-ACCESS   read-only
    STATUS   current
    DESCRIPTION
       "mlb private mib version ."
    ::= {  mlbConfig 1  }

mlbPanelMedia  OBJECT-TYPE 
    SYNTAX   INTEGER {
        unknown(1),
        copper(2),
        fiberOptic(3),
        notSupported (4)
        }
    MAX-ACCESS   read-only
    STATUS   current
    DESCRIPTION
       "The panel media. It can be fiber optic connector or STP+UTP
        in case of copper"
    ::= {  mlbConfig 2  }

mlbRRFrontPanelPort  OBJECT-TYPE 
    SYNTAX   INTEGER {
        unknown(1),
        secondary(2),
        main(3),
        notSupported (4)
        }
    MAX-ACCESS   read-only
    STATUS   current
    DESCRIPTION
       "Front panel port function : MainPort / Sec.Port (case of RADring card) ."
    ::= {  mlbConfig 3  }

mlbRRTermination  OBJECT-TYPE 
    SYNTAX   INTEGER {
        unknown(1),
        on(2),
        off(3),
        notSupported (4)
        }
    MAX-ACCESS   read-only
    STATUS   current
    DESCRIPTION
       "Temination switch - Split back lan and Terminate it. (case of RADring card) ."
    ::= {  mlbConfig 4  }

mlbAddress OBJECT IDENTIFIER ::= {mlb 2}

mlbAddressTable OBJECT-TYPE
      SYNTAX  SEQUENCE OF MlbAddressEntry
      MAX-ACCESS  not-accessible
      STATUS  current
      DESCRIPTION
       "A table that contains information about the MLB ports address ."
      ::= { mlbAddress 1 }

mlbAddressEntry OBJECT-TYPE
    SYNTAX  MlbAddressEntry
    MAX-ACCESS  not-accessible
    STATUS  current
    DESCRIPTION
       "Information about a specific port that the MLB lists define."
    INDEX {mlbPortIndex }
    ::= { mlbAddressTable 1 }

    MlbAddressEntry ::=
        SEQUENCE {
            mlbPortIndex
                Integer32,
            mlbBurnAddress
                MacAddress,
            mlbLocAddress
                MacAddress,
            mlbActiveAddress
                INTEGER
              }


mlbPortIndex OBJECT-TYPE
    SYNTAX Integer32
    MAX-ACCESS read-only
    STATUS current
    DESCRIPTION
        "A unique value for each port, equal to the value of ifIndex for the port. 
        The maximum number of ports for mlb is 2 . "
    ::= { mlbAddressEntry  1  }


mlbBurnAddress   OBJECT-TYPE 
    SYNTAX  MacAddress 
    MAX-ACCESS  read-only
    STATUS  current
    DESCRIPTION
	"This is the burned-in MacAddress on the LANRANger."
    ::= { mlbAddressEntry  2  }

mlbLocAddress   OBJECT-TYPE 
    SYNTAX  MacAddress 
    MAX-ACCESS  read-write
    STATUS  current
    DESCRIPTION
	"This is a locally administered address.  If a zero value appears, the network administrator 
	did  not set a locally administered address."
    ::= { mlbAddressEntry  3 }

mlbActiveAddress OBJECT-TYPE
     SYNTAX INTEGER {burnedIn(1), locallyAdministered(2) }
     MAX-ACCESS read-write
     STATUS current
     DESCRIPTION
         "The MAC address that is in use on the LANRANger. 
          The address selected will appear in ifPhysAddress."
     ::= { mlbAddressEntry  4 }


--NOTIFICATIONS

mlbEvents OBJECT-IDENTITY
    STATUS  current
	DESCRIPTION
	"The events for the MLB."
	::= { mlb 0 }

mlbLanTableOverflow NOTIFICATION-TYPE
    STATUS  current
    DESCRIPTION
         "The station table has the maximum number of addresses for the LANRANger."
	::= { mlbEvents 1 }

mlbStatusChanged NOTIFICATION-TYPE
    OBJECTS  { agnLed }
    STATUS  current
    DESCRIPTION
         "The trap indicates changes in the device status ."
	::= { mlbEvents 2 }

-- 
-- file :v:\doc\rdv\mib\Before~1\cvt.txt
-- 


--Version:   1.0
--Date:   16.10.94              
--By:      RADLINX  &  Orly Nicklass
--File:       cvt.txt
--

genSnar OBJECT IDENTIFIER ::= { radConverters 1 } 
 --                SNAR - SNA conversion software
	--                STC, FTC - Token to SDLC conversion devices
	--                SEC, FEC - Ether to SDLC conversion devices
	--                XTC - X.25/QLLC conversion device
	--    
	--                Definitions apply to all products,
	--                  unless otherwise specified. 
	--                The devices are generally referred
	--                  as 'device'. 
	--    
       Sap         ::= OCTET STRING (SIZE (1))
       SdlcAddr    ::= OCTET STRING (SIZE (1))
--    OctetRange  ::= Integer32      (1..255)

	 --Active ::= INTEGER { inactive(1) , active(2) }
	 --Side   ::= INTEGER { sideA(1) , sideB(2) }
	 --Enable ::= INTEGER { disable(1) , enable(2) }


    --** THE SNAR TREE **--
     
    snarState OBJECT IDENTIFIER ::= { genSnar   1 } 
    snarNva   OBJECT IDENTIFIER ::= { genSnar    3 } 
    snarSna   OBJECT IDENTIFIER ::= { genSnar    5 } 
       
     -- 
     --    SNAR state group
     -- General state information
     --

  snarStatus   OBJECT-TYPE
	   SYNTAX  INTEGER {
	    up   (1),
	    down (2),
	    test (3)
	   }
	   MAX-ACCESS  read-write
	   STATUS  current
	   DESCRIPTION
	  " The status of the whole SNAR process
	      1 -up
	      2 -down
	      3 -test (After setting one of the previous states, the 
		status will be test until the changes will be done).
	   "
	::= { snarState 1 }

	snarBufferUsage   OBJECT-TYPE
	   SYNTAX  Integer32 (0..100)
	   MAX-ACCESS  read-only
	   STATUS  current
	   DESCRIPTION
	   " The buffer usage of the SNAR (in percentage).
	   "
	::= { snarState 2 }

	snarMaxSnaSession   OBJECT-TYPE
	   SYNTAX  Integer32 
	   MAX-ACCESS  read-only
	   STATUS  current
	   DESCRIPTION
	   " Max number of sessions supported in this SNAR implementation
	   "
	::= { snarState 3 }

      snarSaveChanges  OBJECT-TYPE
	 SYNTAX INTEGER{
	    noSave       (1),
	    save         (2),    
	    saveAndReset (3),
	    undoAllChanges (4)
	 }
	 MAX-ACCESS read-write
	 STATUS current
	 DESCRIPTION
	 "N/A to SNAR, only for devices. When changes are made to any 
	 configuration parameters (SNA, NVA or others) it should be 
	 stored in the device's NVRAM and then the device is restarted.
	 Using this variable the manager can:
	 2 - Just save into NVRAM all configuration changes
	 3 - Save into NVRAM the configuration changes and restart the
	     Device, to reflect the changes.
	 4 - Undo all  changes  since  last reset or
	     save, (without resetting the device).
	     Load the original configuration from the NVRAM. 
	 "
	::= { snarState 5 }   


	-- 
	-- snarNVA group    
	-- 
	-- Defines the NetView agent configuration and internal
	-- statistics,  applicable to SNAR and all devices
	-- 


	nvaAgentsNumber OBJECT-TYPE
	   SYNTAX  Counter32 
	   MAX-ACCESS  read-only
	   STATUS  current
	   DESCRIPTION
	   " The number of configured NetView agents
	   "
	::= { snarNva   2 }

      --*********
	nvaAgentTable  OBJECT-TYPE
	   SYNTAX SEQUENCE OF NvaAgentEntry
	   MAX-ACCESS not-accessible
	   STATUS current
	   DESCRIPTION
	  "
	  "
	::= { snarNva 3 }

	nvaAgentEntry  OBJECT-TYPE
	   SYNTAX NvaAgentEntry
	   MAX-ACCESS not-accessible
	   STATUS current
       DESCRIPTION
	   "An entry in table nvaAgentTable."
	   INDEX  { nvaAgIndex }
	::= { nvaAgentTable 1 }

	NvaAgentEntry ::=
	   SEQUENCE {
	      nvaAgIndex
		 Integer32,
	      nvaAgAdminStatus
		 INTEGER,
	      nvaAgOperState
		 INTEGER,
	      nvaAgFilter
		 OCTET STRING,
	      nvaAgAllowRunCmd
		 INTEGER,
	   --****CFG******
	      nvaAgAccessType
		 INTEGER,
	      nvaAgIfIndex
		 Integer32,
	      nvaAgXidBlockId
		 OCTET STRING,
	      nvaAgXidBlockNum
		 OCTET STRING,
	      nvaAgSSap
		 Sap,
	      nvaAgDSap
		 Sap,
	      nvaAgRemMacAddr
		 MacAddress,
	      nvaAgSdlcAddr
		 SdlcAddr,
	      nvaAgResourceName
		 DisplayString
	  }
	

	nvaAgIndex  OBJECT-TYPE
	   SYNTAX Integer32
	   MAX-ACCESS read-only
	   STATUS current
	   DESCRIPTION
	  "Agent number .
	   Range (1 - nvaAgentsNumber)
	  "
	::= { nvaAgentEntry 1 }

	nvaAgAdminStatus  OBJECT-TYPE
	   SYNTAX  INTEGER { disable(1) , enable(2) }
	   MAX-ACCESS read-write
	   STATUS current
	   DESCRIPTION
	  " The admin. status of NV AGENT. Value of 'disable'
	    will prevent the NetView agent from trying to 
	    connect to the NetView management system
	  "
	::= { nvaAgentEntry 3 }

	nvaAgOperState  OBJECT-TYPE
	   SYNTAX INTEGER { inactive(1) , active(2) }
	   MAX-ACCESS read-only
	   STATUS current
	   DESCRIPTION
	  " Current Operation state of the NetView agent. Active
	    state means that the NetView agent is in session
	    with the NetView management system
	  "
	::= { nvaAgentEntry 4 }

	nvaAgFilter  OBJECT-TYPE
	   SYNTAX OCTET STRING
	   MAX-ACCESS read-only
	   STATUS current
	   DESCRIPTION
	  "Alert filter bit mask. Each bit corresponds to a specific alert
	   sent by the NetView agent.
	  "
	::= { nvaAgentEntry 5 }

	nvaAgAllowRunCmd  OBJECT-TYPE
	   SYNTAX   INTEGER { disable(1) , enable(2) }
	   MAX-ACCESS read-write
	   STATUS current
	   DESCRIPTION
	  "Defines whether the NetView agent is allowed to handle
	   operational commands, received by the RUNCMD facility 
	  "
	::= { nvaAgentEntry 6 }

	nvaAgAccessType OBJECT-TYPE
	   SYNTAX INTEGER{
	     llcCsmacd     (1), 
	     llcTokenRing (3),    
	     sdlc           (6),
	     qllcX25       (10)
	    }
	   MAX-ACCESS read-write
	   STATUS current
	   DESCRIPTION
	  " Defines the method in which the agent tries to
	    connect to the NetView management system(the SNA host)
	  "
	::= { nvaAgentEntry 7 }

	nvaAgIfIndex OBJECT-TYPE
	   SYNTAX Integer32
	   MAX-ACCESS read-write
	   STATUS current
	   DESCRIPTION
	  " The port number of the interface in which the 
	    NetView agent connects to the SNA host
	  "
	::= { nvaAgentEntry 8 }

	nvaAgXidBlockId  OBJECT-TYPE
	   SYNTAX OCTET STRING (SIZE (2))
	   MAX-ACCESS read-write
	   STATUS current
	   DESCRIPTION
	  " The BLOCKID part of the XID information which the NetView agent
	    should use to connect to the NetView management system
	    (The SNA host)
	  "
	::= { nvaAgentEntry 9 }

	nvaAgXidBlockNum  OBJECT-TYPE
	   SYNTAX OCTET STRING (SIZE (3))
	   MAX-ACCESS read-write
	   STATUS current
	   DESCRIPTION
	  " The BLOCKNUM part of the XID information which the NetView agent
	    should use to connect to the NetView management system
	    (The SNA host)
	  "
	::= { nvaAgentEntry 10 }

	nvaAgSSap  OBJECT-TYPE
	   SYNTAX Sap
	   MAX-ACCESS read-write
	   STATUS current
	   DESCRIPTION
	  " Local SAP, used for the NetView session - for LLC
	    access type session only.
	  "
	::= { nvaAgentEntry 11 }

	nvaAgDSap  OBJECT-TYPE
	   SYNTAX Sap
	   MAX-ACCESS read-write
	   STATUS current
	   DESCRIPTION
	  " Remote(host) Sap used by the NetView agent for the
	    SNA host connection - for LLC access session type
	    only.
	  "
	::= { nvaAgentEntry 12 }

	nvaAgRemMacAddr  OBJECT-TYPE
	   SYNTAX MacAddress
	   MAX-ACCESS read-write
	   STATUS current
	   DESCRIPTION
	  " Remote(host) MAC address used by the NetView agent
	    for the SNA host connection - for LLC access session
	    type only.
	  "
	::= { nvaAgentEntry 13 }

	nvaAgSdlcAddr  OBJECT-TYPE
	   SYNTAX SdlcAddr
	   MAX-ACCESS read-write
	   STATUS current
	   DESCRIPTION
	  " SDLC address used by the NetView agent for the SNA 
	    host connection - for SDLC access session type only.
	  "
	::= { nvaAgentEntry 14 }

	nvaAgResourceName  OBJECT-TYPE
	   SYNTAX DisplayString
	   MAX-ACCESS read-write
	   STATUS current
	   DESCRIPTION
	  " A 4 character name that is appended to the resource
	    name in the NetView alerts sent by the NetView agent
	  "
	::= { nvaAgentEntry 15 }


	nvaAgentStatTable  OBJECT-TYPE
	   SYNTAX SEQUENCE OF NvaAgentStatEntry
	   MAX-ACCESS not-accessible
	   STATUS current
	   DESCRIPTION
	  "
	  "
	::= { snarNva 4 }

	nvaAgentStatEntry  OBJECT-TYPE
	   SYNTAX NvaAgentStatEntry
	   MAX-ACCESS not-accessible
	   STATUS current
       DESCRIPTION
	   "An entry in table nvaAgentStatTable."
	   INDEX  { nvaAgStatIndex }
	::= { nvaAgentStatTable 1 }

	NvaAgentStatEntry ::=
	   SEQUENCE {
	      nvaAgStatIndex
		 Integer32,

	   --*****STATISTICS****
	      nvaAgStatTime
		 TimeTicks,
	      nvaAgActPu
		 Counter32,
	      nvaAgDactPu
		 Counter32,
	      nvaAgRpNmvt
		 Counter32,
	      nvaAgRnNmvt
		 Counter32,
	      nvaAgSpNmvt
		 Counter32,
	      nvaAgSAlerts
		 Counter32,
	      nvaAgRRunCmd
		 Counter32,
	      nvaAgSRunCmd
		 Counter32,
	      nvaAgSPdstat
		 Counter32
	   }

	nvaAgStatIndex  OBJECT-TYPE
	   SYNTAX Integer32
	   MAX-ACCESS read-only
	   STATUS current
	   DESCRIPTION
	  "Agent number .
	   Range (1 - nvaAgentsNumber)
	  "
	::= { nvaAgentStatEntry 1 }

      
	 nvaAgStatTime  OBJECT-TYPE
	   SYNTAX TimeTicks
	   MAX-ACCESS read-write
	   STATUS current
	   DESCRIPTION
	  " Time since last reset of the NV agent statistics.
	    Setting to a value of  0 will clear all  Agents'
	       statistics.
	  "
	::= { nvaAgentStatEntry 2 }

	nvaAgActPu  OBJECT-TYPE
	   SYNTAX Counter32
	   MAX-ACCESS read-only
	   STATUS current
	   DESCRIPTION
	  " Number of session initiation (ACTPU) requests received from
	    the SNA host
	  "
	::= { nvaAgentStatEntry 3 }

	nvaAgDactPu  OBJECT-TYPE
	   SYNTAX Counter32
	   MAX-ACCESS read-only
	   STATUS current
	   DESCRIPTION
	  " Number of session disconnection (DACTPU) requests received
	    from the SNA host 
	  "
	   ::= { nvaAgentStatEntry 4 }

	nvaAgRpNmvt  OBJECT-TYPE
	   SYNTAX Counter32
	   MAX-ACCESS read-only
	   STATUS current
	   DESCRIPTION
	  " Number of NMVTs received from the SNA host, and responded
	    with a positive response.
	  "
	::= { nvaAgentStatEntry 5 }

	nvaAgRnNmvt  OBJECT-TYPE
	   SYNTAX Counter32
	   MAX-ACCESS read-only
	   STATUS current
	   DESCRIPTION
	  " Number of NMVTs received from the SNA host, and
	    respond with a negative response.
	  "
	  ::= { nvaAgentStatEntry 6 }

	nvaAgSpNmvt  OBJECT-TYPE
	   SYNTAX Counter32
	   MAX-ACCESS read-only
	   STATUS current
	   DESCRIPTION
	  " Number of NMVTs (of any type) sent to the SNA host.
	  "
	::= { nvaAgentStatEntry 7 }

	nvaAgSAlerts  OBJECT-TYPE
	   SYNTAX Counter32
	   MAX-ACCESS read-only
	   STATUS current
	   DESCRIPTION
	  " Number of alert NMVTs sent by the NetView agent.
	  "
	::= { nvaAgentStatEntry 9 }

	nvaAgRRunCmd  OBJECT-TYPE
	   SYNTAX Counter32
	   MAX-ACCESS read-only
	   STATUS current
	   DESCRIPTION
	  " Number of RUNCMD (execute-command NMVTs) received by the 
	    NetView agent.
	  "
	::= { nvaAgentStatEntry 10 }

	nvaAgSRunCmd  OBJECT-TYPE
	   SYNTAX Counter32
	   MAX-ACCESS read-only
	   STATUS current
	   DESCRIPTION
	  "Number of RUNCMD replies sent to the NetView host.
	  "
	::= { nvaAgentStatEntry 11 }

	nvaAgSPdstat  OBJECT-TYPE
	   SYNTAX Counter32
	   MAX-ACCESS read-only
	   STATUS current
	   DESCRIPTION
	  "Number of PDSTAT NMVTs sent by the NetView agent.
	  "
	::= { nvaAgentStatEntry 12 }


	-- 
	-- snaSNA group    
	-- 
	-- Defines the sessions' parameters  to be converted
	--


     --*********
	snaSessTable  OBJECT-TYPE
	   SYNTAX SEQUENCE OF SnaSessEntry
	   MAX-ACCESS not-accessible
	   STATUS current
	   DESCRIPTION
	  " Holding SNA session's parameters for each side of a
	    specific session, indexed by session_id
	  "
	::= { snarSna 3 }

	snaSessEntry  OBJECT-TYPE
	   SYNTAX SnaSessEntry
	   MAX-ACCESS not-accessible
	   STATUS current
       DESCRIPTION
	   "An entry in table snaSessTable."
	   INDEX  { sessIfIndex, sessId, sessSide }
	::= { snaSessTable 1 }

	SnaSessEntry ::=
	   SEQUENCE {
	   sessIfIndex   
	      Integer32,
	   sessId
	      Integer32,
	   sessSide
	      INTEGER,
	   sessDev
	      Integer32,
	   sessAdminStatus
	      INTEGER,
	   sessOperState
	      INTEGER,
	   sessAccessType
	      INTEGER,
	   sessSXidBlockId
	      OCTET STRING,
	   sessSXidBlockNum
	      OCTET STRING,

	   --** LLC/SDLC **
	   sessSSap
	      Sap,
	   sessDSap
	      Sap,
	   sessRemMacAddr
	      MacAddress,

	   --** SDLC     **
	   sessSdlcAddr
	      SdlcAddr,
	   sessGroupPoll
	      SdlcAddr,
	   sessRole
	      INTEGER,
	   --** LLC/IP    **
	   sessIpEncapsulated
	      INTEGER,
	   sessDestIpAddr
	      IpAddress,

	   --** QLLC  x25  **
	   sessRemX25Addr
	      OCTET STRING
	 }
     


	sessIfIndex  OBJECT-TYPE
	   SYNTAX Integer32
	   MAX-ACCESS read-only
	   STATUS current
	   DESCRIPTION
	  "Interface used by this SNA session       
	  "
	::= { snaSessEntry 1 }

	sessId  OBJECT-TYPE
	   SYNTAX Integer32
	   MAX-ACCESS read-only
	   STATUS current
	   DESCRIPTION
	  " The unique identifier of the converted SNA session id
	  "
	 ::= { snaSessEntry 2 }

	sessSide  OBJECT-TYPE
	   SYNTAX INTEGER { sideA(1) , sideB(2) }
	   MAX-ACCESS read-only
	   STATUS current
	   DESCRIPTION
	  " The SNA session side. Each session handled by SNAR/device,
	    creates 2 SNA sessions, hereafter called 'side A' and 'side B'
	    Configuration parameters, and Statistics are defined for each 
	    side separately.
	  "
	::= { snaSessEntry 3 }

	sessDev OBJECT-TYPE
	   SYNTAX Integer32
	   MAX-ACCESS read-only
	   STATUS current
	   DESCRIPTION
	  " The device number, used in devices setup. N/A to SNAR. 
	  "
	::= { snaSessEntry 4 }

	sessAdminStatus  OBJECT-TYPE
	   SYNTAX INTEGER {
	    disable (1),  
	    enable  (2),   
	    underCreation (3),
	    stop    (4),
	    start   (5),      
	    invalid (10)
	   }
			
	   MAX-ACCESS read-write
	   STATUS current
	   DESCRIPTION
	  " Admin. status of this session, as requested by the manager.
	    10 - Session is invalid, and not handled by SNAR 
	       devices.
	    1 - Session is disabled. SNAR/Device will not try to start
	       this session.
	    2-  Session is enabled. SNAR/Device will try to start this
	       session.
	    3-  Under_creation - This session parameters are under creation,
	       manipulated by a manager.
	    4 - stop: stop an enabled session  immediately - no need
	       to save change.
	    5 - start :start a stopped sessions  immediately - no need to 
	       save change.
	  "
	::= { snaSessEntry 5 }

	sessOperState  OBJECT-TYPE
	   SYNTAX INTEGER {
	     stopped     (1),
	     disabled    (2),
	     sdlcProb03  (3),
	     llcProb04   (4),
	     ifProb30    (30),
	     ifProb80    (80),
	     ifProb81    (81),
	     ifProb87    (87),
	     ifProb88    (88),
	     ok          (99)
	   }
	   MAX-ACCESS read-only
	   STATUS current
	   DESCRIPTION
	  " Current operating state.
	    See Manual reference for more information.
	  "
	::= { snaSessEntry 6 }

	sessAccessType  OBJECT-TYPE
	  SYNTAX INTEGER{
	     llcCsmacd     (1), 
	     llcTokenRing (3),    
	     sdlc           (6),
	     qllcX25       (10)
	    }
	   MAX-ACCESS read-write
	   STATUS current
	   DESCRIPTION
	  "The access type  used by this side of the converted 
	   session.
	  "
	::= { snaSessEntry 7 }

	sessSXidBlockId  OBJECT-TYPE
	   SYNTAX OCTET STRING (SIZE (2))
	   MAX-ACCESS read-write
	   STATUS current
	   DESCRIPTION
	  "The BLOCKID part of the XID information sent by this side for the 
	   SNA session initiation
	  "
	::= { snaSessEntry 8 }

	sessSXidBlockNum  OBJECT-TYPE
	   SYNTAX OCTET STRING (SIZE (3))
	   MAX-ACCESS read-write
	   STATUS current
	   DESCRIPTION
	  "The BLOCKNUM part of the XID information sent by this side for the 
	   SNA session initiation
	  "
	::= { snaSessEntry 9 }


	sessSSap  OBJECT-TYPE
	   SYNTAX Sap
	   MAX-ACCESS read-write
	   STATUS current
	   DESCRIPTION
	  "The Local SAP used by SNAR for this session's side (LLC 
	   sessions only)
	  "
	::= { snaSessEntry 10 }

	sessDSap  OBJECT-TYPE
	   SYNTAX Sap
	   MAX-ACCESS read-write
	   STATUS current
	   DESCRIPTION
	  "The remote SAP used by SNAR for this session's side
	   (LLC sessions only)
	  "
	::= { snaSessEntry 11 }

	sessRemMacAddr  OBJECT-TYPE
	   SYNTAX MacAddress
	   MAX-ACCESS read-write
	   STATUS current
	   DESCRIPTION
	  "The remote MAC address used by this session's side
	   (LLC  sessions only)
	  "
	  ::= { snaSessEntry 12 }

	sessSdlcAddr  OBJECT-TYPE
	   SYNTAX SdlcAddr
	   MAX-ACCESS read-write
	   STATUS current
	   DESCRIPTION
	  "The SDLC address used by this session's side
	   (SDLC sessions only, both primary and secondary)
	  "
	::= { snaSessEntry 13 }

	sessGroupPoll  OBJECT-TYPE
	   SYNTAX  SdlcAddr
	   MAX-ACCESS read-write
	   STATUS current
	   DESCRIPTION
	  "The address of the group poll in which this session's side
		    participates (SLDC secondary only).
	   A value of 0 indicates that it doesn't participate 
	   in any group. Only one group is supported for each
	   SDLC line (same port)
	  "
	::= { snaSessEntry 14 }

	sessRole  OBJECT-TYPE
	   SYNTAX INTEGER{
	     primary   (1),
	     secondary (2)
	   }
	   MAX-ACCESS read-write
	   STATUS current
	   DESCRIPTION
	  "The type of SDLC session for this side. 
	  "
	::= { snaSessEntry 15 }

	sessIpEncapsulated  OBJECT-TYPE
	   SYNTAX  INTEGER { disable(1) , enable(2) }
	   MAX-ACCESS read-write
	   STATUS current
	   DESCRIPTION
	  "Specified whether this session data is encapsulated within 
	   UDP/IP
	  "
	::= { snaSessEntry 16 }  

	sessDestIpAddr  OBJECT-TYPE
	   SYNTAX IpAddress
	   MAX-ACCESS read-write
	   STATUS current
	   DESCRIPTION
	  "The destination IP address (IP encapsulated sessions only).
	  "
	::= { snaSessEntry 17 }  

	sessRemX25Addr  OBJECT-TYPE
	   SYNTAX OCTET STRING
	   MAX-ACCESS read-write
	   STATUS current
	   DESCRIPTION
	  "The remote X25 address (QLLC only) .
	  "
	::= { snaSessEntry 18 }

	   
      --*********
      snaSessTuneTable  OBJECT-TYPE
	   SYNTAX SEQUENCE OF SnaSessTuneEntry
	   MAX-ACCESS not-accessible
	   STATUS current
	   DESCRIPTION
	  " Holding SNA session parameters for each side of a
	    specific session, indexed by session_id
	  "
	::= { snarSna 4 }

       snaSessTuneEntry  OBJECT-TYPE
	   SYNTAX SnaSessTuneEntry
	   MAX-ACCESS not-accessible
	   STATUS current
       DESCRIPTION
	   "An entry in table snaSessTuneTable."
	   INDEX  { sessTuneIfIndex, sessTuneId, sessTuneSide}
	::= { snaSessTuneTable 1 }

	SnaSessTuneEntry ::=
	   SEQUENCE {
	   sessTuneIfIndex
	      Integer32,
	   sessTuneId
	      Integer32,
	   sessTuneSide 
	      INTEGER,

	   --** TUNNING   **
	   sessBufferSize
	      Integer32,
	   sessSegmentation
	      INTEGER,
	   sessFirstSide
	      INTEGER,
	   sessWindow
	      Integer32,
	   sessDuplex
	      INTEGER,
	   sessRXidBlockId
	      OCTET STRING,
	   sessRXidBlockNum
	      OCTET STRING,
	   sessCheckXid
	      INTEGER,
	   sessT1
	      Integer32,
	   sessTi
	      Integer32,
	   sessT2
	      Integer32,
	   sessN2
	      Integer32,
	   sessUdpPort
	      Integer32
	 }


	sessTuneIfIndex  OBJECT-TYPE
	   SYNTAX Integer32
	   MAX-ACCESS read-only
	   STATUS current
	   DESCRIPTION
	  " The SNA session side.
	  "
	::= { snaSessTuneEntry 1 }

	sessTuneId  OBJECT-TYPE
	   SYNTAX Integer32
	   MAX-ACCESS read-only
	   STATUS current
	   DESCRIPTION
	  " The unique identifier of the converted SNA session.
	  "
	 ::= { snaSessTuneEntry 2 }

	sessTuneSide  OBJECT-TYPE
	   SYNTAX INTEGER { sideA(1) , sideB(2) }
	   MAX-ACCESS read-only
	   STATUS current
	   DESCRIPTION
	  " The SNA session's side.
	  "
	::= { snaSessTuneEntry 3 }

	sessBufferSize  OBJECT-TYPE
	   SYNTAX Integer32
	   MAX-ACCESS read-write
	   STATUS current
	   DESCRIPTION
	  " The max. buffer size of remote device (All sessions).
	  "
	::= { snaSessTuneEntry 4 }

	sessSegmentation  OBJECT-TYPE
	   SYNTAX  INTEGER { disable(1) , enable(2) }
	   MAX-ACCESS read-write
	   STATUS current
	   DESCRIPTION
	  " Specifies whether the SNAR should perform
	    segmentation when incoming frame on one side is
	    longer then the sessSideBufferSize of the other size
	    
	    1 - disable - don't perform segmentation
	    2 - enable - perform segmentation
	  "
	::= { snaSessTuneEntry 5 }

	sessFirstSide  OBJECT-TYPE
	   SYNTAX INTEGER { sideA(1) , sideB(2) }
	   MAX-ACCESS read-only
	   STATUS current
	   DESCRIPTION
	  "Specifies which side of the two SNA sides (side_a or side_b) 
	   should be started first (SNAR only, N/A to devices)
	  "
	::= { snaSessTuneEntry 6 }



	sessWindow  OBJECT-TYPE
	   SYNTAX Integer32
	   MAX-ACCESS read-write
	   STATUS current
	   DESCRIPTION
	  " The max window size (1 .. 127) for this session's side.
	  "
	::= { snaSessTuneEntry 7 }

	sessDuplex  OBJECT-TYPE
	   SYNTAX INTEGER{
	    half (1),
	    full (2) 
	   }
	   MAX-ACCESS read-write
	   STATUS current
	   DESCRIPTION
	  " Specifies the type of SDLC device on the other end
	    of the SDLC line. FULL- means a device capable of
	    transmit and receive data simultaneously.
	  "
	::= { snaSessTuneEntry 8 }

	sessRXidBlockId  OBJECT-TYPE
	   SYNTAX OCTET STRING   (SIZE (2))
	   MAX-ACCESS read-write
	   STATUS current
	   DESCRIPTION
	  "The BLOCKID part of the XID information expected to be received
	   on this  side of the SNA session
	  "
	::= { snaSessTuneEntry 9 }

	sessRXidBlockNum  OBJECT-TYPE
	   SYNTAX OCTET STRING   (SIZE (3))
	   MAX-ACCESS read-write
	   STATUS current
	   DESCRIPTION
	  "The BLOCKNUM part of the XID information expected to be received
	   on this  side of the SNA session
	  "
	::= { snaSessTuneEntry 10 }

	sessCheckXid  OBJECT-TYPE
	   SYNTAX  INTEGER { disable(1) , enable(2) }
	   MAX-ACCESS read-write
	   STATUS current
	   DESCRIPTION
	  "Specified whether the received XID information should
	   be checked and compared to the value of sessRXid:
	    1 - disable: don't check
	    2 - enable  : check
	  "
	::= { snaSessTuneEntry 11 }

	sessT1  OBJECT-TYPE
	   SYNTAX Integer32
	   MAX-ACCESS read-write
	   STATUS current
	   DESCRIPTION
	  " The T1 timer (in 100 msec) for this  session's side.
	  "
	::= { snaSessTuneEntry 12 }

	sessTi  OBJECT-TYPE
	   SYNTAX Integer32
	   MAX-ACCESS read-write
	   STATUS current
	   DESCRIPTION
	  " The Ti timer (in sec) for this  session
	  "
	::= { snaSessTuneEntry 13 }

	sessT2  OBJECT-TYPE
	   SYNTAX Integer32
	   MAX-ACCESS read-write
	   STATUS current
	   DESCRIPTION
	  " The T2 timer (in 100 msec) for this   session
	  "
	::= { snaSessTuneEntry 14 }

	sessN2  OBJECT-TYPE
	   SYNTAX Integer32
	   MAX-ACCESS read-write
	   STATUS current
	   DESCRIPTION
	  " The N2 value for this  session's side  
	  "
	::= { snaSessTuneEntry 15 }

	sessUdpPort  OBJECT-TYPE
	   SYNTAX Integer32
	   MAX-ACCESS read-write
	   STATUS current
	   DESCRIPTION
	  " The UDP port used by SNAR (IP encapsulated 
		     sessions only)
	  "
	::= { snaSessTuneEntry 16 }  


      --*********
      snaSessStatTable  OBJECT-TYPE
	   SYNTAX SEQUENCE OF SnaSessStatEntry
	   MAX-ACCESS not-accessible
	   STATUS current
	   DESCRIPTION
	  "
	  Holding SNA session parameters for each side of a
		   specific session, indexed by session_id
	  "
	::= { snarSna 5 }

       snaSessStatEntry  OBJECT-TYPE
	   SYNTAX SnaSessStatEntry
	   MAX-ACCESS not-accessible
	   STATUS current
       DESCRIPTION
	   "An entry in table snaSessStatTable."
	   INDEX  { sessStatIfIndex, sessStatId, sessStatSide }
	::= { snaSessStatTable 1 }

	SnaSessStatEntry ::=
	   SEQUENCE {
	   sessStatIfIndex
	      Integer32,
	   sessStatId
	      Integer32,
	   sessStatSide
	      INTEGER,

	   --** STATISTICS **
	   sessStatTime
	      TimeTicks,
	   sessSPius
	      Counter32,
	   sessSBytes
	      Counter32,
	   sessRPius
	      Counter32,
	   sessRBytes
	      Counter32,
	   sessSessFailure
	      Counter32,
	   sessXidDenieds
	      Counter32
       }

       sessStatIfIndex  OBJECT-TYPE
	   SYNTAX Integer32
	   MAX-ACCESS read-only
	   STATUS current
	   DESCRIPTION
	  " "
	::= { snaSessStatEntry 1 }

	sessStatId  OBJECT-TYPE
	   SYNTAX Integer32
	   MAX-ACCESS read-only
	   STATUS current
	   DESCRIPTION
	  " The unique identifier of the converted SNA session.
	  "
	 ::= { snaSessStatEntry 2 }

       sessStatSide  OBJECT-TYPE
	   SYNTAX INTEGER { sideA(1) , sideB(2) }
	   MAX-ACCESS read-only
	   STATUS current
	   DESCRIPTION
	  " The SNA session's side.
	  "
	::= { snaSessStatEntry 3 }


	sessStatTime  OBJECT-TYPE
	   SYNTAX TimeTicks
	   MAX-ACCESS read-write
	   STATUS current
	   DESCRIPTION
	  " Time since last reset of this session statistics.
	    Setting to a   value of 0 will clear all session
	       statistics.
	  "
	   ::= { snaSessStatEntry 4 }

	sessSPius  OBJECT-TYPE
	   SYNTAX Counter32
	   MAX-ACCESS read-only
	   STATUS current
	   DESCRIPTION
	  " The number of PIUs sent by this  session's side 
	  "
	   ::= { snaSessStatEntry 5 }

	sessSBytes  OBJECT-TYPE
	   SYNTAX Counter32
	   MAX-ACCESS read-only
	   STATUS current
	   DESCRIPTION
	  " The number of bytes sent by this session's side.
	  "
	::= { snaSessStatEntry 6 }

	sessRPius  OBJECT-TYPE
	   SYNTAX Counter32
	   MAX-ACCESS read-only
	   STATUS current
	   DESCRIPTION
	  " The number of PIUs received by this session 
	  "
	::= { snaSessStatEntry 7 }

	sessRBytes  OBJECT-TYPE
	   SYNTAX Counter32
	   MAX-ACCESS read-only
	   STATUS current
	   DESCRIPTION
	  " The number of bytes received by this session's side.
	  "
	::= { snaSessStatEntry 8 }

	sessSessFailure  OBJECT-TYPE
	   SYNTAX Counter32
	   MAX-ACCESS read-only
	   STATUS current
	   DESCRIPTION
	  " The number of session failures occurs to this
	    session's side.
	  "
	::= { snaSessStatEntry 9 }

	sessXidDenieds  OBJECT-TYPE
	   SYNTAX Counter32 
	   MAX-ACCESS read-only
	   STATUS current
	   DESCRIPTION
	  " The number of XID denied by this session's side
	  "
	::= { snaSessStatEntry 10 }

      snaSessQllcTable  OBJECT-TYPE
	   SYNTAX SEQUENCE OF SnaSessQllcEntry
	   MAX-ACCESS not-accessible
	   STATUS current
	   DESCRIPTION
	  "
	  Holding SNA session parameters for each side of a
		   specific session, indexed by session_id
	  "
	::= { snarSna 7 }

       snaSessQllcEntry  OBJECT-TYPE
	   SYNTAX SnaSessQllcEntry
	   MAX-ACCESS not-accessible
	   STATUS current
       DESCRIPTION
	   "An entry in table snaSessQllcTable."
	   INDEX  { sessQllcIfIndex, sessQllcId, sessQllcSide }
	::= { snaSessQllcTable 1 }

	SnaSessQllcEntry ::=
	   SEQUENCE {
	   sessQllcIfIndex
	      Integer32,
	   sessQllcId
	      Integer32,
	   sessQllcSide
	      INTEGER,

		 --***QLLC PARAM
	   sessInCalls
	      INTEGER,
	   sessOutCalls     
	      INTEGER,
	   sessPVC
	      INTEGER,
	   sessCallReqData
	      OCTET STRING,
	   sessConnReqFacility
	      OCTET STRING,
	   sessGroupId
	      OCTET STRING,
	   sessDtePswd
	      OCTET STRING,
	   sessDteId
	      OCTET STRING,
	   sessMaxInPktSize
	      Integer32,           
	   sessMaxOutPktSize
	      Integer32,           
	   sessCallIndReverse
	      OCTET STRING
	}
	sessQllcIfIndex  OBJECT-TYPE
	   SYNTAX Integer32
	   MAX-ACCESS read-only
	   STATUS current
	   DESCRIPTION
	  " 
	  "
	::= { snaSessQllcEntry 1 }

	sessQllcId  OBJECT-TYPE
	   SYNTAX Integer32
	   MAX-ACCESS read-only
	   STATUS current
	   DESCRIPTION
	  " The unique identifier of the converted SNA session.
	  "
	 ::= { snaSessQllcEntry 2 }

       sessQllcSide  OBJECT-TYPE
	   SYNTAX  INTEGER { sideA(1) , sideB(2) }
	   MAX-ACCESS read-only
	   STATUS current
	   DESCRIPTION
	  " The SNA session's side.
	  "
	::= { snaSessQllcEntry 3 }


	sessInCalls  OBJECT-TYPE
	   SYNTAX  INTEGER { disable(1) , enable(2) }
	   MAX-ACCESS read-write
	   STATUS current
	   DESCRIPTION
	  "N/Allowed to accept call indicators (QLLC only)
	    1- disable: don't allow to accept call indications
	    2- enable:  Allow to accept call indications
	  "
	::= { snaSessQllcEntry 4 }


	sessOutCalls  OBJECT-TYPE
	   SYNTAX  INTEGER { disable(1) , enable(2) }
	   MAX-ACCESS read-write
	   STATUS current
	   DESCRIPTION
	  " N/Allowed to initiate call requests (QLLC only)
	    1- disable: don't allow to initiate call requests
	    2- enable:  Allow to initiate call requests
	  "
	::= { snaSessQllcEntry 5 }

	sessPVC  OBJECT-TYPE
	   SYNTAX  INTEGER { disable(1) , enable(2) }
	   MAX-ACCESS read-write
	   STATUS current
	   DESCRIPTION
	  " PVC being used or not  (QLLC only)
	       1 - disable :not use
	       2 - enable  :use
	  "
	::= { snaSessQllcEntry 6 }

	sessCallReqData  OBJECT-TYPE
	   SYNTAX OCTET STRING
	   MAX-ACCESS read-write
	   STATUS current
	   DESCRIPTION
	  " The user's data  for call requests (QLLC only).
	  "
	::= { snaSessQllcEntry 7 }


	sessConnReqFacility  OBJECT-TYPE
	   SYNTAX OCTET STRING
	   MAX-ACCESS read-write
	   STATUS current
	   DESCRIPTION
	  " The facilities for connection requests (QLLC only).
	  "
	::= { snaSessQllcEntry 8 }

	sessGroupId  OBJECT-TYPE
	   SYNTAX OCTET STRING
	   MAX-ACCESS read-write
	   STATUS current
	   DESCRIPTION
	  " The facility group id (QLLC only)
	  "
	::= { snaSessQllcEntry 9 }

	sessDtePswd  OBJECT-TYPE
	   SYNTAX OCTET STRING
	   MAX-ACCESS read-write
	   STATUS current
	   DESCRIPTION
	  " The password for local DTE (QLLC only)
	  "
	::= { snaSessQllcEntry 10}

	sessDteId  OBJECT-TYPE
	   SYNTAX OCTET STRING
	   MAX-ACCESS read-write
	   STATUS current
	   DESCRIPTION
	  " The identification for local DTE (QLLC only).
	  "
	::= { snaSessQllcEntry 11 }

	sessMaxInPktSize  OBJECT-TYPE
	   SYNTAX Integer32
	   MAX-ACCESS read-write
	   STATUS current
	   DESCRIPTION
	  " The max inbound packet size (QLLC only).
	  "
	::= { snaSessQllcEntry 12 }

	sessMaxOutPktSize  OBJECT-TYPE
	   SYNTAX Integer32
	   MAX-ACCESS read-write
	   STATUS current
	   DESCRIPTION
	  " The max outbound packet size (QLLC only).
	  "
	::= { snaSessQllcEntry 13 }

	sessCallIndReverse  OBJECT-TYPE
	   SYNTAX OCTET STRING
	   MAX-ACCESS read-write
	   STATUS current
	   DESCRIPTION
	  " 	  "
	   ::= { snaSessQllcEntry 14 }
--
--
 
cvtIfn    OBJECT IDENTIFIER ::= {radConverters 2  }
cvtSdlc   OBJECT IDENTIFIER ::= {cvtIfn 1 }

--****************************
--**** SDLC GROUP   **********
--****************************

	sdlcLinesNumber  OBJECT-TYPE
	      SYNTAX  Integer32
	      MAX-ACCESS  read-only
	      STATUS  current
	      DESCRIPTION
		      "
		      "
	      ::= { cvtSdlc 1 }

	sdlcTable  OBJECT-TYPE
	   SYNTAX SEQUENCE OF SdlcEntry
	   MAX-ACCESS not-accessible
	   STATUS current
	   DESCRIPTION
	  "
	  "
	::= { cvtSdlc 3 }

	sdlcEntry  OBJECT-TYPE
	   SYNTAX SdlcEntry
	   MAX-ACCESS not-accessible
	   STATUS current
       DESCRIPTION
	   "An entry in table sdlcTable."
	   INDEX  { sdlcIfIndex }
	::= { sdlcTable 1 }

		SdlcEntry ::=
		   SEQUENCE {
			sdlcIfIndex 
			      Integer32,
			sdlcNrz 
			      INTEGER,
			sdlcDuplex 
			      INTEGER,
			sdlcClockType
			      INTEGER,
			sdlcSpeed
			      Integer32,
			sdlcConnectorType
			      DisplayString,
			sdlcRts 
			      INTEGER
		}

	sdlcIfIndex  OBJECT-TYPE
	      SYNTAX  Integer32
	      MAX-ACCESS  read-only
	      STATUS  current
	      DESCRIPTION
			     "The value of this object identifies the
			      interface for which this entry
			      contains management information.  The
			      value of this object for a particular
			      interface has the same value as the
			      ifIndex object, defined in [4,6],
			      for the same interface."
	      ::= { sdlcEntry 1 }

	sdlcNrz  OBJECT-TYPE
	      SYNTAX  INTEGER { nrz(1), nrzi(2) }
	      MAX-ACCESS  read-write
	      STATUS  current
	      DESCRIPTION
		      "
		      "
	      ::= { sdlcEntry 2 }

	sdlcDuplex  OBJECT-TYPE
	      SYNTAX  INTEGER { half(1), full(2) }
	      MAX-ACCESS  read-write
	      STATUS  current
	      DESCRIPTION
		      "
		      "
	      ::= { sdlcEntry 3 }

	sdlcClockType  OBJECT-TYPE
	      SYNTAX  INTEGER { external(1), internal(2)}
	      MAX-ACCESS  read-write
	      STATUS  current
	      DESCRIPTION
		      "
		      "
	      ::= { sdlcEntry 4 }

	sdlcSpeed  OBJECT-TYPE
	      SYNTAX  Integer32
	      MAX-ACCESS  read-write
	      STATUS  current
	      DESCRIPTION
		      "
		      "
	      ::= { sdlcEntry 5 }

	sdlcConnectorType  OBJECT-TYPE
	      SYNTAX  DisplayString
	      MAX-ACCESS  read-only
	      STATUS  current
	      DESCRIPTION
		      "
		      "
	      ::= { sdlcEntry 6 }

	sdlcRts  OBJECT-TYPE
	      SYNTAX  INTEGER { constatnt(1), controled(2) }
	      MAX-ACCESS  read-only
	      STATUS  current
	      DESCRIPTION
		      "
		      "
	      ::= { sdlcEntry 7 }



	--**************

	sdlcStatTable  OBJECT-TYPE
	   SYNTAX SEQUENCE OF SdlcStatEntry
	   MAX-ACCESS not-accessible
	   STATUS current
	   DESCRIPTION
	  "
	  "
	::= { cvtSdlc 4 }

	sdlcStatEntry  OBJECT-TYPE
	   SYNTAX SdlcStatEntry
	   MAX-ACCESS not-accessible
	   STATUS current
       DESCRIPTION
	   "An entry in table sdlcStatTable."
	   INDEX  { sdlcStatIfIndex }
	::= { sdlcStatTable 1 }

		SdlcStatEntry ::=
		   SEQUENCE {
			sdlcStatIfIndex 
			      Integer32,
			sdlcTimeSinceReset
			      TimeTicks,
			sdlcStatFramesTrans 
			      Counter32,
			sdlcStatBytesTrans 
			      Counter32,
			sdlcStatFramesRcv 
			      Counter32,
			sdlcStatBytesRcv
			      Counter32,
			sdlcStatFramesAbort
			      Counter32,
			sdlcStatFramesBad
			      Counter32,
			sdlcStatFramesCrc 
			      Counter32

			}

	sdlcStatIfIndex  OBJECT-TYPE
	      SYNTAX  Integer32
	      MAX-ACCESS  read-only
	      STATUS  current
	      DESCRIPTION
			     "The value of this object identifies the
			      interface for which this entry
			      contains management information.  The
			      value of this object for a particular
			      interface has the same value as the
			      ifIndex object, defined in [4,6],
			      for the same interface."
	      ::= { sdlcStatEntry 1 }

	sdlcTimeSinceReset  OBJECT-TYPE
	      SYNTAX  TimeTicks
	      MAX-ACCESS  read-write
	      STATUS  current
	      DESCRIPTION
		      " The time laps since the last reset statistics.
		Setting the object  to   0 will   reset all  line statistics.
		      "
	      ::= { sdlcStatEntry 2 }

	sdlcStatFramesTrans  OBJECT-TYPE
	      SYNTAX  Counter32
	      MAX-ACCESS  read-only
	      STATUS  current
	      DESCRIPTION
		      "
		      "
	      ::= { sdlcStatEntry 3 }

	sdlcStatBytesTrans  OBJECT-TYPE
	      SYNTAX  Counter32
	      MAX-ACCESS  read-only
	      STATUS  current
	      DESCRIPTION
		      "
		      "
	      ::= { sdlcStatEntry 4 }

	sdlcStatFramesRcv  OBJECT-TYPE
	      SYNTAX  Counter32
	      MAX-ACCESS  read-only
	      STATUS  current
	      DESCRIPTION
		      "
		      "
	      ::= { sdlcStatEntry 5 }

	sdlcStatBytesRcv  OBJECT-TYPE
	      SYNTAX  Counter32
	      MAX-ACCESS  read-only
	      STATUS  current
	      DESCRIPTION
		      "
		      "
	      ::= { sdlcStatEntry 6 }

	sdlcStatFramesAbort  OBJECT-TYPE
	      SYNTAX  Counter32
	      MAX-ACCESS  read-only
	      STATUS  current
	      DESCRIPTION
		      "
		      "
	      ::= { sdlcStatEntry 7 }

	sdlcStatFramesBad  OBJECT-TYPE
	      SYNTAX  Counter32
	      MAX-ACCESS  read-only
	      STATUS  current
	      DESCRIPTION
		      " This counter holds the number of all   bad frames.
		      "
	      ::= { sdlcStatEntry 8 }

	sdlcStatFramesCrc  OBJECT-TYPE
	      SYNTAX  Counter32
	      MAX-ACCESS  read-only
	      STATUS  current
	      DESCRIPTION
		      "
		      "
	      ::= { sdlcStatEntry 9 }

-- LAN Token Ring interface
-- Private MIB - dot5 / TR interface unit

cvtDot5     OBJECT IDENTIFIER ::= { cvtIfn 2 }

	  cvtDot5Table  OBJECT-TYPE
		     SYNTAX  SEQUENCE OF CvtDot5Entry
		     MAX-ACCESS  not-accessible
		     STATUS  current
		     DESCRIPTION
			     "This table contains Token Ring interface
			     parameters and state variables. One entry
			     per 802.3 interface."
		     ::= { cvtDot5 1 }

	  cvtDot5Entry  OBJECT-TYPE
		     SYNTAX  CvtDot5Entry
		     MAX-ACCESS  not-accessible
		     STATUS  current
	         DESCRIPTION
	  	     "An entry in table cvtDot5Table."
		     INDEX   { cvtDot5IfIndex }
		     ::= { cvtDot5Table 1 }

	  CvtDot5Entry
	      ::= SEQUENCE {
		      cvtDot5IfIndex
			  Integer32,
		      cvtDot5MacAddr
			  MacAddress,
		      cvtDot5Commands
			  INTEGER,
		      cvtDot5RingSpeed
			  INTEGER,
		      cvtDot5ActMonParticipate
			  INTEGER,
		      cvtDot5Functional
			  MacAddress

		  }

	  cvtDot5IfIndex  OBJECT-TYPE
		     SYNTAX  Integer32
		     MAX-ACCESS  read-only
		     STATUS  current
		     DESCRIPTION
			     "The value of this object identifies the
			      802.5 interface for which this entry
			      contains management information.  The
			      value of this object for a particular
			      interface has the same value as the
			      ifIndex object, defined in [4,6],
			      for the same interface."
		     ::= { cvtDot5Entry 1 }


	  cvtDot5MacAddr OBJECT-TYPE
		     SYNTAX  MacAddress
		     MAX-ACCESS  read-write
		     STATUS  current
		     DESCRIPTION
			     "
			     "
		     ::= { cvtDot5Entry 2 }

	  cvtDot5Commands  OBJECT-TYPE
		     SYNTAX  INTEGER {
				   no-op(1),
				   open(2),
				   reset(3),
				   close(4)
			     }
		     MAX-ACCESS  read-write
		     STATUS  current
		     DESCRIPTION
			     "When this object is set to the value of
			      open(2), the station should go into the
			      open state. 
			       When this object is set to the value of
			      of reset(3), the station should perform reset.
			      When this object is set to the value
			      of close(4), the station should go into
			      the stopped state by removing itself
			      from the ring.
				  Setting this object to a value of
			      no-op(1) has no effect.
				  When read, this object always has a
			      value of no-op(1)."
		     ::= { cvtDot5Entry 3 }

	  cvtDot5RingSpeed  OBJECT-TYPE
		     SYNTAX  INTEGER {
				   unknown(1),
				   oneMegabit(2),
				   fourMegabit(3),
				   sixteenMegabit(4)
			     }
		     MAX-ACCESS  read-write
		     STATUS  current
		     DESCRIPTION
			     "The ring's bandwidth."
		     ::= { cvtDot5Entry 4 }

	  cvtDot5ActMonParticipate OBJECT-TYPE
		     SYNTAX  INTEGER {
				   true(1),
				   false(2)
			     }
		     MAX-ACCESS  read-write
		     STATUS  current
		     DESCRIPTION
			     "If this object has a value of true(1) then
			     this interface will participate in the
			     active monitor selection process.  If the
			     value is false(2) then it will not.
			     Setting this object might not have an
			     effect until the next time the interface
			     is opened."
		     ::= { cvtDot5Entry 5 }

	  cvtDot5Functional OBJECT-TYPE
		     SYNTAX  MacAddress
		     MAX-ACCESS  read-write
		     STATUS  current
		     DESCRIPTION
			     "The bit mask of all TR functional
			     addresses for which this interface will
			     accept frames."
		     ::= { cvtDot5Entry 6 }

-- LAN ETHERNET interface
-- Private MIB - dot3 interface unit

	  cvtDot3       OBJECT IDENTIFIER ::= { cvtIfn 3 }

	  cvtDot3Table  OBJECT-TYPE
		     SYNTAX  SEQUENCE OF CvtDot3Entry
		     MAX-ACCESS  not-accessible
		     STATUS  current
		     DESCRIPTION
			     "This table contains ETHERNET interface
			     parameters and state variables, one entry
			     per 802.3 interface."
		     ::= { cvtDot3 1 }

	  cvtDot3Entry  OBJECT-TYPE
		     SYNTAX  CvtDot3Entry
		     MAX-ACCESS  not-accessible
		     STATUS  current
	         DESCRIPTION
		     "An entry in table cvtDot3Table."
		     INDEX   { cvtDot3IfIndex }
		     ::= { cvtDot3Table 1 }

	  CvtDot3Entry
	      ::= SEQUENCE {
		      cvtDot3IfIndex
			  Integer32,
		      cvtDot3MacAddr
			  MacAddress,
		      cvtDot3Commands
			  INTEGER,
		     cvtDot3ActMonParticipate
			  INTEGER,
		      cvtDot3Functional
			  MacAddress

		  }

	  cvtDot3IfIndex  OBJECT-TYPE
		     SYNTAX  Integer32
		     MAX-ACCESS  read-only
		     STATUS  current
		     DESCRIPTION
			     "The value of this object identifies the
			      802.3 interface for which this entry
			      contains management information.  The
			      value of this object for a particular
			      interface has the same value as the
			      ifIndex object, defined in [4,6],
			      for the same interface."
		     ::= { cvtDot3Entry 1 }


	  cvtDot3MacAddr OBJECT-TYPE
		     SYNTAX  MacAddress
		     MAX-ACCESS  read-write
		     STATUS  current
		     DESCRIPTION
			     "
			     "
		     ::= { cvtDot3Entry 2 }

	  cvtDot3Commands  OBJECT-TYPE
		     SYNTAX  INTEGER {
				   no-op(1),
				   open(2),
				   reset(3),
				   close(4)
			     }
		     MAX-ACCESS  read-write
		     STATUS  current
		     DESCRIPTION
			     "When this object is set to the value of
			      open(2), the station should go into the
			      open state. 
			      of reset(3), then the station should do
			      a reset.  On a reset, all MIB counters
			      should retain their values, if possible.
			      Other side affects are dependent on the
			      hardware chip set.
				  When this object is set to the value
			      of close(4), the station should go into
			      the stopped state by removing itself
			      from the ring.
				  Setting this object to a value of
			      no-op(1) has no effect.
				  When read, this object always has a
			      value of no-op(1)."
		     ::= { cvtDot3Entry 3 }

	  cvtDot3ActMonParticipate OBJECT-TYPE
		     SYNTAX  INTEGER {
				   true(1),
				   false(2)
			     }
		     MAX-ACCESS  read-write
		     STATUS  current
		     DESCRIPTION
			     "If this object has a value of true(1) then
			     this interface will participate in the
			     active monitor selection process.  If the
			     value is false(2) then it will not.
			     Setting this object might not have an
			     effect until the next time the interface
			     is opened."
		     ::= { cvtDot3Entry 4 }

	  cvtDot3Functional OBJECT-TYPE
		     SYNTAX  MacAddress
		     MAX-ACCESS  read-write
		     STATUS  current
		     DESCRIPTION
			     "The bit mask of all Ethernet functional
			     addresses for which this interface will
			     accept frames."
		     ::= { cvtDot3Entry 5 }



-- 
-- file :v:\doc\rdv\mib\Before~1\stkhubgn.txt
-- 
--Version:   1.0
--Date:    17.10.94
--By:        Orly Nicklass      
--File:          stkhubgn.txt
--Last update: Smadar Tauber 12.02.96

radStkHubEvents OBJECT-IDENTITY
     STATUS  current
     DESCRIPTION
     "The events for Rad Stackable General products."
     ::= { radStkHub 0 }

 stkHubGen              OBJECT IDENTIFIER ::= { radStkHub 1 }  -- Rad Stackable General

 stkHubGenAgn OBJECT IDENTIFIER ::= { stkHubGen 1 }  -- Rad Stackable Agent



-- Stackable Hub's agent general parameters 

stkHubAgentResetConfig OBJECT-TYPE
      SYNTAX  INTEGER {
	  off(2),
	  on(3)
      }
      MAX-ACCESS  read-write
      STATUS  current
      DESCRIPTION
      "Setting the value to ON(3)is interpreted as a reset command
      for the agent NV Ram. When reset process is ended, a trap
      will be issued. "
      ::= { stkHubGenAgn 1 }

stkHubAgentSpecific OBJECT-TYPE
      SYNTAX  OBJECT IDENTIFIER
      MAX-ACCESS  read-only
      STATUS  current
      DESCRIPTION
      " Object identifier of entity containing additional information
      regarding this instance."
      ::= { stkHubGenAgn 2 }


-- Hub's Security parameters 


stkHubSecurityTable OBJECT-TYPE
	       SYNTAX SEQUENCE OF StkHubSecurityEntry
	       MAX-ACCESS not-accessible
	       STATUS current
		   DESCRIPTION
		   "Hub's Security parameters."
	       ::= { stkHubGen 2 }

stkHubSecurityEntry OBJECT-TYPE
      SYNTAX StkHubSecurityEntry
      MAX-ACCESS not-accessible
      STATUS current
	  DESCRIPTION
	  "An entry in table stkHubSecurityTable."
      INDEX {   stkHubSecID }
      ::= { stkHubSecurityTable 1 }

StkHubSecurityEntry ::=
      SEQUENCE {
      stkHubSecID
	  Integer32,
      stkHubSecEnable
	  INTEGER,
      stkHubSecurityPattern
	  OCTET STRING,
      stkHubSecurityMask
	  OCTET STRING
      }


stkHubSecID OBJECT-TYPE
      SYNTAX  Integer32  (1..3)
      MAX-ACCESS  read-only
      STATUS  current
      DESCRIPTION
	  "Segment's security unique identification number"
      ::= { stkHubSecurityEntry 1 }

stkHubSecEnable  OBJECT-TYPE
      SYNTAX  INTEGER {
	  off(2),
	  on(3)
      }
      MAX-ACCESS  read-write
      STATUS  current
      DESCRIPTION
	  "This entry indicates whether the specific segment's security is active or not"
      ::= { stkHubSecurityEntry 2 }

stkHubSecurityPattern OBJECT-TYPE
      SYNTAX OCTET STRING
      MAX-ACCESS  read-write
      STATUS  current
      DESCRIPTION
	"A six-octet(48 bit) pattern: where the masked bits of stkHubSecurityMask
	 need to match the MAC address of each port within the segment.Value of all
	 zeros  indicates no security."
      ::= { stkHubSecurityEntry 3 }

stkHubSecurityMask  OBJECT-TYPE
      SYNTAX  OCTET STRING
      MAX-ACCESS  read-write
      STATUS  current
      DESCRIPTION
	"Mask of the allowed MAC address that can be connected through
	the ports within  the segment"
      ::= { stkHubSecurityEntry 4 }

-- Port Security parameters 

stkHubPrtSecurityTable OBJECT-TYPE
	       SYNTAX SEQUENCE OF StkHubPrtSecurityEntry
	       MAX-ACCESS not-accessible
	       STATUS current
		   DESCRIPTION
		   "Port Security parameters."
	       ::= { stkHubGen 3 }

stkHubPrtSecurityEntry OBJECT-TYPE
      SYNTAX StkHubPrtSecurityEntry
      MAX-ACCESS not-accessible
      STATUS current
	  DESCRIPTION
	  "An entry in table stkHubPrtSecurityTable."
      INDEX { stkHubModuleID, stkHubPrtID, stkHubPrtSecID }
      ::= { stkHubPrtSecurityTable 1 }

StkHubPrtSecurityEntry ::=
      SEQUENCE {
    stkHubModuleID
	 Integer32,
    stkHubPrtID
	 Integer32,
    stkHubPrtSecID
	 Integer32,
    stkHubPrtSecurityEnable
	 INTEGER,
    stkHubPrtSecurityPattern
	 OCTET STRING,
    stkHubPrtSecurityMask
	 OCTET STRING
}

stkHubModuleID OBJECT-TYPE
      SYNTAX  Integer32
      MAX-ACCESS  read-only
      STATUS  current
      DESCRIPTION
      "A unique identifier of the module(slot no.)this port is attached to."
      ::= { stkHubPrtSecurityEntry 1 }

stkHubPrtID OBJECT-TYPE
      SYNTAX  Integer32
      MAX-ACCESS  read-only
      STATUS  current
      DESCRIPTION
      "A unique identifier of the port within its module."
      ::= { stkHubPrtSecurityEntry 2 }

stkHubPrtSecID OBJECT-TYPE
      SYNTAX  Integer32
      MAX-ACCESS  read-only
      STATUS  current
      DESCRIPTION
      "A unique identifier of the security of a given port within its module."
      ::= { stkHubPrtSecurityEntry 3 }

stkHubPrtSecurityEnable OBJECT-TYPE
      SYNTAX  INTEGER {
	   unknown(1),
	   off(2),
	   on(3)
      }
      MAX-ACCESS  read-write
      STATUS  current
      DESCRIPTION
      "The value of this attribute determines application of the
       port security."
      ::= { stkHubPrtSecurityEntry 4 }

stkHubPrtSecurityPattern OBJECT-TYPE
      SYNTAX  OCTET STRING
      MAX-ACCESS  read-write
      STATUS  current
      DESCRIPTION
      "A six-octet(48 bit) pattern: where the masked bits of stkHubPortSecurityMask 
       need to match the MAC address."
      ::= { stkHubPrtSecurityEntry 5 }

stkHubPrtSecurityMask OBJECT-TYPE
      SYNTAX  OCTET STRING
      MAX-ACCESS  read-write
      STATUS  current
      DESCRIPTION
      "Mask of the allowed MAC address that can be connected through
      this port. The security of the individual port over writes  the
       security of the segment where the port belongs to"
      ::= { stkHubPrtSecurityEntry 6 }


-- Traps are defined using the conventions in RFC 1215 [6].

		
softErrors NOTIFICATION-TYPE
      STATUS  current
      DESCRIPTION
      " This trap is sent when the software errors threshold is 
        exceeded."
      ::= { radStkHubEvents 33 }

resetRequired NOTIFICATION-TYPE
      OBJECTS  { trimErrorDesc, trimErrorSeverity, agnLed} 
      STATUS  current
      DESCRIPTION
      "This trap indicates that in order to perform the last SET 
       request, a reset operation  of the router/bridge is required. 
       This occurs when the layer 2 routing algorithm is changed 
       between SPF and Spanning Tree. The reset can be performed 
       manually or using the variable radBridgeAction."
      ::= { radRBHEEvents 10 }

compNotActive NOTIFICATION-TYPE
      OBJECTS  { trimErrorDesc, trimErrorSeverity, agnLed}
      STATUS  current
      DESCRIPTION
      "Compression was enabled but cannot be activated, since 
       connected device does not support correct compression. "
      ::= { radRBHEEvents 20 }

noCompression NOTIFICATION-TYPE
     OBJECTS  { trimErrorDesc, trimErrorSeverity, agnLed}
     STATUS  current
     DESCRIPTION
     "Compression card not present."
     ::= { radRBHEEvents 21 }

errorBackUp NOTIFICATION-TYPE
      OBJECTS  { trimErrorDesc, trimErrorSeverity, agnLed}
      STATUS  current
      DESCRIPTION
      "Automatic switchover to backup link because of excessive 
       link errors."
      ::= { radRBHEEvents 22 }

faultBackUp NOTIFICATION-TYPE
      OBJECTS  { trimErrorDesc, trimErrorSeverity, agnLed}
      STATUS  current
      DESCRIPTION
      "Automatic switchover to backup link because of main link 
       fault."
      ::= { radRBHEEvents 23 }

mainLinkUp NOTIFICATION-TYPE
      OBJECTS  { trimErrorDesc, trimErrorSeverity, agnLed}
      STATUS  current
      DESCRIPTION
      "Communication returned to main link."
      ::= { radRBHEEvents 24 }

failedDialUp NOTIFICATION-TYPE
      OBJECTS  { trimErrorDesc, trimErrorSeverity, agnLed}
      STATUS  current
      DESCRIPTION
      "Cannot establish backup dial-up connection."
     ::= { radRBHEEvents 25 }

extLoopBack   NOTIFICATION-TYPE
      OBJECTS  { trimErrorDesc, trimErrorSeverity, agnLed}
      STATUS  current
      DESCRIPTION
      " This trap is sent when Loopback starts on the link. "
      ::= { radRBHEEvents 29 }

dialUpConnFailed NOTIFICATION-TYPE
      OBJECTS  { trimErrorDesc, trimErrorSeverity, agnLed }
      STATUS  current
      DESCRIPTION
      " This trap is sent when the dialUp connection is terminated 
        due to a failure."
      ::= { radRBHEEvents 41 }

dialUpConnEstablished NOTIFICATION-TYPE
      OBJECTS  { trimErrorDesc, trimErrorSeverity, agnLed }
      STATUS  current
      DESCRIPTION
      " This trap is sent when the dialUp connection is established."
      ::= { radRBHEEvents 42 }

dialUpConnTerminated NOTIFICATION-TYPE
      OBJECTS  { trimErrorDesc, trimErrorSeverity, agnLed }
      STATUS  current
      DESCRIPTION
      " This trap is sent when the dialUp connection is normally 
        terminated."
      ::= { radRBHTEvents 43 }
-- 
-- file :v:\doc\rdv\mib\Before~1\stkhubtr.txt
-- 
--Title:       STK-T-MIB
--Version: 2.0
--Date:      9-aug-94
--By:         Orly Nicklass & Rina Nathaniel & Benny Dolnik
--File:        STKHUBTR.TXT
--Update:    26-December-95

-- Ring information for the ring the agent is connected to.

stkHubTR OBJECT IDENTIFIER ::= { radStkHub 2 }  --  Stackable Token Ring

stkHubTRRing       OBJECT IDENTIFIER ::= { stkHubTR 1}

stkHubTRRingCorrelationEnable OBJECT-TYPE
    SYNTAX  INTEGER {
        off(2),
        on(3)
    }
    MAX-ACCESS  read-write
    STATUS  current
    DESCRIPTION
       "When set to ON(3), the in-band agent should perform
       correlation each time a station enters/leaves the segment."
    ::= { stkHubTRRing 1 }

stkHubTRRingAutorecEnable OBJECT-TYPE
    SYNTAX  INTEGER {
        off(2),
        on(3)
    }
    MAX-ACCESS  read-write
    STATUS  current
    DESCRIPTION
       "When set to ON(3), the in-band agent should perform
       autorecovery each time a beacon status is detected."
    ::= { stkHubTRRing 2 }

stkHubTRRingAutorecResult OBJECT-TYPE
    SYNTAX  INTEGER {
        not-started(1),
        started(2),
        segment-ok(3),
        segment-fixed(4),
        segment-closed(5),
        failed(6)
    }
    MAX-ACCESS  read-only
    STATUS  current
    DESCRIPTION
       "When autorecovery is completed the result will be recorded.
       While in process, STARTED will be recorded.Before process, NOT STARTED
       will be recorded"
    ::= { stkHubTRRing 3 }


stkHubTRRingResetStatistics OBJECT-TYPE
    SYNTAX  INTEGER {
       unknown(1),
       off(2),
       on(3)
    }
    MAX-ACCESS  read-write
    STATUS  current
    DESCRIPTION
      "Setting the value of this attribute to ON(3) resets all the inband
      statistics and error counters."
    ::= { stkHubTRRing 4 }

stkHubTRRingLineErrCnt OBJECT-TYPE
    SYNTAX  Counter32
    MAX-ACCESS  read-only
    STATUS  current
    DESCRIPTION
       "This counter is incremented when a frame or token is copied or
       repeated by any of the stations on the ring, the E bit is zero in the frame
       or token and one of the following conditions exists: 1) there is a
       non-data bit (J or K bit) between the SD and the ED of the frame or token, or
       2) there is an FCS error in the frame."
    ::= { stkHubTRRing 5 }

stkHubTRRingBurstErrCnt OBJECT-TYPE
    SYNTAX  Counter32
    MAX-ACCESS  read-only
    STATUS  current
    DESCRIPTION
          "This counter is incremented when any of the stations on the ring detects the
          absence of transitions for five half-bit timers (burst-five error)."
    ::= { stkHubTRRing 6 }

stkHubTRRingACFCErrCnt  OBJECT-TYPE
    SYNTAX  Counter32
    MAX-ACCESS  read-only
    STATUS  current
    DESCRIPTION
        "This counter is incremented when any of the stations on the ring receives an 
        AMP or SMP frame in which A is equal to C is equal to 0, and then receives
        another SMP frame with A is equal to C is equal to 0 without first receiving an AMP
        frame. It denotes a station that cannot set the AC bits properly."
    ::= { stkHubTRRing 7 }

stkHubTRRingTotErrCnt OBJECT-TYPE
    SYNTAX  Counter32
    MAX-ACCESS  read-only
    STATUS  current
    DESCRIPTION
        "The total of the above described errors"
    ::= { stkHubTRRing 8 }

stkHubTRRingTotErrThreshold OBJECT-TYPE
    SYNTAX  Integer32
    MAX-ACCESS  read-write
    STATUS  current
    DESCRIPTION
       "The Total Errors Threshold value. A trap indicating Soft Error
	    will be sent, if the total number of errors during the last 10 seconds,
		reached the threshold value. Threshold value = 0 , disables this trap."
    ::= { stkHubTRRing 9}

stkHubTRRingTotalFrames OBJECT-TYPE
    SYNTAX  Counter32
    MAX-ACCESS  read-only
    STATUS  current
    DESCRIPTION
        "The total frames of the Ring."
    ::= { stkHubTRRing 10 }

stkHubTRRingTotalFramesRate OBJECT-TYPE
    SYNTAX  Integer32
    MAX-ACCESS  read-only
    STATUS  current
    DESCRIPTION
        "The rate of total frames on the Ring."
    ::= { stkHubTRRing 11 }

stkHubTRRingTotalOctets OBJECT-TYPE
    SYNTAX  Counter32
    MAX-ACCESS  read-only
    STATUS  current
    DESCRIPTION
	"The total octets of the Ring."
    ::= { stkHubTRRing 12 }

stkHubTRRingOctetsRatio OBJECT-TYPE
    SYNTAX  Integer32
    MAX-ACCESS  read-only
    STATUS  current
    DESCRIPTION
    "Current traffic for the last time interval. The traffic is 
     expressed in percents of the maximum TokenRing traffic ."
    ::= { stkHubTRRing 13 }



--  Bridge Hub Module table for TR media type
--  Contains general information about the Module


stkHubTRMdl       OBJECT IDENTIFIER ::= { stkHubTR 2}

 stkHubTRMdlTable OBJECT-TYPE
    SYNTAX SEQUENCE OF  StkHubTRMdlEntry
    MAX-ACCESS not-accessible
    STATUS current
	DESCRIPTION
	"Bridge Hub Module table for TR media type
	 Contains general information about the Module"
    ::= { stkHubTRMdl 1 }

stkHubTRMdlEntry OBJECT-TYPE
    SYNTAX StkHubTRMdlEntry
    MAX-ACCESS    not-accessible
    STATUS current
	DESCRIPTION
	"An entry in table stkHubTRMdlTable."
    INDEX     {stkHubTRMdlID}
    ::= { stkHubTRMdlTable 1}

StkHubTRMdlEntry ::=
    SEQUENCE {
   stkHubTRMdlID
           Integer32,
   stkHubTRMdlType
          INTEGER,
   stkHubTRMdlReset
          INTEGER,
   stkHubTRMdlLed
          OCTET STRING,
   stkHubTRMdlSpeed
          INTEGER,
   stkHubTRMdlMngState
          INTEGER,
   stkHubTRMdlAutodisable
          INTEGER,
   stkHubTRMdlConfigMsg
          OCTET STRING
        }

stkHubTRMdlID OBJECT-TYPE
      SYNTAX  Integer32 (1..10)
      MAX-ACCESS  read-only
      STATUS  current
      DESCRIPTION
      "A unique identifier of the module in stack. Internal module identifier
      is always 1 "
      ::= {stkHubTRMdlEntry 1}

stkHubTRMdlType OBJECT-TYPE
      SYNTAX  INTEGER {
	       unknown(1),
		   sah16int(2),
		   sah16ext(3),
		   empty(255)
		      }
      MAX-ACCESS  read-only
      STATUS  current
      DESCRIPTION
       "Indicates the type of the module connected with specific identifier "
      ::= {stkHubTRMdlEntry 2 }

 stkHubTRMdlReset  OBJECT-TYPE
      SYNTAX  INTEGER {
           unknown(1),
           off(2),
           on(3)
             }
      MAX-ACCESS  read-write
      STATUS  current
      DESCRIPTION
      "When this object is set to the value of ON(3),
       the module performs software reset. Upon completion, a trap  will
       be issued to the management station and  the value
       will be set to OFF."
      ::= {stkHubTRMdlEntry 3}

stkHubTRMdlLed  OBJECT-TYPE
      SYNTAX  OCTET STRING
      MAX-ACCESS  read-only
      STATUS  current
      DESCRIPTION
        "This entry specifies  the LEDs status in the module . Each led will 
         be represented by 4 bits where the first 2 bits will specify  the 
         status (NA, OFF, ON, BLINK), and the next two bits
         will specify the color (RED, GREEN, YELLOW)"
      ::= {stkHubTRMdlEntry 4}

stkHubTRMdlSpeed OBJECT-TYPE
      SYNTAX  INTEGER {
          unknown(1),
          fourMegabit(2),
          sixteenMegabit(3)
      }
      MAX-ACCESS  read-write
      STATUS  current
      DESCRIPTION
      "Attribute describing the bandwidth of the media as set by the module
       switch.       
       For certain products, if the value of stkHubTRMdlMngState 
       is 'enabled', then stkHubTRMdlSpeed can be set to the desired 
       value. Else, it will be read-only, and will show the status 
       of the jumper set of the main module.
       Refer product's manual."
      ::= { stkHubTRMdlEntry 5}

stkHubTRMdlMngState   OBJECT-TYPE
      SYNTAX  INTEGER {
	   unknown (1),
	   disabled(2),
       enabled (3)
      }    
      MAX-ACCESS  read-only
      STATUS  current
      DESCRIPTION
       "This object indicates the status of the Manage switch 
        as set on the back panel of the main module.
        'enabled' - means that management can override setting of 
                    some HW switch/es."
      ::= {stkHubTRMdlEntry 6 }


stkHubTRMdlAutodisable  OBJECT-TYPE
      SYNTAX   INTEGER {
                unknown(1),
                off(2),
                on(3)
        }
      MAX-ACCESS  read-write
      STATUS  current
      DESCRIPTION
      "Attribute describing the status of port Autodisable 
       mechanism, that protects against inserting in Token Ring 
       adapters at the wrong speed.
       For certain products, if the value of stkHubTRMdlMngState 
       is 'enabled', then stkHubTRMdlAutodisable can be set to 
       the desired value. Else, it will be read-only, and will 
       show the status of the jumper set of the main module.
       Refer product's manual."
   ::= {stkHubTRMdlEntry 7 }


stkHubTRMdlConfigMsg OBJECT-TYPE
      SYNTAX  OCTET STRING
      MAX-ACCESS  read-only
      STATUS  current
      DESCRIPTION
      "Full configuration message  coded in internal RND application format.
      This entry describes  module' configuration. "
      ::= {stkHubTRMdlEntry 8}


--  Bridge Hub  port table for TR media type
--  Contains general information about the ports.


stkHubTRPrt       OBJECT IDENTIFIER ::= { stkHubTR 3}

stkHubTRPrtTable OBJECT-TYPE
      SYNTAX SEQUENCE OF StkHubTRPrtEntry
      MAX-ACCESS not-accessible
      STATUS current
	  DESCRIPTION
	  "Bridge Hub  port table for TR media type
	   Contains general information about the ports."
      ::= { stkHubTRPrt 1 }

stkHubTRPrtEntry OBJECT-TYPE
      SYNTAX    StkHubTRPrtEntry
      MAX-ACCESS    not-accessible
      STATUS    current
	  DESCRIPTION
	  "An entry in table stkHubTRPrtTable."
      INDEX     {  stkHubTRPrtMdlID,
                   stkHubTRPrtID }
      ::= { stkHubTRPrtTable 1 }

StkHubTRPrtEntry ::=
      SEQUENCE {
      stkHubTRPrtMdlID
             Integer32,
      stkHubTRPrtID
             Integer32,
      stkHubTRPrtFunctionality
             INTEGER,
      stkHubTRPrtConnectorType
             INTEGER,
      stkHubTRPrtAdminCmd
             INTEGER,
      stkHubTRPrtActiveState
             INTEGER,
      stkHubTRPrtTrapMaskEnable
             INTEGER,
      stkHubTRPrtStatus
             INTEGER,
      stkHubTRPrtCableProtectEnable
             INTEGER,
	  stkHubTRPrtFlipProtectEnable
	         INTEGER,
      stkHubTRPrtMACAddress
             MacAddress,
      stkHubTRPrtType
             INTEGER
      }

stkHubTRPrtMdlID OBJECT-TYPE
      SYNTAX  Integer32
      MAX-ACCESS  read-only
      STATUS  current
      DESCRIPTION
      "A unique identifier of the module this port is attached to."
      ::= { stkHubTRPrtEntry 1 }

stkHubTRPrtID OBJECT-TYPE
      SYNTAX  Integer32
      MAX-ACCESS  read-only
      STATUS  current
      DESCRIPTION
      "A unique identifier of the port within its module."
      ::= { stkHubTRPrtEntry 2 }

stkHubTRPrtFunctionality OBJECT-TYPE
      SYNTAX  INTEGER {
           unknown(1),
           ringin(2) ,
           ringout(3) ,
           satellite(4),
           lobe(5)
      }
      MAX-ACCESS  read-only
      STATUS  current
      DESCRIPTION
      "Describes the functionality of the port in a Token ring topology"
      ::= { stkHubTRPrtEntry 3 }

stkHubTRPrtConnectorType OBJECT-TYPE
      SYNTAX  INTEGER {
           notApplicable(1),
           idc(2),
           rj45(3),
           srJ45(4),
           db9(5),
           bnc(6),
           fo-st(7),
           db25(8)
--         fo-sma(8),
--         fo-fc(9)
      }
      MAX-ACCESS  read-only
      STATUS  current
      DESCRIPTION
      "Type of hardware connector in the port."
      ::= { stkHubTRPrtEntry 4 }

stkHubTRPrtAdminCmd OBJECT-TYPE
      SYNTAX  INTEGER {
          unknown(1),
          disable(2),
          enable(3),
          short(4),
          normal(5)
      }
      MAX-ACCESS  read-write
      STATUS  current
      DESCRIPTION
         "By setting this attribute to DISABLE(2) or SHORT(4) the
         management station can force this  lobe/port-connection  to be
         removed and block any access to the  network via this lobe/port.
         It is not mandatory that a certain lobe/port will support all the
         enumerated states. The state of the lobe/port is type specific and
         indicated within the specific group"
      ::= { stkHubTRPrtEntry 5 }

stkHubTRPrtActiveState OBJECT-TYPE
      SYNTAX  INTEGER {
          unknown(1),
          off(2),
          on(3),
          standby(4)
      }
      MAX-ACCESS  read-only
      STATUS  current
      DESCRIPTION
        "This attribute describes the electrical or optical activity
         state of  a lobe or the state of a port.  Certain values may
         not be applicable in some cases"
      ::= { stkHubTRPrtEntry 6 }

stkHubTRPrtTrapMaskEnable OBJECT-TYPE
      SYNTAX  INTEGER {
          off(2),
          on(3)
      }
      MAX-ACCESS  read-write
      STATUS  current
      DESCRIPTION
      "When this attribute is set to OFF by the management console the
       agent starts sending the unmasked traps related to this port.
       Otherwise no traps from this port are sent."
      ::= { stkHubTRPrtEntry 7 }

stkHubTRPrtStatus OBJECT-TYPE
      SYNTAX  INTEGER {
          unknown(1),
          disabledManual(2),
          disabledAutorec(3),
          disabledSecurity(4),
          disabledAuto(5),
          disabledFlip(6),
          inserted(7),
          bypass(8),
          forcedloop(9),
          trunkfail(10),
          normal(11)
      }
      MAX-ACCESS  read-only
      STATUS  current
      DESCRIPTION
      "This attribute indicates the status of this lobe/port connection:
      DISABLED-(2) to  (6) indicates the reason for the disabled state.
      INSERTED(7)indicates that the lobe hardware inserts this lobe into
      the ring , thus it becomes part of the ring
      BYPASSED(8)indicates that the ring bypasses this lobe and the lobe
      hardware provides loopback connection towards the station for media 
      test purposes.
      FORCEDLOOP(9) indicates the port is in a loopback state and the
      main ring is connected to the backup path.
      TRUNKFAIL (10) indicates that the ring connection is broken for a
      repeater, converter or a cable protector.
      NORMAL(11) indicates the port is in normal condition
      It is not mandatory that a certain lobe/port will support all the 
       enumerated states."
      ::= { stkHubTRPrtEntry 8 }

stkHubTRPrtCableProtectEnable OBJECT-TYPE
      SYNTAX  INTEGER {
          unknown(1),
          off(2),
          on(3),
          inhibit(4)
      }
      MAX-ACCESS  read-only
      STATUS  current
      DESCRIPTION
      "The value of this attribute determines activation of the cable-fault
      protection mechanism of  TCR and the optical link mechanism of
      TFR and TFC ."
      ::= { stkHubTRPrtEntry  9 }

stkHubTRPrtFlipProtectEnable OBJECT-TYPE
      SYNTAX  INTEGER {
          unknown(1),
          off(2),
          on(3)
      }
      MAX-ACCESS  read-write
      STATUS  current
      DESCRIPTION
      "The value of this attribute determines activation of the flipping-lobe
      protection mechanism of the port."
      ::= { stkHubTRPrtEntry  10 }

stkHubTRPrtMACAddress OBJECT-TYPE
      SYNTAX  MacAddress
      MAX-ACCESS  read-only
      STATUS  current
      DESCRIPTION
      " The value of this object is the specific MAC address
      of this interface which uniquely identifies this Interface
      on a ring."
      ::= { stkHubTRPrtEntry 11 }

stkHubTRPrtType OBJECT-TYPE
      SYNTAX  INTEGER
      {
      notApplicable(1),
      tfr(2),
      tfc(3),
      tcr(4),
      tcp(5)
      }
      MAX-ACCESS  read-only
      STATUS  current
      DESCRIPTION
      "Type of the port specific hardware"
      ::= { stkHubTRPrtEntry 12}

		
-- TRAPS

--NOTIFICATIONS

stkHubTREvents OBJECT-IDENTITY
	   STATUS  current
	   DESCRIPTION
	  "The events for Stackable Token Ring."
	  ::= { stkHubTR 0 }

macAddressUpdated  NOTIFICATION-TYPE
   OBJECTS { stkHubTRPrtMACAddress }
   STATUS  current
   DESCRIPTION
   "This trap will be sent upon every change of 
    MACAddress on a port."
   ::= { stkHubTREvents 91 }

mdlStatusChanged  NOTIFICATION-TYPE
   OBJECTS { stkHubTRMdlLed, stkHubTRMdlType }
   STATUS  current
   DESCRIPTION
   "This trap is sent each time module status was changed.When a module is 
    disconnected, the stkHubTRMdlLed status will be 00 (no led) and the
    stkHubTRMdlType will be empty(255)."
    ::= { stkHubTREvents 27 }

ringBeaconing  NOTIFICATION-TYPE
   OBJECTS  { trimErrorDesc, trimErrorSeverity, agnLed }
   STATUS  current
   DESCRIPTION
   "This trap is sent when Token Ring LAN is beaconing."
   ::= { radRBHTEvents 30 }

lanAdapterRemoved  NOTIFICATION-TYPE
   OBJECTS  { trimErrorDesc, trimErrorSeverity, agnLed }
   STATUS  current
   DESCRIPTION
   "This trap is sent when Token Ring LAN adapter was removed by LAN 
   manager."
   ::= { radRBHTEvents 31 }

-- 
-- file :v:\doc\rdv\mib\Before~1\stkhubet.txt
-- 

--Title:        STK-E-MIB
-- Version: 1.0
--Date:       9.10.94
--By:          Orly Nicklass & Rina Nathaniel & Benny Dolnik
--File:         STKHUBET.TXT  

--Update:   09.03.95



stkHubET OBJECT IDENTIFIER ::= { radStkHub 3 }  --  Stackable Ethernet


--  Bridge Hub Module table for ET media type
--  Contains general information about the Module


stkHubETMdl       OBJECT IDENTIFIER ::= { stkHubET 2}

 stkHubETMdlTable OBJECT-TYPE
    SYNTAX SEQUENCE OF  StkHubETMdlEntry
    MAX-ACCESS not-accessible
    STATUS current
	DESCRIPTION
	"Bridge Hub Module table for ET media type
	 Contains general information about the Module"
    ::= { stkHubETMdl 1 }

stkHubETMdlEntry OBJECT-TYPE
    SYNTAX StkHubETMdlEntry
    MAX-ACCESS    not-accessible
    STATUS current
	DESCRIPTION
	"An entry in table stkHubETMdlTable."
    INDEX     {stkHubETMdlID}
    ::= { stkHubETMdlTable 1}

StkHubETMdlEntry ::=
    SEQUENCE {
   stkHubETMdlID
           Integer32,
   stkHubETMdlLed
           OCTET STRING,
   stkHubETMdlReset
          INTEGER
   }


stkHubETMdlID OBJECT-TYPE
      SYNTAX  Integer32 (1..10)
      MAX-ACCESS  read-only
      STATUS  current
      DESCRIPTION
      "A unique identifier of the module in stack. Internal module identifier
      is always 1 "
      ::= {stkHubETMdlEntry 1}


stkHubETMdlLed  OBJECT-TYPE
      SYNTAX  OCTET STRING
      MAX-ACCESS  read-only
      STATUS  current
      DESCRIPTION
        "This entry specifies  the LEDs status in the module . Each led will 
         be represented by 4 bits where the first 2 bits will specify  the 
         status (NA, OFF, ON, BLINK), and the next two bits
         will specify the color (RED, GREEN, YELLOW)"
      ::= {stkHubETMdlEntry 2}


stkHubETMdlReset  OBJECT-TYPE
      SYNTAX  INTEGER {
           unknown(1),
           off(2),
           hwReset(3),
		   configReset(4)
             }
      MAX-ACCESS  read-write
      STATUS  current
      DESCRIPTION
      "When this object is set to the value of hwReset(3),
       the module performs HW reset. 
	   When this object is set to the value of configReset(4),
       the module performs Configuration reset.
       Upon completion, a trap  will
       be issued to the management station and  the value
       will be set to OFF."
      ::= {stkHubETMdlEntry 3}


-- Traps are defined using the conventions in RFC 1215 [6].

portStatusChanged  NOTIFICATION-TYPE
      OBJECTS  { stkHubETMdlLed, rpMauMediaAvailable, 
                                 rptrPortOperStatus }
      STATUS  current
      DESCRIPTION
      "This trap is sent each time port status was changed."
      ::= { radStkHubEvents 26 }
-- 
-- file :v:\doc\rdv\mib\Before~1\etrptr.txt
-- 
--Title:       ET-RPTR-MIB
--Version: 1.0
--Date:      26-JAN-94
--By:         Orly Nicklass 
--File:        ETRPTR.TXT

--Update:  12-MAR-95

  -- Basic Repeater Information
  --
  -- Configuration, status, and control objects for the overall
  -- repeater
  --

radEthRptr  OBJECT IDENTIFIER ::= { rad 9 } -- Ethernet Repeaters products 


etRptrTable  OBJECT-TYPE
	SYNTAX  SEQUENCE OF EtRptrEntry
	MAX-ACCESS  not-accessible
	STATUS current
	DESCRIPTION
	"This table contains repeater data specific to the etRptrIndex."
	::= { radEthRptr 1 }

etRptrEntry OBJECT-TYPE
	SYNTAX  EtRptrEntry
	MAX-ACCESS  not-accessible
	STATUS current
    DESCRIPTION
    "An entry in table etRptrTable."
	INDEX { etRptrIndex  }
	::= { etRptrTable 1 }


EtRptrEntry  ::=
	    SEQUENCE {
	etRptrIndex
	  Integer32,
	etRptrGroupCapacity
	  Integer32,
	etRptrOperStatus
	  INTEGER,
	etRptrHealthText
	  DisplayString,
	etRptrReset
	  INTEGER,
	etRptrNonDisruptTest
	  INTEGER,
	etRptrTotalPartitionedPorts
	  Gauge32,
	etRptrMdlVector
	  Integer32,
	etRptrMonitorTransmitCollisions
	  Counter32
	}

   etRptrIndex  OBJECT-TYPE		   
	   SYNTAX    Integer32 
       MAX-ACCESS    read-only
       STATUS    current
       DESCRIPTION
			   " The Repeater Id, this table data refer to." 
       ::= { etRptrEntry 1 }

   etRptrGroupCapacity OBJECT-TYPE
       SYNTAX    Integer32 (1..1024)
       MAX-ACCESS    read-only
       STATUS    current
       DESCRIPTION
               "The etRptrGroupCapacity is the number of groups
               that can be contained within the repeater.  Within
               each managed repeater, the groups are uniquely
               numbered in the range from 1 to etRptrGroupCapacity.

               Some groups may not be present in the repeater, in
               which case the actual number of groups present
               will be less than etRptrGroupCapacity.  The number
               of groups present will never be greater than
               etRptrGroupCapacity.

               Note:  In practice, this will generally be the
               number of field-replaceable units (i.e., modules,
               cards, or boards) that can fit in the physical
               repeater enclosure, and the group numbers will
               correspond to numbers marked on the physical
               enclosure."
       REFERENCE
               "Reference IEEE 802.3 Rptr Mgt, 19.2.3.2,
                RepeaterGroupCapacity."
       ::= { etRptrEntry 2 }

   etRptrOperStatus OBJECT-TYPE
       SYNTAX  INTEGER {
                   other(1),            -- undefined or unknown status
                   ok(2),               -- no known failures
                   rptrFailure(3),      -- repeater-related failure
                   groupFailure(4),     -- group-related failure
                   portFailure(5),      -- port-related failure
                   generalFailure(6)    -- failure, unspecified type
               }
       MAX-ACCESS    read-only
       STATUS    current
       DESCRIPTION
               "The etRptrOperStatus object indicates the
               operational state of the repeater.  The
               etRptrHealthText object may be consulted for more
               specific information about the state of the
               repeater's health.
               In the case of multiple kinds of failures (e.g.,
               repeater failure and port failure), the value of
               this attribute shall reflect the highest priority
               failure in the following order, listed highest
               priority first:

                   rptrFailure(3)
                   groupFailure(4)
                   portFailure(5)
                   generalFailure(6)."
       REFERENCE
               "Reference IEEE 802.3 Rptr Mgt, 19.2.3.2,
               aRepeaterHealthState."
       ::= { etRptrEntry 3 }

   etRptrHealthText OBJECT-TYPE
       SYNTAX    DisplayString (SIZE (0..255))
       MAX-ACCESS    read-only
       STATUS    current
       DESCRIPTION
               "The health text object is a text string that
               provides information relevant to the operational
               state of the repeater.  Agents may use this string
               to provide detailed information on current
               failures, including how they were detected, and/or
               instructions for problem resolution.  The contents
               are agent-specific."
       REFERENCE
               "Reference IEEE 802.3 Rptr Mgt, 19.2.3.2,
               aRepeaterHealthText."
       ::= { etRptrEntry 4 }


   etRptrReset OBJECT-TYPE
       SYNTAX    INTEGER {
                     noReset(1),
                     resetHW(2),
					 resetConfig(3)
                 }
       MAX-ACCESS    read-write
       STATUS    current
       DESCRIPTION
               "Setting this object to reset(2) causes a
               transition to the START state of Fig 9-2 in
               section 9 [IEEE 802.3 Std].

               Setting this object to noReset(1) has no effect.
               The agent will always return the value noReset(1)
               when this object is read.

               After receiving a request to set this variable to
               resetHW(2), the agent is allowed to delay the reset
               for a short period.  For example, the implementor
               may choose to delay the reset long enough to allow
               the SNMP response to be transmitted.  In any
               event, the SNMP response must be transmitted.

               This action does not reset the management counters
               defined in this document nor does it affect the
               portAdminStatus parameters.  Included in this
               action is the execution of a disruptive Self-Test
               with the following characteristics:  a) The nature
               of the tests is not specified.  b) The test resets
               the repeater but without affecting management
               information about the repeater.  c) The test does
               not inject packets onto any segment.  d) Packets
               received during the test may or may not be
               transferred.  e) The test does not interfere with
               management functions.

               After performing this self-test, the agent will
               update the repeater health information (including
               etRptrOperStatus and etRptrHealthText), and send a
               etRptrHealth trap.
               
               Setting this object to resetConfig(3) will cause
               resetting the repeater to its default values."
       REFERENCE
               "Reference IEEE 802.3 Rptr Mgt, 19.2.3.3,
               acResetRepeater."
       ::= { etRptrEntry 5 }

   etRptrNonDisruptTest OBJECT-TYPE
       SYNTAX    INTEGER {
                     noSelfTest(1),
                     selfTest(2)
                 }
       MAX-ACCESS    read-write
       STATUS    current
       DESCRIPTION
               "Setting this object to selfTest(2) causes the
               repeater to perform a agent-specific, non-
               disruptive self-test that has the following
               characteristics:  a) The nature of the tests is
               not specified.  b) The test does not change the
               state of the repeater or management information
               about the repeater.  c) The test does not inject
               packets onto any segment.  d) The test does not
               prevent the relay of any packets.  e) The test
               does not interfere with management functions.

               After performing this test, the agent will update
               the repeater health information (including
               etRptrOperStatus and etRptrHealthText) and send a
               etRptrHealth trap.

               Note that this definition allows returning an
               'okay' result after doing a trivial test.

               Setting this object to noSelfTest(1) has no
               effect.  The agent will always return the value
               noSelfTest(1) when this object is read."
       REFERENCE
               "Reference IEEE 802.3 Rptr Mgt, 19.2.3.3,
               acExecuteNonDisruptiveSelfTest."
       ::= { etRptrEntry 6 }

   etRptrTotalPartitionedPorts OBJECT-TYPE
       SYNTAX    Gauge32
       MAX-ACCESS    read-only
       STATUS    current
       DESCRIPTION
               "This object returns the total number of ports in
               the repeater whose current state meets all three
               of the following criteria:  etRptrPortOperStatus
               does not have the value notPresent(3),
               etRptrPortAdminStatus is enabled(1), and
               etRptrPortAutoPartitionState is autoPartitioned(2)."
       ::= { etRptrEntry 7 }

   etRptrMdlVector OBJECT-TYPE
       SYNTAX    Integer32
       MAX-ACCESS    read-write
       STATUS    current
       DESCRIPTION
               "This object returns a vector mapping the location of  the repeater modules
                    to their corresponding bit position. A bit that is set indicates an existing module "
       ::= { etRptrEntry 8 }


   --
   -- Repeater Monitor Information
   --
   -- Performance monitoring statistics for the repeater
   --

   etRptrMonitorTransmitCollisions OBJECT-TYPE
       SYNTAX    Counter32
       MAX-ACCESS    read-only
       STATUS    current
       DESCRIPTION
               "This counter is incremented every time the
               repeater state machine enters the TRANSMIT
               COLLISION state from any state other than ONE PORT
               LEFT (Ref: Fig 9-2, IEEE 802.3 Std).

               The approximate minimum time for rollover of this
               counter is 16 hours."
       REFERENCE
               "Reference IEEE 802.3 Rptr Mgt, 19.2.3.2,
               aTransmitCollisions."
       ::= { etRptrEntry 9 }


-- Repeater Security Table

	etRptrSecTable   OBJECT-TYPE
		   SYNTAX SEQUENCE OF EtRptrSecEntry
	       MAX-ACCESS not-accessible
	       STATUS current
		   DESCRIPTION
		   "Repeater Security Table"
	       ::= { radEthRptr 2 }

etRptrSecEntry OBJECT-TYPE
      SYNTAX EtRptrSecEntry
      MAX-ACCESS not-accessible
      STATUS current
      DESCRIPTION
	  "An entry in table etRptrSecTable."
      INDEX {etRptrId, etRptrSecID }
      ::= { etRptrSecTable 1 }

EtRptrSecEntry ::=
      SEQUENCE {
	  etRptrId
	  Integer32,
      etRptrSecID
	  Integer32,
      etRptrSecEnable
	  INTEGER,
      etRptrSecPattern
	  OCTET STRING,
      etRptrSecMask
	  OCTET STRING
      }


etRptrId  OBJECT-TYPE		   
	   SYNTAX    Integer32 
       MAX-ACCESS    read-only
       STATUS    current
       DESCRIPTION
       " The Repeater Id, this table data refer to." 
       ::= { etRptrSecEntry 1 }


etRptrSecID OBJECT-TYPE
      SYNTAX  Integer32  (1..3)
      MAX-ACCESS  read-only
      STATUS  current
      DESCRIPTION
	  "Segment's security unique identification number"
      ::= { etRptrSecEntry 2 }

etRptrSecEnable  OBJECT-TYPE
      SYNTAX  INTEGER {
	  off(2),
	  on(3)
      }
      MAX-ACCESS  read-write
      STATUS  current
      DESCRIPTION
	  "This entry indicates whether the specific segment's security is active or not"
      ::= { etRptrSecEntry 3 }

etRptrSecPattern OBJECT-TYPE
      SYNTAX OCTET STRING
      MAX-ACCESS  read-write
      STATUS  current
      DESCRIPTION
	"A six-octet(48 bit) pattern: where the masked bits of etRptrSecMask
	 need to match the MAC address of each port within the segment.Value of all
	 zeros  indicates no security."
      ::= { etRptrSecEntry 4 }


etRptrSecMask  OBJECT-TYPE
      SYNTAX  OCTET STRING
      MAX-ACCESS  read-write
      STATUS  current
      DESCRIPTION
	"Mask of the allowed MAC address that can be connected through
	the ports within  the segment"
      ::= { etRptrSecEntry 5 }



--NOTIFICATIONS

   radEthRptrEvents OBJECT-IDENTITY
	   STATUS  current
	   DESCRIPTION
	  "The events for Ethernet Repeater."
	  ::= { radEthRptr 0 }

   etRptrHealth NOTIFICATION-TYPE
       OBJECTS  { etRptrOperStatus, rptrGroupOperStatus, agnLed }
	   STATUS  current
       DESCRIPTION
               "The etRptrHealth trap conveys information related
               to the operational status of the repeater.  This
               trap is sent either when the value of
               etRptrOperStatus changes, or upon completion of a
               non-disruptive test.

               See the etRptrOperStatus object for descriptions 
               of the information that is sent.
               The agent must throttle the generation of
               consecutive etRptrHealth traps so that there is at
               least a five-second gap between traps of this
               type.  When traps are throttled, they are dropped,
               not queued for sending at a future time.  (Note
               that 'generating' a trap means sending to all
               configured recipients.)"
       REFERENCE
               "Reference IEEE 802.3 Rptr Mgt, 19.2.3.4,
               hubHealth notification."
       ::= { radEthRptrEvents 1 }


   etRptrResetEvent NOTIFICATION-TYPE
       OBJECTS   { etRptrOperStatus, etRptrIndex, agnLed }
	   STATUS  current
       DESCRIPTION
               "The etRptrResetEvent trap conveys information
               related to the operational status of the repeater.
               This trap is sent on completion of a repeater
               reset action.  A repeater reset action is defined
               as an a transition to the START state of Fig 9-2
               in section 9 [IEEE 802.3 Std], when triggered by a
               management command (e.g., an SNMP Set on the
               etRptrReset object).
               The agent must throttle the generation of
               consecutive etRptrResetEvent traps so that there is
               at least a five-second gap between traps of this
               type.  When traps are throttled, they are dropped,
               not queued for sending at a future time.  (Note
               that 'generating' a trap means sending to all
               configured recipients.)

               The etRptrResetEvent trap is not sent when the agent
               restarts and sends an SNMP coldStart or warmStart
               trap.  However, it is recommended that a repeater
               agent send the etRptrOperStatus object as an
               optional object with its coldStart and warmStart
               trap PDUs.

               The etRptrOperStatus object must be included in the
               varbind list sent with this trap.  The agent may
               optionally include the etRptrHealthText object as
               well."
       REFERENCE
               "Reference IEEE 802.3 Rptr Mgt, 19.2.3.4, hubReset
               notification."
       ::= { radEthRptrEvents 2 }


   etRptrConfig NOTIFICATION-TYPE
       OBJECTS  { etRptrMdlVector, agnLed }
	   STATUS  current
       DESCRIPTION
			   " This trap is sent upon every change of the
			     etRptrMdlVector object."
       ::= { radEthRptrEvents 3 }




-- 
-- file :v:\doc\rdv\mib\ver485\mpmx.txt
-- 

--Title:     RAD's WAN PRODUCTS MIB
--Version:   1.0
--Date:      31.1.1993
--By:        Yaira Gabay, Orly Nicklass
--Update :   10.11.1994
--By:  Arik Sadovski


--Last Update: 	 09-Sep-2002
--By:            Smadar Tauber
--File:          v:\doc\rdv\mib\ver485\mpmx.txt

--IMPORTS
--      enterprises                            FROM RFC1155-SMI
--      DisplayString                          FROM RFC1213-MIB
--      IpAddress                              FROM RFC1155-SMI
--      OCTET STRING                           FROM RFC1213-MIB
--      OBJECT-TYPE                            FROM RFC1212;


--Some MIB compilers need those two lines:
-- enterprises OBJECT IDENTIFIER ::=
--                       { iso org(3) dod(6) internet(1) private(4) 1 }

--systems OBJECT IDENTIFIER ::= { radGen 1}
--agnt OBJECT IDENTIFIER ::= { radGen 2}
--radSysWan OBJECT IDENTIFIER ::= { systems 3 }

--  -----------------------------------------------------------------------------

 wanGen   OBJECT IDENTIFIER ::= {radWan 1}

 muxHub OBJECT IDENTIFIER ::= {radWan 2}

--  ----------------------------------------------------------------------------------------------
chasWanGen  OBJECT IDENTIFIER ::= {wanGen 1}
agnWanGen   OBJECT IDENTIFIER ::= {wanGen 2}
mdlWanGen   OBJECT IDENTIFIER ::= {wanGen 3}
prtWanGen   OBJECT IDENTIFIER ::= {wanGen 4}
mapWanGen   OBJECT IDENTIFIER ::= {wanGen 5}
diverseIfWanGen OBJECT IDENTIFIER ::= {wanGen 6}
--ethIf          OBJECT IDENTIFIER ::= {diverseIfWanGen 1} (see ethif.txt)
--sonetInterface OBJECT IDENTIFIER ::= {diverseIfWanGen 2} (see radsonet.txt)
--ds3Interface	 OBJECT IDENTIFIER ::= {diverseIfWanGen 3} (see radds3.txt)
--ds1Interface	 OBJECT IDENTIFIER ::= {diverseIfWanGen 4} (see radds1.txt)
--hdlcMibObjects OBJECT IDENTIFIER ::= {diverseIfWanGen 5} (see radhdlc.txt)
--v51If          OBJECT IDENTIFIER ::= {diverseIfWanGen 6} (see v51.txt)
--ip2If          OBJECT IDENTIFIER ::= {diverseIfWanGen 7} (see ipmux.txt)
--broadbandIf    OBJECT IDENTIFIER ::= {diverseIfWanGen 8} (see bdband.txt)
--r2If           OBJECT IDENTIFIER ::= {diverseIfWanGen 9} (see r2.txt)
--adslIf		 OBJECT IDENTIFIER ::= {diverseIfWanGen 10} (see radadsl.txt)
--sdslIf		 OBJECT IDENTIFIER ::= {diverseIfWanGen 11} (see radsdsl.txt)
--shdslIf		 OBJECT IDENTIFIER ::= {diverseIfWanGen 12} (see radshdsl.txt)
--voipWanGen OBJECT IDENTIFIER ::= {wanGen 7} (see voip.txt)


statAgnGen       OBJECT IDENTIFIER ::= {agnWanGen 1}
cnfgAgnGen       OBJECT IDENTIFIER ::= {agnWanGen 2}
cmprAgnGen       OBJECT IDENTIFIER ::= {agnWanGen 3}
alrBuffGen       OBJECT IDENTIFIER ::= {agnWanGen 4}
agnFlipDb        OBJECT IDENTIFIER ::= {agnWanGen 5}
agnSa            OBJECT IDENTIFIER ::= {agnWanGen 6}
agnListDecoding  OBJECT IDENTIFIER ::= {agnWanGen 7}
agnSystemDlci    OBJECT IDENTIFIER ::= {agnWanGen 8}
agnVoiceSwitching    OBJECT IDENTIFIER ::= {agnWanGen 9}
agnSigProfile    OBJECT IDENTIFIER ::= {agnWanGen 10}
agnSystemTs      OBJECT IDENTIFIER ::= {agnWanGen 11}
systemVoice      OBJECT IDENTIFIER ::= {agnWanGen 12}

statMdlGen   OBJECT IDENTIFIER ::= {mdlWanGen 1}
cnfgMdlGen   OBJECT IDENTIFIER ::= {mdlWanGen 2}
cmprMdlGen   OBJECT IDENTIFIER ::= {mdlWanGen 3}


statPrtGen   OBJECT IDENTIFIER ::= {prtWanGen 1}
cnfgPrtGen   OBJECT IDENTIFIER ::= {prtWanGen 2}
cmprPrtGen   OBJECT IDENTIFIER ::= {prtWanGen 3}


agnMux        OBJECT IDENTIFIER ::= {muxHub 1}
mdlMux        OBJECT IDENTIFIER ::= {muxHub 2}
prtMux        OBJECT IDENTIFIER ::= {muxHub 3}


statPrtMux         OBJECT IDENTIFIER ::= {prtMux 1}
cnfgPrtMux         OBJECT IDENTIFIER ::= {prtMux 2}

--

--prtHsfStatTable   OBJECT IDENTIFIER ::= {statPrtMux 6}

--

prtClCnfg       OBJECT IDENTIFIER ::= {cnfgPrtMux 1}
prtPh1MlCnfg    OBJECT IDENTIFIER ::= {cnfgPrtMux 2} --MPH1/e1/t1
prtPhPlCnfg     OBJECT IDENTIFIER ::= {cnfgPrtMux 3} --MPH1,MPH3,MPL6
prtLs2Cnfg      OBJECT IDENTIFIER ::= {cnfgPrtMux 4} --LS2 family
--prtVc2CnfgTable      OBJECT IDENTIFIER ::= {cnfgPrtMux 5}
--prtHsfCnfgTable      OBJECT IDENTIFIER ::= {cnfgPrtMux 6}
prtHs4Cnfg      OBJECT IDENTIFIER ::= {cnfgPrtMux 7}
prtHsiCnfg      OBJECT IDENTIFIER ::= {cnfgPrtMux 8}
prtPVc4Cnfg     OBJECT IDENTIFIER ::= {cnfgPrtMux 9}
prtHsrCnfg      OBJECT IDENTIFIER ::= {cnfgPrtMux 10}
prtMbeCnfg      OBJECT IDENTIFIER ::= {cnfgPrtMux 11}
prtTreCnfg      OBJECT IDENTIFIER ::= {cnfgPrtMux 12}
prtLs6Cnfg      OBJECT IDENTIFIER ::= {cnfgPrtMux 13}
prtVc3Cnfg      OBJECT IDENTIFIER ::= {cnfgPrtMux 14}
prtVcPbxCnfg    OBJECT IDENTIFIER ::= {cnfgPrtMux 15}
prtIsdnCnfg     OBJECT IDENTIFIER ::= {cnfgPrtMux 16}
prtLogicalCnfg  OBJECT IDENTIFIER ::= {cnfgPrtMux 17}
prtFrPlusCnfg   OBJECT IDENTIFIER ::= {cnfgPrtMux 18}
prtMl4Cnfg      OBJECT IDENTIFIER ::= {cnfgPrtMux 19}
prtAcmCnfg      OBJECT IDENTIFIER ::= {cnfgPrtMux 20}
prtE2Cnfg       OBJECT IDENTIFIER ::= {cnfgPrtMux 21}

--
-- Wan chassis general information
--

chasVersion OBJECT-TYPE
      SYNTAX  DisplayString (SIZE (0..255))
      MAX-ACCESS  read-only
      STATUS  current
      DESCRIPTION
      "An ASCII string for description and display of the agent chassis version."
      ::= { chasWanGen 1 }

chasTotalNoOfSlt  OBJECT-TYPE
      SYNTAX  Integer32
      MAX-ACCESS  read-only
      STATUS  current
      DESCRIPTION
      "This entry indicates the number of physical slots in the
       chassis."
      ::= { chasWanGen 2 }

chasTotalNoOfIoSlt  OBJECT-TYPE
      SYNTAX  Integer32
      MAX-ACCESS  read-only
      STATUS  current
      DESCRIPTION
      "This entry indicates the total number of physical IO slots
       in the chassis, (not all slots hardware should be occupied
       and active) ."
      ::= { chasWanGen 3 }

chasTotalNoOfPsSlt  OBJECT-TYPE
      SYNTAX  Integer32
      MAX-ACCESS  read-only
      STATUS  current
      DESCRIPTION
      "This entry indicates the number of physical Power Supply
       slots in the chassis."
      ::= { chasWanGen 4 }

chasTotalNoOfClSlt  OBJECT-TYPE
      SYNTAX  Integer32
      MAX-ACCESS  read-only
      STATUS  current
      DESCRIPTION
      "This entry indicates the number of physical Common Logic slots in the
       chassis."
      ::= { chasWanGen 5 }

--
-- Wan agent status general information
--
agnSDateFormat  OBJECT-TYPE
      SYNTAX  INTEGER
       {
          ddMMYYYY (1),
          mmDDYYYY (2),
          yyyyDDMM (3),
		  yyyyMMDD (4)
       }
      MAX-ACCESS  read-write
      STATUS  current
      DESCRIPTION
      "This entry indicates the date and time format used for the
       agnSDateAndTimeCmd and for the alarm history report."
      ::= { statAgnGen 1 }

agnSDateCmd  OBJECT-TYPE
      SYNTAX  DisplayString (SIZE (0..255))
      MAX-ACCESS  read-write
      STATUS  current
      DESCRIPTION
      "This entry indicates the current date as it is known by the
       agent using its own real-time clock. The format would be as
       specified by the agnSDateFormat.
       This  parameter can be set for time synchronization between
       the NMS and the Agent."
      ::= { statAgnGen 2 }

agnSTimeCmd  OBJECT-TYPE
      SYNTAX  DisplayString (SIZE (0..255))
      MAX-ACCESS  read-write
      STATUS  current
      DESCRIPTION
      "This entry indicates the current time as it is known by the
       agent using its own real-time clock.
       This  parameter can be set for time synchronization between
       the NMS and the Agent."
      ::= { statAgnGen 3 }

agnSActiveCnfg  OBJECT-TYPE
      SYNTAX  Integer32
      MAX-ACCESS  read-only
      STATUS  current
      DESCRIPTION
      "This entry specifies the unique identifier of the  configuration,
       that is currently  active and running."
      ::= { statAgnGen 4 }
-- return 1 (db1) in phase I

agnSEditCnfg OBJECT-TYPE
      SYNTAX  Integer32
      MAX-ACCESS  read-only
      STATUS  current
      DESCRIPTION
      "This entry indicates the  unique identifier of the
       configuration that is currently loaded into the tmp working
       space  for manipulation and update operations. Value of 255
       means no config. is under editing process."
      ::= { statAgnGen 5 }
-- return 1 (db1) in phase I

agnSLastCnfgFlipTime OBJECT-TYPE
      SYNTAX  DisplayString (SIZE (0..255))
      MAX-ACCESS  read-only
      STATUS  current
      DESCRIPTION
      "This entry indicates the Date & Time of the last flip to the
       current configuration at the agent."
      ::= { statAgnGen 6 }
-- return sysUpTime in phase I

agnSLastCnfgFlipCause OBJECT-TYPE
      SYNTAX  DisplayString (SIZE (0..255))
      MAX-ACCESS  read-only
      STATUS  current
      DESCRIPTION
      "This entry describes the flip's cause."
      ::= { statAgnGen 7 }
-- In phase I return two causes:
--          Power up
--          Update Db

agnSEditBy OBJECT-TYPE
      SYNTAX  INTEGER
       {
           none            (1),
           snmp            (2),
           terCon1         (3),
           terCon2         (4),
           terInbandCon1   (5),
           terInbandCon2   (6),
           lcd             (7)
       }
      MAX-ACCESS  read-only
      STATUS  current
      DESCRIPTION
      "This entry indicates which MMI application is working on  the
       edited config.
       The editing phase starts at the first modify operation and
       ends after an update(load) operation."
      ::= { statAgnGen 8 }

agnSClkSrc  OBJECT-TYPE
      SYNTAX  INTEGER
    {
        master  (1),
        fallback(2),
        internal(3)
 }
      MAX-ACCESS  read-only
      STATUS  current
      DESCRIPTION
     "This entry indicates the source of the system clock."
      ::= { statAgnGen 9 }

agnSAlrStatus OBJECT-TYPE
      SYNTAX  INTEGER
       {
  off      (2),
  event    (3),
  minor    (4),
  major    (5),
  warning  (6),
  critical (7)
       }
      MAX-ACCESS  read-only
      STATUS  current
      DESCRIPTION
      "Indicates the alarm state in the agent level, i.e. lower
       level (card/port) alarms not included.
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
      ::= { statAgnGen 10 }

agnSAlrStatusAll OBJECT-TYPE
      SYNTAX  INTEGER
       {
  off      (2),
  event    (3),
  minor    (4),
  major    (5),
     warning  (6),
  critical (7)
       }
      MAX-ACCESS  read-only
      STATUS  current
      DESCRIPTION
      "Indicates the alarm state of the entire agent, i.e.
       including card and port alarms status.
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
      ::= { statAgnGen 11 }

agnSMaskedAlrStat OBJECT-TYPE
      SYNTAX  INTEGER
       {
  off      (2),
  event    (3),
  minor    (4),
  major    (5),
     warning  (6),
  critical (7)
       }
      MAX-ACCESS  read-only
      STATUS  current
      DESCRIPTION
      "Indicates the alarm state in the agent level,[ i.e. lower
       level (card/port) alarms not included] including Masked
       alarms.
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
      ::= { statAgnGen 12 }

agnSMaskedAlrStatAll OBJECT-TYPE
      SYNTAX  INTEGER
       {
  off      (2),
  event    (3),
  minor    (4),
  major    (5),
     warning  (6),
  critical (7)
       }
      MAX-ACCESS  read-only
      STATUS  current
      DESCRIPTION
      "Indicates the alarm state of the entire agent, i.e.
       including card and port alarms status,including
       Masked alarms.
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
      ::= { statAgnGen 13 }

agnSTstStatAll OBJECT-TYPE
      SYNTAX  INTEGER
       {
  off(2),
  on (3)
       }
      MAX-ACCESS  read-only
      STATUS  current
      DESCRIPTION
      "on(3) - when there is at least one test in progress in one
               of the agent cards,
       otherwise the value will be off(2)."
      ::= { statAgnGen 14 }

agnSAlrTable OBJECT-TYPE
      SYNTAX SEQUENCE OF AgnSAlrEntry
      MAX-ACCESS not-accessible
      STATUS current
      DESCRIPTION
      "List of agent related alarms and indications for alarms at
       system level."
      ::= { statAgnGen 15 }

agnSAlrEntry OBJECT-TYPE
      SYNTAX AgnSAlrEntry
      MAX-ACCESS not-accessible
      STATUS current
	DESCRIPTION  "An entry in table."
	INDEX { agnSAlrIdx}
      ::= { agnSAlrTable 1}

AgnSAlrEntry ::=
      SEQUENCE {
  agnSAlrIdx              Integer32,
  agnSAlrCodeDescription  DisplayString (SIZE (0..255)),
  agnSAlrCode             Integer32,
  agnSAlrSeverity         INTEGER,
  agnSAlrState            INTEGER,
  agnSAlrCounter          Integer32,
  agnSAlrMask             INTEGER,
  agnSAlrInvert           INTEGER
      }

agnSAlrIdx OBJECT-TYPE
      SYNTAX  Integer32
      MAX-ACCESS  read-only
      STATUS  current
      DESCRIPTION
      "A unique number to identify an entry in the alarm status table
       of the agent."
      ::= { agnSAlrEntry 1 }

agnSAlrCodeDescription OBJECT-TYPE
      SYNTAX  DisplayString (SIZE (0..255))
      MAX-ACCESS  read-only
      STATUS  current
      DESCRIPTION
      "This attribute is a full text description of the alarm .
       The alarm description includes the following information:
       alarm code, alarm text, alarm severity, Masked or Inverted
       flag and counter."
     ::= { agnSAlrEntry 2 }

agnSAlrCode OBJECT-TYPE
      SYNTAX  Integer32
      MAX-ACCESS  read-only
      STATUS  current
      DESCRIPTION
      "A code identifying the alarm of an entry in the alarm status
       table at system level."
      ::= { agnSAlrEntry 3 }

agnSAlrSeverity OBJECT-TYPE
      SYNTAX  INTEGER
       {
  event    (3),
  minor    (4),
  major    (5),
  warning  (6),
  critical (7)
       }
      MAX-ACCESS  read-only
      STATUS  current
      DESCRIPTION
      "The severity of the alarm."
      ::= { agnSAlrEntry 4 }

agnSAlrState  OBJECT-TYPE
      SYNTAX  INTEGER
       {
  off(2),
  on (3)
       }
      MAX-ACCESS  read-only
      STATUS  current
      DESCRIPTION
      "State of the alarm."
      ::= { agnSAlrEntry 5 }

agnSAlrCounter OBJECT-TYPE
      SYNTAX  Integer32
      MAX-ACCESS  read-only
      STATUS  current
      DESCRIPTION
      "A counter - how many times the alarm occured since last
       clear operation.
       ON and OFF Alarm will be counted separately."
      ::= { agnSAlrEntry 6 }

agnSAlrMask  OBJECT-TYPE
      SYNTAX  INTEGER
       {
  off(2),
  on (3)
       }
      MAX-ACCESS  read-only
      STATUS  current
      DESCRIPTION
      "Alarm mask : on/off."
      ::= { agnSAlrEntry 7 }

agnSAlrInvert  OBJECT-TYPE
      SYNTAX  INTEGER
       {
  off(2),
  on (3)
       }
      MAX-ACCESS  read-only
      STATUS  current
      DESCRIPTION
      "Alarm invert : on/off."
      ::= { agnSAlrEntry 8 }


agnSClearAlrCmd  OBJECT-TYPE
      SYNTAX  INTEGER
       {
  off(2),
  on (3)
       }
      MAX-ACCESS  read-write
      STATUS  current
      DESCRIPTION
      "Setting this attribute to ON, enforce a  clear operation on
       all the agent(general) events. General alarms are alarms
       which are not specific to a card or port. The clear
       operation will not be applied for masked/inverted alarms."
      ::= { statAgnGen 16 }

agnSClearAllAlrCmd OBJECT-TYPE
      SYNTAX  INTEGER
       {
  off(2),
  on (3)
       }
      MAX-ACCESS  read-write
      STATUS  current
      DESCRIPTION
      "Setting this attribute to ON, enforce a clear operation on
       all MUX alarm events at the levels of agent, slots and ports.
       The clear operation will not be applied for masked/inverted
       alarms."
      ::= { statAgnGen 17 }

agnSSanityCheckStatus OBJECT-TYPE
      SYNTAX  INTEGER
       {
  unknown (1),
  fail    (2),
  warning (3),
  ok      (4)
       }
      MAX-ACCESS  read-only
      STATUS  current
      DESCRIPTION
      "Upon completion of the Sanity check process on the TmpCnfg
       this attribute will be set to:
       FAIL(2) - when there is at least one error encountered and
                 possibly some warnings.
       WARNING(3) - when there are only warnings.
       otherwise, the value will be OK(4).
       The value will be UNKNOWN(1) if changes were made in the
       TmpCnfg following the last Sanity check."
      ::= { statAgnGen 18 }

agnSNoOfSanityCheckErr OBJECT-TYPE
      SYNTAX  Integer32
      MAX-ACCESS  read-only
      STATUS  current
      DESCRIPTION
      "This entry indicates the number of errors/warnings discovered
       by the last SanityCheck process."
      ::= { statAgnGen 19 }

agnSErrListTable OBJECT-TYPE
      SYNTAX SEQUENCE OF AgnSErrListEntry
      MAX-ACCESS not-accessible
      STATUS current
      DESCRIPTION
      "List of errors and warnings found during Sanity Check
       process."
      ::= { statAgnGen 20 }

agnSErrListEntry OBJECT-TYPE
      SYNTAX AgnSErrListEntry
      MAX-ACCESS not-accessible
      STATUS current
	DESCRIPTION  "An entry in table."
	INDEX { agnSErrIdx}
      ::= { agnSErrListTable 1}

AgnSErrListEntry ::=
      SEQUENCE {
  agnSErrIdx          Integer32,
     agnSErrDescription  DisplayString (SIZE (0..255))
               }

agnSErrIdx OBJECT-TYPE
      SYNTAX  Integer32
      MAX-ACCESS  read-only
      STATUS  current
      DESCRIPTION
      "Unique number to identify an entry in the  error list table.
       The maximum entry  value cannot exceed the value of
       'agnSNoOfSanityCheckErr'. "
    ::= { agnSErrListEntry 1}

agnSErrDescription OBJECT-TYPE
      SYNTAX  DisplayString (SIZE (0..255))
      MAX-ACCESS  read-only
      STATUS  current
      DESCRIPTION
      "This attribute is a full text description of the sanity check
       error including error code, slot and port numbers related to
       the code ."
  ::= { agnSErrListEntry 2}

agnSMaxNoOfCnfg OBJECT-TYPE
      SYNTAX  Integer32
      MAX-ACCESS  read-only
      STATUS  current
      DESCRIPTION
      "Maximum number of configurations that can be defined and
       stored in the MUX.
       If the mux has a large capacity, the maximum will be limited
       to  254."
      ::= { statAgnGen 21}
-- return 1 (db1) in phase I

agnSCnfgTable OBJECT-TYPE
      SYNTAX SEQUENCE OF AgnSCnfgEntry
      MAX-ACCESS not-accessible
      STATUS  current
      DESCRIPTION
      "This table contains an entry per configuration. It indicates
       if the configuration is valid."
      ::= { statAgnGen 22 }
--  - in phase I only one entry

agnSCnfgEntry OBJECT-TYPE
      SYNTAX AgnSCnfgEntry
      MAX-ACCESS not-accessible
      STATUS current
	DESCRIPTION  "An entry in table."
	INDEX { agnSEntryIdx}
      ::= {agnSCnfgTable  1}

AgnSCnfgEntry ::=
      SEQUENCE  {
 agnSEntryIdx         Integer32,
 agnSEntryIsValid     INTEGER
      }

agnSEntryIdx OBJECT-TYPE
      SYNTAX  Integer32
      MAX-ACCESS  read-only
      STATUS  current
      DESCRIPTION
      "Unique number to identify an entry in the configuration table."
    ::= { agnSCnfgEntry 1}

agnSEntryIsValid OBJECT-TYPE
      SYNTAX  INTEGER
       {
  no  (2),
  yes (3)
       }
      MAX-ACCESS  read-only
      STATUS  current
      DESCRIPTION
      "This attribute indicates whether the specific configuration
       is valid in the MUX . Value of NO indicates: no such
       configuration  in the MUX. "
    ::= { agnSCnfgEntry 2}

--
-- Wan agent configuration information
--
agnCSanityCheckCmd OBJECT-TYPE
      SYNTAX  INTEGER
       {
       off(2),
       on (3)
       }
      MAX-ACCESS  read-write
      STATUS  current
      DESCRIPTION
      "Setting this attribute to on(3) will initiate the process
       of Sanity check on the TmpCnfg. Upon completion the value
       will automatically be changed to off(2)."
      ::= { cnfgAgnGen 1 }

agnCSaveCnfgIdxCmd OBJECT-TYPE
      SYNTAX  Integer32   (1..100)
      MAX-ACCESS  read-write
      STATUS  current
      DESCRIPTION
      "This attribute specifies the Id of the target RealCnfg to
       which the TmpCnfg should be transferred. Upon set command the
       MUX will initiate the Sanity-Check  process first. If
       successful, the actual transfer will be performed. If warnings
       are detected, the user will have to perform the command again
       to confirm the operation. Setting this object a second time
       to the same value without performing any change in the database,
       will cause the result: agnSSanityCheckStatus = unknown"
      ::= { cnfgAgnGen 2 }
-- In phase I only the value 1 (Cnfg1) is valid.

agnCLoadCnfgIdxCmd OBJECT-TYPE
      SYNTAX  Integer32  (1..100)
      MAX-ACCESS  read-write
      STATUS  current
      DESCRIPTION
      "This attribute specifies the Id of the source Cnfg to be
       loaded into the TmpCnfg. Upon set operation the actual
       transfer will be initiated.
       The operation is valid only on Valid configurations
       (agnSEntryIsValid)"
      ::= { cnfgAgnGen 3 }
-- In phase I only the value 1 (Cnfg1) is valid.


agnCClkSrcTable  OBJECT-TYPE
      SYNTAX SEQUENCE OF AgnCClkSrcEntry
      MAX-ACCESS not-accessible
      STATUS  current
      DESCRIPTION
      "All the entries of this table are identical (have the same
       value) for all the configurations (1..100) except the
       TmpCnfg.
       The write operation into the Table Objects is valid only
       for the TmpCnfg entry."
       ::= { cnfgAgnGen 4}

agnCClkSrcEntry OBJECT-TYPE
      SYNTAX AgnCClkSrcEntry
      MAX-ACCESS not-accessible
      STATUS current
	DESCRIPTION  "An entry in table."
	INDEX {agnCClkCnfgIdx, agnCClkSrcIdx}
      ::= { agnCClkSrcTable 1}

AgnCClkSrcEntry ::=
      SEQUENCE {
   agnCClkCnfgIdx      Integer32,
   agnCClkSrcIdx       Integer32,
   agnCClkSrcMode      INTEGER,
   agnCClkSrcSlt       INTEGER,
   agnCClkSrcPrt       Integer32
      }

agnCClkCnfgIdx OBJECT-TYPE
      SYNTAX Integer32 (1..255)
      MAX-ACCESS read-only
      STATUS current
      DESCRIPTION
      "This attribute indicates the Idx of the Cnfg(1..100) being
       accessed and Idx 255 relates to the TmpCnfg."
      ::= { agnCClkSrcEntry 1}
-- In phase I only the values 1 (Cnfg1) and 255 (temp) are valid.

agnCClkSrcIdx OBJECT-TYPE
      SYNTAX  Integer32 (1..2)
      MAX-ACCESS  read-only
      STATUS  current
      DESCRIPTION
      "An index to the table. There are only two entries to this
       table.
       Index 1 points to the Master clock parameters and Index 2
       points to the Fallback clock parameters"
      ::= { agnCClkSrcEntry 2}

agnCClkSrcMode OBJECT-TYPE
      SYNTAX  INTEGER
       {
           internal   (1),
           rxClk      (2),
		   adaptive   (3)
       }
      MAX-ACCESS  read-write
      STATUS  current
      DESCRIPTION
      "The source of the nodal timing."
      ::= { agnCClkSrcEntry 3}

agnCClkSrcSlt OBJECT-TYPE
      SYNTAX  INTEGER
        {
       notApplicable   (1),
       io1   (5),
       io2   (6),
       io3   (7),
       io4   (8),
       io5   (9),
       io6  (10),
       io7  (11),
       io8  (12),
       io9  (13),
       io10 (14),
       io11 (15),
       io12 (16)
     }
      MAX-ACCESS  read-write
      STATUS  current
      DESCRIPTION
      "This entry is valid only when we are working in rxClk mode.
       For an invalid entry, the return value will be '7fff'h."
      ::= { agnCClkSrcEntry 4}

agnCClkSrcPrt OBJECT-TYPE
      SYNTAX  Integer32
      MAX-ACCESS  read-write
      STATUS  current
      DESCRIPTION
      "This entry is valid only when we are working in rxClk or 
       adaptive mode.
       For an invalid entry, the return value will be '7fff'h.
       - For rxClk mode, the values can be:
              exPrt1    (1) ,
              exPrt2    (2) ,
              exPrt3    (3) ,
              exPrt4    (4) ,
              exPrt5    (5) ,
              exPrt6    (6) ,
              exPrt7    (7) ,
              exPrt8    (8) ,
              exPrt9    (9) ,
              exPrt10  (10) ,
              exPrt11  (11) ,
              exPrt12  (12) ,
              notApplicable   (100),
	 	 	  inPrt1  (101) ,
	 	 	  inPrt2  (102) ,
	 	 	  inPrt3  (103) ,
	 	 	  inPrt4  (104)
       - For adaptive mode, the value will be the ifIndex of the 
         selected IP Bundle."
      ::= { agnCClkSrcEntry 5}

agnCDeleteCnfgIdxCmd OBJECT-TYPE
  SYNTAX  Integer32 (1..100)
  MAX-ACCESS  read-write
  STATUS  current
  DESCRIPTION
  "Setting this attribute will delete the requested DB
   from the NVRAM ."
  ::= { cnfgAgnGen 5 }

agnCDefaultCnfgIdxCmd OBJECT-TYPE
  SYNTAX  Integer32 (1..100)
  MAX-ACCESS  read-write
  STATUS  current
  DESCRIPTION
  "Setting this attribute will define the desired working
   configuration when no conditions of the Flip DB Table are
   fulfilled and no Net GO command was issued. This command
   will be accepted only if the Configuration number exists
   (agnSEntryIsValid=yes)."
  ::= { cnfgAgnGen 6 }

agnCnfgDataTable OBJECT-TYPE
      SYNTAX SEQUENCE OF AgnCnfgDataEntry
      MAX-ACCESS not-accessible
      STATUS  current
      DESCRIPTION
      "This table contains data about the agent configurations.
       The table will support only data about valid configurations
       of the agent."
       ::= { cnfgAgnGen 7}

agnCnfgDataEntry OBJECT-TYPE
      SYNTAX AgnCnfgDataEntry
      MAX-ACCESS not-accessible
      STATUS current
	DESCRIPTION  "An entry in table."
	INDEX {agnCnfgIdx}
      ::= { agnCnfgDataTable 1}

AgnCnfgDataEntry ::=
      SEQUENCE {
   agnCnfgIdx      Integer32,
   agnCnfgDesc     DisplayString,
   agnCnfgUpdDate  DisplayString,
   agnCnfgUpdTime  DisplayString,
   agnCnfgUpdMnger IpAddress
      }

agnCnfgIdx OBJECT-TYPE
      SYNTAX Integer32 (1..255)
      MAX-ACCESS read-only
      STATUS current
      DESCRIPTION
      "This object indicates the Idx of the agent' Cnfg the following 
       objects refer.
       255=Temporary Cnfg (Set is done only to this configuration)."
      ::= { agnCnfgDataEntry 1}
-- Only the values 1..10, 255 are valid.

agnCnfgDesc OBJECT-TYPE
      SYNTAX DisplayString (SIZE (0..30))
      MAX-ACCESS read-write
      STATUS current
      DESCRIPTION
      "This object is a description of the Configuration, entered
       by user, to enhance Cnfg recognition."
      ::= { agnCnfgDataEntry 2}

agnCnfgUpdDate  OBJECT-TYPE
      SYNTAX  DisplayString (SIZE (0..255))
      MAX-ACCESS  read-only
      STATUS  current
      DESCRIPTION
      "This object indicates the date when last update of this
       configuration was performed, as it is known by the
       agent using its own real-time clock. The format would be as
       specified by the agnSDateFormat.
       When update is performed, the agent should save the date."
      ::= { agnCnfgDataEntry 3 }

agnCnfgUpdTime  OBJECT-TYPE
      SYNTAX  DisplayString (SIZE (0..255))
      MAX-ACCESS  read-only
      STATUS  current
      DESCRIPTION
      "This object indicates the time when last update of this
       configuration was performed, as it is known by the
       agent using its own real-time clock.
       When update is performed, the agent should save the time."
      ::= { agnCnfgDataEntry 4 }

agnCnfgUpdMnger  OBJECT-TYPE
      SYNTAX  IpAddress
      MAX-ACCESS  read-only
      STATUS  current
      DESCRIPTION
      "This object indicates the IP Address of the Manager who
       performed the last update of this configuration.
       When update is performed, the agent should save the
       IP Address of the Manager who commanded the update.
       That will enable a manager to know if he performed the last
       update, or another manager did."
      ::= { agnCnfgDataEntry 5 }


agnCnfgAlarm   OBJECT IDENTIFIER ::= { cnfgAgnGen 8}

agnCnfgAlrFilterWindow OBJECT-TYPE
      SYNTAX Integer32 (0..255)
      MAX-ACCESS read-write
      STATUS current
      DESCRIPTION
      "Window of time, in seconds.
       During this Window, the alarms filter is performed.
       Same Window for all agent alarms that need filtering.
       Upon end of the Window, the state of the alarm is updated
       and a new Window starts.
       If no alarm needs filtering, this object's value will not be
       used."
      ::= { agnCnfgAlarm 1}

agnCnfgAlrTable OBJECT-TYPE
      SYNTAX SEQUENCE OF AgnCnfgAlrEntry
      MAX-ACCESS not-accessible
      STATUS  current
      DESCRIPTION
      "This table enables the user to set attributes to each alarm.
       Setting  for a non-existing entry agnCnfgAlrMask,
       agnCnfgAlrInvert or agnCnfgAlrFilter to 'yes'(or yesAndSave
       for Mask) will add this new entry to the table.
       Setting  for an existing entry agnCnfgAlrMask/
       agnCnfgAlrInvert/agnCnfgAlrFilter (one or more) to 'no'
       (noAndSave for Mask)  so that ALL  these objects' values are
       'no' , will delete this entry from the table.
       For agnCnfgAlrMask, only if [(last saved value=noAndSave)
       AND (new value is 'no' or 'noAndSave')] the object's value
       is considered 'no' for deleting the entry.
       
       For some products (like MP, MPH, Vmux2100) the Active Alarms are always
       part of the table and cannot be removed even if their Mask/Invert/Filter
       are No."
       ::= { agnCnfgAlarm 2}

agnCnfgAlrEntry OBJECT-TYPE
      SYNTAX AgnCnfgAlrEntry
      MAX-ACCESS not-accessible
      STATUS current
	DESCRIPTION  "An entry in table."
	INDEX {agnCnfgAlrCode, agnCnfgAlrSlot, agnCnfgAlrPort}
      ::= { agnCnfgAlrTable 1}

AgnCnfgAlrEntry ::=
      SEQUENCE {
   agnCnfgAlrCode        Integer32,
   agnCnfgAlrSlot        INTEGER,
   agnCnfgAlrPort        Integer32,
   agnCnfgAlrMask        INTEGER,
   agnCnfgAlrInvert      INTEGER,
   agnCnfgAlrFilter      INTEGER,
   agnCnfgAlrFilterSet   Integer32,
   agnCnfgAlrFilterReset Integer32 
	}

agnCnfgAlrCode OBJECT-TYPE
      SYNTAX Integer32
      MAX-ACCESS read-only
      STATUS current
      DESCRIPTION
      "The alarm code. The following attributes refer this code."
      ::= { agnCnfgAlrEntry 1 }

agnCnfgAlrSlot OBJECT-TYPE
      SYNTAX INTEGER
      {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
       all           (200),
       notApplicable (255)
   }
      MAX-ACCESS read-only
      STATUS current
      DESCRIPTION
      "The alarm slot. The following attributes apply for the alarm
       code and slot selected.
       all = the attributes apply to all slots.
       notApplicable = the selected alarm is for system level.
       For the Vmux2100 Main Board clA  (3) is used."
      ::= { agnCnfgAlrEntry 2 }

agnCnfgAlrPort OBJECT-TYPE
      SYNTAX Integer32
      MAX-ACCESS read-only
      STATUS current
      DESCRIPTION
      "The alarm port. The following attributes apply for the alarm
       code,slot and port selected.
       200 = all = the attributes apply to all ports of the selected slot.
             When selected Slot is 'all', only 'all' or	'notApplicable' are valid  
             Port selections.
       notApplicable = the selected alarm is for system or card
                       level.
					   =255 for MP
					   =100 for DXC
	   - For MP:
	     - valid cards' ports are: exPrt1(1)..exPrt16(16)
								   inPrt1(101)..inPrt48 (148)
		 - IP Bundles 
	   - For DXC, the port index will include the Slot, as for all DXC 
	     tables: [(IO Slot+10)&n]  ; n=odd  for external ports
		                             n=even for internal ports."
      ::= { agnCnfgAlrEntry 3 }

agnCnfgAlrMask OBJECT-TYPE
      SYNTAX INTEGER
      {
       no         (1),
       noAndSave  (2),
       yes        (3),
       yesAndSave (4)
   }
      MAX-ACCESS read-write
      STATUS current
      DESCRIPTION
      "An attribute defining the desired Mask state of an alarm .
       no - unmask (this command is not saved in agent's common
            database)
       noAndSave -  unmask ; this command is saved in agent's
             common database
       yes - mask  (this command is not saved in agent's
             common database)
       yesAndSave - mask  ; this command is saved in
             agent's common database.
       Commands that are not saved, will be lost upon power-up or
       selected card removal.      "
      ::= { agnCnfgAlrEntry 4 }

agnCnfgAlrInvert OBJECT-TYPE
      SYNTAX INTEGER
      {
       no            (2),
       yes           (3)
   }
      MAX-ACCESS read-write
      STATUS current
      DESCRIPTION
      "An attribute defining the desired Invert state of an alarm .
       no  - not inverted.
       yes - inverted. For MP, it is not applicable for alarms
             that are currently OFF."
      ::= { agnCnfgAlrEntry 5 }

agnCnfgAlrFilter OBJECT-TYPE
      SYNTAX INTEGER
      {
       no            (2),
       yes           (3)
   }
      MAX-ACCESS read-write
      STATUS current
      DESCRIPTION
      "An attribute defining if Filter is desired for the alarm .
       no  - no  filter.
       yes - filter activate.

       This filter is activated within a window of time defined by
       agnCnfgAlrFilterWindow.
       Its purpose is to avoid frequent changes of an alarm between
       ON/OFF states."
      ::= { agnCnfgAlrEntry 6 }

agnCnfgAlrFilterSet OBJECT-TYPE
      SYNTAX Integer32
      MAX-ACCESS read-write
      STATUS current
      DESCRIPTION
      "This is a top threshold causing the alarm that passes it,
       to be declared Set (ON) at the end of the respective
       window of time.
       - For alarms defined by default as state alarms (minor,major)
         this value will be in [%].
       - For alarms defined by default as events, this value will be
         an integer meaning how many times this event should appear
         at least, during the window in order to be considered ON.
       The maximum value will be 255.
       This value should be greater than the one of
       agnCnfgAlrFilterReset.
       Agents that do not support Alarms Filter, will return 0."
      ::= { agnCnfgAlrEntry 7 }

agnCnfgAlrFilterReset OBJECT-TYPE
      SYNTAX Integer32
      MAX-ACCESS read-write
      STATUS current
      DESCRIPTION
      "This is a bottom threshold causing the alarm that does not
       pass it, to be declared Reset (ON) at the end of the
       respective window of time.
       - For alarms defined by default as state alarms (minor,major)
         this value will be in [%].
       - For alarms defined by default as events, this value will be
         an integer meaning how many times this event should appear
         at most, during the window, in order to be considered OFF.
       This value should be less than the one of
       agnCnfgAlrFilterSet.
       Agents that do not support Alarms Filter, will return 0."
      ::= { agnCnfgAlrEntry 8 }


agnCnfgAlrReportTable OBJECT-TYPE
      SYNTAX SEQUENCE OF AgnCnfgAlrReportEntry
      MAX-ACCESS not-accessible
      STATUS  current
      DESCRIPTION
      "This table enables the user to configure the desired Alarm
       Reports according to alarms severity."
       ::= { agnCnfgAlarm 3}

agnCnfgAlrReportEntry OBJECT-TYPE
      SYNTAX AgnCnfgAlrReportEntry
      MAX-ACCESS not-accessible
      STATUS current
	DESCRIPTION  "An entry in table."
	INDEX {agnCnfgAlrReportType}
      ::= { agnCnfgAlrReportTable 1}

AgnCnfgAlrReportEntry ::=
      SEQUENCE {
   agnCnfgAlrReportType        INTEGER,
   agnCnfgAlrStartReportOn     INTEGER,
   agnCnfgAlrStartReportOff    INTEGER
      }

agnCnfgAlrReportType OBJECT-TYPE
      SYNTAX INTEGER
         {
          trap        (1),
          buffer      (2),
          relay       (3),	 --Relay 1 = R1
          alrLedOn    (4),	 --Minor LED
          alrLedBlink (5),	 --Major LED
		  relay2      (6)    --Relay 2 = R2
         }
      MAX-ACCESS read-only
      STATUS current
      DESCRIPTION
      "The alarm report type.
       trap - traps will be sent only for alarms having the
              selected On/Off severity or higher.
       buffer - only alarms having the selected On/Off severity and
                higher, will be reported to the buffer.
       relay -  relay contact will be activated only for alarms
                having the selected On severity or higher.
				For products having 2 relays, this is the R1 Relay.

       alrLedOn/alrLedBlink - user should select a higher severity
                (ReportOn) for alrLedBlink than for alrLedOn
                (Blinking Led means a more severe alarm than steady
                 ON Led).
       alrLedOn - MTCL-1 Alarm Led will be ON only when
                agnSAlrStatusAll equals the selected severity or
                higher, but lower severity than that selected for
                'alrLedBlink'.
				For products having 2 LEDs, this is the Minor LED.
       alrLedBlink - MTCL-1 Alarm Led will Blink only when
                agnSAlrStatusAll equals the selected severity or
                higher.
				For products having 2 LEDs, this is the Major LED.
       relay2 -  relay 2 contact will be activated only for alarms
                having the selected On severity or higher.
				This is the R2 Relay."
      ::= { agnCnfgAlrReportEntry 1 }

agnCnfgAlrStartReportOn OBJECT-TYPE
      SYNTAX INTEGER
         {
          noReport (2),
          event    (3),
          minor    (4),
          major    (5),
          warning  (6),
          critical (7)
         }  
      MAX-ACCESS read-write
      STATUS current
      DESCRIPTION
      "This object specifies the severity from which alarms will 
       be reported. Alarms having this severity or higher, will be
       reported.
       This object specifies the report severity only for alarms
       that turn to ON state.
       noReport - no Report at all (for any severity)."
      ::= { agnCnfgAlrReportEntry 2 }

agnCnfgAlrStartReportOff OBJECT-TYPE
      SYNTAX INTEGER
         {
        notApplicable (1),
        noReport (2),
        event    (3),
        minor    (4),
        major    (5),
        warning  (6),
        critical (7)
         }  
      MAX-ACCESS read-write
      STATUS current
      DESCRIPTION
      "This object specifies the severity from which alarms will 
       be reported. Alarms having this severity or higher, will be
       reported.
       This object specifies the report severity only for alarms
       that turn to OFF state. 
       notApplicable - for 'relay','alrLedOn','alrLedBlink', 'relay2' report 
                       types, in MP.
       noReport - no Report at all (for any severity)."
      ::= { agnCnfgAlrReportEntry 3 }

agnCOffsetCmd OBJECT-TYPE
      SYNTAX INTEGER
      {
       notApplicable (1),
       normal        (2),
       u1            (3)
      }
      MAX-ACCESS read-write
      STATUS current
      DESCRIPTION
      "An object defining special user request.
       notApplicable - is RO value for products that do not support this object.
       normal -  nothing special
       u1 - user 1 - for all Voice cards, the DISPLAYED Tx and Rx Levels
            will have the following Offsets:
            - 2 Wires port: Tx Level: the base value (for 0dBm) = 0
                            Rx Level: the base value (for 0dBm) = -2
            - 4 Wires port: Tx Level: the base value (for 0dBm) = -16
                            Rx Level: the base value (for 0dBm) = 7    
            The MIB and application DB will use the values without Offset."
      ::= { cnfgAgnGen 9 }

--System T1/E1 Ring Table
--
--This table contains all ML ports that participate in a T1/E1 Ring,
--and their ML port pair. 
--The table indexes are Cnfg and the Primary card & port

agnCT1E1RingTable OBJECT-TYPE
      SYNTAX SEQUENCE OF AgnCT1E1RingEntry
      MAX-ACCESS not-accessible
      STATUS current
      DESCRIPTION
      "Configuration of all T1/E1 Ring ML cards and ports.
       The write operation into the table objects is valid only
       for the TmpCnfg.
       A Slot/Port that does not participate in the T1/E1 Ring, 
       will not exist in this table.
       A ML port that exists in this table, cannot exist at the same
       time in the IO Redundancy table (sysCRdnTable)."
      ::= { cnfgAgnGen 10 }

agnCT1E1RingEntry OBJECT-TYPE
      SYNTAX AgnCT1E1RingEntry
      MAX-ACCESS not-accessible
      STATUS current
      DESCRIPTION
	  "An Entry in table agnCT1E1RingTable"
      INDEX { agnCT1E1RingCnfgIdx, agnCT1E1RingPrimeSlot, agnCT1E1RingPrimePort}
      ::= { agnCT1E1RingTable 1}

AgnCT1E1RingEntry ::=
      SEQUENCE {
     agnCT1E1RingCnfgIdx   Integer32,
     agnCT1E1RingPrimeSlot INTEGER,
     agnCT1E1RingPrimePort Integer32,
     agnCT1E1RingSecSlot   INTEGER,
     agnCT1E1RingSecPort   Integer32,
	 agnCT1E1RingRecTime   Integer32,
     agnCT1E1RingRowStatus RowStatus
      }

agnCT1E1RingCnfgIdx OBJECT-TYPE
      SYNTAX  Integer32
      MAX-ACCESS  read-only
      STATUS  current
      DESCRIPTION
      "This object indicates the Idx of the Cnfg(1..255) being 
       accessed ; Idx of 255 relates to the TmpCnfg."
      ::= { agnCT1E1RingEntry 1 }

agnCT1E1RingPrimeSlot OBJECT-TYPE
      SYNTAX  INTEGER 
       {
       io1   (5),
       io2   (6),
       io3   (7),
       io4   (8),
       io5   (9),
       io6  (10),
       io7  (11),
       io8  (12),
       io9  (13),
       io10 (14),
       io11 (15),
       io12 (16),
       notApplicable (255)
       }
      MAX-ACCESS  read-only
      STATUS  current
      DESCRIPTION
      "The slot number of the Primary card of the Ring Pair."      
	  ::= { agnCT1E1RingEntry 2 }

agnCT1E1RingPrimePort OBJECT-TYPE
      SYNTAX  Integer32 
      MAX-ACCESS  read-only
      STATUS  current
      DESCRIPTION
      "The port number in the Primary Card.
	   For external ports, the value will be as that of the port in the
	       card. Example: external-3 -> 3
                          external-4 -> 4
	   For internal ports, the value will be 100 + the port in the
	       card. Example: internal-1 -> 101
                          internal-4 -> 104  "      
      ::= { agnCT1E1RingEntry 3 }

agnCT1E1RingSecSlot OBJECT-TYPE
      SYNTAX  INTEGER 
       {
       io1   (5),
       io2   (6),
       io3   (7),
       io4   (8),
       io5   (9),
       io6  (10),
       io7  (11),
       io8  (12),
       io9  (13),
       io10 (14),
       io11 (15),
       io12 (16),
       notApplicable (255)
       }
      MAX-ACCESS  read-create
      STATUS  current
      DESCRIPTION
      "The slot number of the Secondary card of the Ring Pair."      
	  ::= { agnCT1E1RingEntry 4 }

agnCT1E1RingSecPort OBJECT-TYPE
      SYNTAX  Integer32 
      MAX-ACCESS  read-create
      STATUS  current
      DESCRIPTION
      "The port number in the Secondary Card.
	   For external ports, the value will be as that of the port in the
	       card. Example: external-3 -> 3
                          external-4 -> 4
	   For internal ports, the value will be 100 + the port in the
	       card. Example: internal-1 -> 101
                          internal-4 -> 104  "      
      ::= { agnCT1E1RingEntry 5 }

agnCT1E1RingRecTime OBJECT-TYPE
      SYNTAX  Integer32 (1..99)
      MAX-ACCESS  read-create
      STATUS  current
      DESCRIPTION
      "T1/E1 Ring Recovery Time (sec)."
      ::= { agnCT1E1RingEntry 6 }

agnCT1E1RingRowStatus  OBJECT-TYPE
      SYNTAX  RowStatus
      MAX-ACCESS   read-create
      STATUS   current
      DESCRIPTION
      "This parameter allows NMS to create/delete entries of this table.
       The only possible supported RowStatus vaules are
       active (1) and destroy (6)."
      ::= { agnCT1E1RingEntry 7 }


--
-- Compressed information.
--
-- Specially for RadView management station
--
agnCmprTable  OBJECT-TYPE
      SYNTAX SEQUENCE OF AgnCmprEntry
      MAX-ACCESS not-accessible
      STATUS current
	DESCRIPTION  "A table."
	::=  { cmprAgnGen 1 }

agnCmprEntry OBJECT-TYPE
      SYNTAX AgnCmprEntry
      MAX-ACCESS not-accessible
      STATUS current
	DESCRIPTION  "An entry in table."
	INDEX { agnCmprTypIdx, agnCmprCnfgIdx ,agnCmprVersion}
      ::= {agnCmprTable  1}

AgnCmprEntry ::=
      SEQUENCE {
     agnCmprTypIdx      Integer32,
     agnCmprCnfgIdx     Integer32,
     agnCmprVersion     Integer32,
     agnCmprObj         OCTET STRING
      }

agnCmprTypIdx OBJECT-TYPE
      SYNTAX  Integer32
      MAX-ACCESS  read-only
      STATUS  current
      DESCRIPTION
      "This attribute indicates the Type of the Compressed being
       referred."
      ::= { agnCmprEntry 1}

agnCmprCnfgIdx OBJECT-TYPE
      SYNTAX  Integer32
      MAX-ACCESS  read-only
      STATUS  current
      DESCRIPTION
      "This attribute indicates the configuration to which the
       Compressed information is  related."
      ::= { agnCmprEntry 2}

agnCmprVersion OBJECT-TYPE
      SYNTAX  Integer32
      MAX-ACCESS  read-only
      STATUS  current
      DESCRIPTION
      "This attribute indicates the version of the internal format
       of the Compressed data"
      ::= { agnCmprEntry 3}

agnCmprObj OBJECT-TYPE
      SYNTAX  OCTET STRING
      MAX-ACCESS  read-write
      STATUS  current
      DESCRIPTION
      "This attribute is the compressed information itself."
      ::= { agnCmprEntry 4}


-- Compressed Dlci table in the Agent level
-- The only way of reading this table is by the command 'GET NEXT'

agnDlciCmprTable  OBJECT-TYPE
      SYNTAX SEQUENCE OF AgnDlciCmprEntry
      MAX-ACCESS not-accessible
      STATUS current
	DESCRIPTION  "A table."
	::=  {cmprAgnGen 2}

agnDlciCmprEntry OBJECT-TYPE
      SYNTAX AgnDlciCmprEntry
      MAX-ACCESS not-accessible
      STATUS current
	DESCRIPTION  "An entry in table."
	INDEX {agnDlciCmprCnfgIdx,agnDlciCmprVersion,agnDlciCmprDlciIdx}
      ::= {agnDlciCmprTable  1}

AgnDlciCmprEntry ::=
      SEQUENCE {
     agnDlciCmprCnfgIdx       Integer32,
     agnDlciCmprVersion       Integer32,
     agnDlciCmprDlciIdx       Integer32,
     agnDlciCmprObj          OCTET STRING
      }

agnDlciCmprCnfgIdx OBJECT-TYPE
      SYNTAX  Integer32
      MAX-ACCESS  read-only
      STATUS  current
      DESCRIPTION
      "This attribute indicates the configuration to which the
       Compressed information is  related."
      ::= { agnDlciCmprEntry 1}

agnDlciCmprVersion OBJECT-TYPE
      SYNTAX  Integer32
      MAX-ACCESS  read-only
      STATUS  current
      DESCRIPTION
      "This attribute indicates the version of the internal format
       of the Compressed data"
      ::= { agnDlciCmprEntry 2}

agnDlciCmprDlciIdx  OBJECT-TYPE
      SYNTAX  Integer32
      MAX-ACCESS  read-only
      STATUS  current
      DESCRIPTION
      "This attribute indicates a unique identifier of  the Dlci,
       the compressed information relates to.
       The values are between 16 - 991."
      ::= { agnDlciCmprEntry 3}

agnDlciCmprObj OBJECT-TYPE
      SYNTAX  OCTET STRING
      MAX-ACCESS  read-write
      STATUS  current
      DESCRIPTION
      "This attribute is the compressed information itself."
      ::= { agnDlciCmprEntry 4}

-- Compressed Status Alarm table at the Agent level
-- The only way of reading this table is by the command 'GET NEXT'

agnAlarmsCmprTable  OBJECT-TYPE
      SYNTAX SEQUENCE OF AgnAlarmsCmprEntry
      MAX-ACCESS not-accessible
      STATUS current
	DESCRIPTION  "A table."
	::=  {cmprAgnGen 3}

agnAlarmsCmprEntry OBJECT-TYPE
      SYNTAX AgnAlarmsCmprEntry
      MAX-ACCESS not-accessible
      STATUS current
	DESCRIPTION  "An entry in table."
	INDEX {agnAlarmsCmprVersion,agnAlarmsCmprAlarmIdx}
      ::= {agnAlarmsCmprTable  1}

AgnAlarmsCmprEntry ::=
      SEQUENCE {
     agnAlarmsCmprVersion      Integer32,
     agnAlarmsCmprAlarmIdx     Integer32,
     agnAlarmsCmprObj          OCTET STRING
      }

agnAlarmsCmprVersion OBJECT-TYPE
      SYNTAX  Integer32
      MAX-ACCESS  read-only
      STATUS  current
      DESCRIPTION
      "This attribute indicates the version of the internal
       format of the Compressed data"
      ::= { agnAlarmsCmprEntry 1}

agnAlarmsCmprAlarmIdx  OBJECT-TYPE
      SYNTAX  Integer32
      MAX-ACCESS  read-only
      STATUS  current
      DESCRIPTION
      "A unique number to identify an entry in the alarm status table
       of the agent."
      ::= { agnAlarmsCmprEntry 2}

agnAlarmsCmprObj OBJECT-TYPE
      SYNTAX  OCTET STRING
      MAX-ACCESS  read-only
      STATUS  current
      DESCRIPTION
      "This attribute is the compressed information itself."
      ::= { agnAlarmsCmprEntry 3}

-- Compressed History Alarms buffer
-- The only way of reading this table is by the command 'GET NEXT'

agnAlrBufCmprTable  OBJECT-TYPE
      SYNTAX SEQUENCE OF AgnAlrBufCmprEntry
      MAX-ACCESS not-accessible
      STATUS current
	DESCRIPTION  "A table."
	::=  {cmprAgnGen 4}

agnAlrBufCmprEntry OBJECT-TYPE
      SYNTAX AgnAlrBufCmprEntry
      MAX-ACCESS not-accessible
      STATUS current
	DESCRIPTION  "An entry in table."
	INDEX {agnAlrBufCmprVersion,agnAlrBufCmprAlarmIdx}
      ::= {agnAlrBufCmprTable  1}

AgnAlrBufCmprEntry ::=
      SEQUENCE {
     agnAlrBufCmprVersion      Integer32,
     agnAlrBufCmprAlarmIdx     Integer32,
     agnAlrBufCmprObj          OCTET STRING
      }

agnAlrBufCmprVersion OBJECT-TYPE
      SYNTAX  Integer32
      MAX-ACCESS  read-only
      STATUS  current
      DESCRIPTION
      "This attribute indicates the version of the internal format of
       the Compressed data"
      ::= { agnAlrBufCmprEntry 1}

agnAlrBufCmprAlarmIdx  OBJECT-TYPE
      SYNTAX  Integer32
      MAX-ACCESS  read-only
      STATUS  current
      DESCRIPTION
      "A unique number to identify an entry in the history alarms
       buffer of the agent."
      ::= { agnAlrBufCmprEntry 2}

agnAlrBufCmprObj OBJECT-TYPE
      SYNTAX  OCTET STRING
      MAX-ACCESS  read-only
      STATUS  current
      DESCRIPTION
      "This attribute is the compressed information itself."
      ::= { agnAlrBufCmprEntry 3}


-- Compressed Sanity Errors buffer
-- The only way of reading this table is by the command 'GET NEXT'


agnSCmprErrListTable OBJECT-TYPE
      SYNTAX SEQUENCE OF AgnSCmprErrListEntry
      MAX-ACCESS not-accessible
      STATUS current
	DESCRIPTION  "A table."
	::=  { cmprAgnGen 5 }

agnSCmprErrListEntry OBJECT-TYPE
      SYNTAX AgnSCmprErrListEntry
      MAX-ACCESS not-accessible
      STATUS current
	DESCRIPTION  "An entry in table."
	INDEX {agnSCmprErrVersion,agnSCmprErrIdx}
      ::= { agnSCmprErrListTable 1}

AgnSCmprErrListEntry ::=
      SEQUENCE {
     agnSCmprErrVersion      Integer32,
     agnSCmprErrIdx          Integer32,
     agnSCmprErrObj          OCTET STRING
      }

agnSCmprErrVersion OBJECT-TYPE
      SYNTAX  Integer32
      MAX-ACCESS  read-only
      STATUS  current
      DESCRIPTION
      "The version of the compressed data "
       ::= { agnSCmprErrListEntry 1}

agnSCmprErrIdx OBJECT-TYPE
      SYNTAX  Integer32
      MAX-ACCESS  read-only
      STATUS  current
      DESCRIPTION
      "Unique number to identify an entry in the errors list table.
       The maximum entry  value  cannot exceed the value of
       'agnSNoOfSanityCheckErr'. "
       ::= { agnSCmprErrListEntry 2}

agnSCmprErrObj OBJECT-TYPE
      SYNTAX  OCTET STRING
      MAX-ACCESS  read-only
      STATUS  current
      DESCRIPTION
      "This attribute is a full text description of the error,
       including: error code, slot and port numbers related to the
       code ."
     ::= { agnSCmprErrListEntry 3}


-- New TS Assignment compressed table, per port 01/09/98
-- The only way of reading this table is by the command 'GET NEXT'

agnTsCmprTable  OBJECT-TYPE
      SYNTAX SEQUENCE OF AgnTsCmprEntry
      MAX-ACCESS not-accessible
      STATUS current
	DESCRIPTION  "A table."
	::=  { cmprAgnGen 6 }

agnTsCmprEntry OBJECT-TYPE
      SYNTAX AgnTsCmprEntry
      MAX-ACCESS not-accessible
      STATUS current
	DESCRIPTION  "An entry in table."
	INDEX { agnTsCmprVerIdx,  agnTsCmprCnfgIdx , agnTsCmprSlotIdx,
              agnTsCmprPortIdx, agnTsCmprPduIdx }
      ::= {agnTsCmprTable  1}

AgnTsCmprEntry ::=
      SEQUENCE {
     agnTsCmprVerIdx      Integer32,
     agnTsCmprCnfgIdx     Integer32,
     agnTsCmprSlotIdx     Integer32,
     agnTsCmprPortIdx     Integer32,
     agnTsCmprPduIdx      Integer32,
     agnTsCmprData        OCTET STRING
      }

agnTsCmprVerIdx OBJECT-TYPE
      SYNTAX  Integer32
      MAX-ACCESS  read-only
      STATUS  current
      DESCRIPTION
      "This object indicates the version of the internal format
       of the Compressed data."
      ::= { agnTsCmprEntry 1}

agnTsCmprCnfgIdx OBJECT-TYPE
      SYNTAX  Integer32
      MAX-ACCESS  read-only
      STATUS  current
      DESCRIPTION
      "This object indicates the configuration to which the
       Compressed information is related.
       255=temporary configuration.
       Set can be performed only to the temporary configuration."
      ::= { agnTsCmprEntry 2}

agnTsCmprSlotIdx OBJECT-TYPE
      SYNTAX  Integer32
      MAX-ACCESS  read-only
      STATUS  current
      DESCRIPTION
      "This object indicates the Slot to which the
       Compressed information is  related.
       For MP-2100: IO-1..IO-12 = (5).. (16)
       For DXC-30 : IO-1..IO-15 = (5).. (19)."
      ::= { agnTsCmprEntry 3}

agnTsCmprPortIdx OBJECT-TYPE
      SYNTAX  Integer32
      MAX-ACCESS  read-only
      STATUS  current
      DESCRIPTION
      "This object indicates the Port within the Slot, to which the
       Compressed information is  related.
       For Port Index see each product's spec."
      ::= { agnTsCmprEntry 4}

agnTsCmprPduIdx OBJECT-TYPE
      SYNTAX  Integer32
      MAX-ACCESS  read-only
      STATUS  current
      DESCRIPTION
      "This object indicates the PDU index within the same port.
       That provides for the case when one PDU is not sufficient for all TS
       Assignment data of the same port."
      ::= { agnTsCmprEntry 5}

agnTsCmprData OBJECT-TYPE
      SYNTAX  OCTET STRING
      MAX-ACCESS  read-write
      STATUS  current
      DESCRIPTION
      "This object is the compressed information itself. It provides
       information about all TSs of a port."
      ::= { agnTsCmprEntry 6}

-- Extended Compress Genearl Table with 7 indexes -  10/02/99
-- Used for: V5.1 Variant, 

agnXCmprTable  OBJECT-TYPE
      SYNTAX SEQUENCE OF AgnXCmprEntry
      MAX-ACCESS not-accessible
      STATUS current
	DESCRIPTION  "A table."
	::=  { cmprAgnGen 7 }

agnXCmprEntry OBJECT-TYPE
      SYNTAX AgnXCmprEntry
      MAX-ACCESS not-accessible
      STATUS current
	DESCRIPTION  "An entry in table."
	INDEX {agnXCmprTypIdx, agnXCmprVersion, agnXCmprIdx3,agnXCmprIdx4,
             agnXCmprIdx5, agnXCmprIdx6, agnXCmprIdx7}
      ::= {agnXCmprTable  1}

AgnXCmprEntry ::=
      SEQUENCE {
     agnXCmprTypIdx       Integer32,
     agnXCmprVersion      Integer32,
     agnXCmprIdx3         Integer32,
     agnXCmprIdx4         Integer32,
     agnXCmprIdx5         Integer32,
     agnXCmprIdx6         Integer32,
     agnXCmprIdx7         Integer32,
     agnXCmprObj          OCTET STRING
      }

agnXCmprTypIdx OBJECT-TYPE
      SYNTAX  Integer32
      MAX-ACCESS  read-only
      STATUS  current
      DESCRIPTION
      "This attribute indicates the Type of the Compressed being
       referred. 
       One of the types is V5.1 Variant data."
      ::= { agnXCmprEntry 1}

agnXCmprVersion OBJECT-TYPE
      SYNTAX  Integer32
      MAX-ACCESS  read-only
      STATUS  current
      DESCRIPTION
      "This attribute indicates the version of the internal format of
       the Compressed data."
      ::= { agnXCmprEntry 2}

agnXCmprIdx3 OBJECT-TYPE
      SYNTAX  Integer32
      MAX-ACCESS  read-only
      STATUS  current
      DESCRIPTION
      "3rd index - can be used for any purpose according to the 
       agnXCmprTypIdx.
       Example: for V5.1 Variant, this attribute indicates the configuration
       to which the Compressed information is  related.
       255=temporary configuration.
       Set can be performed only to the temporary configuration."
      ::= { agnXCmprEntry 3}

agnXCmprIdx4  OBJECT-TYPE
      SYNTAX  Integer32
      MAX-ACCESS  read-only
      STATUS  current
      DESCRIPTION
      "4th index - can be used for any purpose according to the 
       agnXCmprTypIdx.
       Example: for V5.1 Variant,this attribute indicates a unique number of 
       the slot position where the card is inserted.
	   Valid values: psA(1),psB(2),clA(3),clB(4),io1(5)..io12(16); notApplicable=255."
      ::= { agnXCmprEntry 4}

agnXCmprIdx5   OBJECT-TYPE
      SYNTAX  Integer32
      MAX-ACCESS  read-only
      STATUS  current
      DESCRIPTION
      "5th index - can be used for any purpose according to the 
       agnXCmprTypIdx.
       Example: for V5.1 Variant,this attribute indicates a unique identifier 
       of  the port	the compressed information relates to.
       Valid values: exPrt1    (1) .. exPrt12  (12) ,
                     inPrt1  (101) .. inPrt48 (148)."
      ::= { agnXCmprEntry 5}

agnXCmprIdx6  OBJECT-TYPE
      SYNTAX  Integer32
      MAX-ACCESS  read-only
      STATUS  current
      DESCRIPTION
      "6th index - can be used for any purpose according to the 
       agnXCmprTypIdx.
       Example: for V5.1 Variant,this attribute indicates the Variant index. 
       Valid values are: 0..127, 255 (= temp cnfg).Set can be performed only 
       to the temporary configuration."
      ::= { agnXCmprEntry 6}

agnXCmprIdx7  OBJECT-TYPE
      SYNTAX  Integer32
      MAX-ACCESS  read-only
      STATUS  current
      DESCRIPTION
      "7th index - can be used for any purpose according to the 
       agnXCmprTypIdx.
       Example: for V5.1 Variant,this attribute is not needed. Therefore, its 
       value will be always 255=notApplicable."
      ::= { agnXCmprEntry 7}

agnXCmprObj OBJECT-TYPE
      SYNTAX  OCTET STRING
      MAX-ACCESS  read-write
      STATUS  current
      DESCRIPTION
      "This attribute is the compressed information itself."
      ::= { agnXCmprEntry 8}

--
-- Link Mapping Table for internal use
--
agnLinkMapTable OBJECT-TYPE
      SYNTAX SEQUENCE OF AgnLinkMapEntry
      MAX-ACCESS not-accessible
      STATUS current
	DESCRIPTION  "A table."
	::=  { mapWanGen 1}

agnLinkMapEntry OBJECT-TYPE
      SYNTAX AgnLinkMapEntry
      MAX-ACCESS not-accessible
      STATUS current
	DESCRIPTION  "An entry in table."
	INDEX {mapLinkId}
      ::= {agnLinkMapTable 1}

AgnLinkMapEntry ::=
      SEQUENCE {
      mapLinkId               Integer32,
      mapLinkSltIdx           INTEGER,
      mapLinkPrtIdx           INTEGER,
      mapLinkStatus           INTEGER
      }

mapLinkId     OBJECT-TYPE
      SYNTAX  Integer32
      MAX-ACCESS  read-only
      STATUS  current
      DESCRIPTION
      "A unique identifier of the link"
::=  {agnLinkMapEntry 1}

mapLinkSltIdx    OBJECT-TYPE
      SYNTAX  INTEGER
        {
          noConnect   (2),
       clA   (3),
       io1   (5),
       io2   (6),
       io3   (7),
       io4   (8),
       io5   (9),
       io6  (10),
       io7  (11),
       io8  (12),
       io9  (13),
       io10 (14),
       io11 (15),
       io12 (16),
    notApplicable (255)
     }
      MAX-ACCESS  read-write
      STATUS  current
      DESCRIPTION
      "This attribute indicates a unique  slot  position where
       the card is inserted.
       In the ?004 Unit the entries clA(3), io6(10)..io12(16) are
       not valid."
::=  {agnLinkMapEntry 2}

mapLinkPrtIdx  OBJECT-TYPE
      SYNTAX  INTEGER
      {
         exPrt1    (1) ,
         exPrt2    (2) ,
         exPrt3    (3) ,
         exPrt4    (4) ,
         exPrt5    (5) ,
         exPrt6    (6) ,
         exPrt7    (7) ,
         exPrt8    (8) ,
         exPrt9    (9) ,
         exPrt10  (10) ,
         exPrt11  (11) ,
         exPrt12  (12) ,
         noConnect  (100) ,
         inPrt1  (101) ,
         inPrt2  (102) ,
         inPrt3  (103) ,
         inPrt4  (104) ,
         inPrt5  (105) ,
         inPrt6  (106) ,
         inPrt7  (107) ,
         inPrt8  (108) ,
         inPrt9  (109) ,
         inPrt10 (110) ,
         inPrt11 (111) ,
         inPrt12 (112)
      }
      MAX-ACCESS  read-write
      STATUS  current
      DESCRIPTION
      "This attribute indicates a unique  port number. "
::=  {agnLinkMapEntry 3}

mapLinkStatus   OBJECT-TYPE
      SYNTAX  INTEGER
 {
 unknown(1),
 down(2),
 up(3)
 }
      MAX-ACCESS  read-only
      STATUS  current
      DESCRIPTION
      "This attribute indicates the status of the link between the
       two muxes"
::=  {agnLinkMapEntry 4}


--
-- diverseIfWanGen - diverse NON-DS1 interfaces of WAN products
--



--sonetInterface  OBJECT IDENTIFIER  ::=  {diverseIfWanGen 2}     (see radsonet.txt)
--ds3Interface    OBJECT IDENTIFIER  ::=  {diverseIfWanGen 3}	  (see radds3.txt)
--ds1Interface    OBJECT IDENTIFIER  ::=  {diverseIfWanGen 4}	  (see radds1.txt)
--hdlcMibObjects  OBJECT IDENTIFIER  ::=  {diverseIfWanGen 5}     (see radhdlc.txt)
--ip2If           OBJECT IDENTIFIER ::= { diverseIfWanGen 7 }	  (see ipmux.txt)


--
-- Wan alarm buffer (history) information
--
alrBufTable  OBJECT-TYPE
      SYNTAX SEQUENCE OF AlrBufEntry
      MAX-ACCESS not-accessible
      STATUS current
	DESCRIPTION  "A table."
	::=  { alrBuffGen 1 }

alrBufEntry OBJECT-TYPE
      SYNTAX AlrBufEntry
      MAX-ACCESS not-accessible
      STATUS current
	DESCRIPTION  "An entry in table."
	INDEX { alrBufIdx }
      ::= { alrBufTable 1}

AlrBufEntry ::=
      SEQUENCE {
  alrBufIdx          Integer32,
     alrBufDescription  DisplayString (SIZE (0..255))
      }

alrBufIdx OBJECT-TYPE
      SYNTAX  Integer32
      MAX-ACCESS  read-only
      STATUS  current
      DESCRIPTION
      "This attribute indicates a  unique number to identify this
       entry"
    ::= { alrBufEntry 1}

alrBufDescription  OBJECT-TYPE
      SYNTAX  DisplayString (SIZE (0..255))
      MAX-ACCESS  read-only
      STATUS  current
      DESCRIPTION
      "This entry is a unique text description of the alarm in the
       buffer.
       The alarm description includes the following information:
       alarm code, slot id, card type, channel id ,
       alarm text, alarm status, masked flag and event counter"
       ::= { alrBufEntry 2}


--
-- Wan Flip Data-Base parameters
--
--         agnCAgendaTable :
--

agnCAgendaTable OBJECT-TYPE
      SYNTAX SEQUENCE OF AgnCAgendaEntry
      MAX-ACCESS not-accessible
      STATUS  current
      DESCRIPTION
      "This table devides the week days into categories needed for
       DB flip consideration."
      ::= {agnFlipDb 1}

agnCAgendaEntry OBJECT-TYPE
      SYNTAX AgnCAgendaEntry
      MAX-ACCESS not-accessible
      STATUS current
	DESCRIPTION  "An entry in table."
	INDEX {agnCAgendaCnfgIdx, agnCAgendaDayIdx}
      ::= {agnCAgendaTable 1}

AgnCAgendaEntry ::=
      SEQUENCE {
           agnCAgendaCnfgIdx    INTEGER,
           agnCAgendaDayIdx           INTEGER,
           agnCAgendaDayCategory      INTEGER
               }

agnCAgendaCnfgIdx OBJECT-TYPE
      SYNTAX  INTEGER
              {
                active    (1),
                temporary  (255)
              }
      MAX-ACCESS  read-only
      STATUS  current
      DESCRIPTION
      "Active or Temporary Agenda Table.
       Both configurations can be read but only the Temporary can
       be written to."
      ::= {agnCAgendaEntry 1}

agnCAgendaDayIdx OBJECT-TYPE
      SYNTAX  INTEGER
              {
                sunday    (1),
                monday    (2),
                tuesday   (3),
                wednesday (4),
                thursday  (5),
                friday    (6),
                saturday  (7)
              }
      MAX-ACCESS  read-only
      STATUS  current
      DESCRIPTION
      "Day of week"
      ::= {agnCAgendaEntry 2}

agnCAgendaDayCategory OBJECT-TYPE
      SYNTAX  INTEGER
              {
                fullWorkday    (1),
                partialWorkday (2),
                weekend        (3)
              }
      MAX-ACCESS  read-write
      STATUS  current
      DESCRIPTION
      "The Category of the Day "
      ::= {agnCAgendaEntry 3}


--          agnCFlipNetEventsTable :
--

agnCFlipNetEventsTable OBJECT-TYPE
      SYNTAX SEQUENCE OF AgnCFlipNetEventsEntry
      MAX-ACCESS not-accessible
      STATUS  current
      DESCRIPTION
      "This table holds the Net Events the MUX should trace"
      ::= {agnFlipDb 2}

agnCFlipNetEventsEntry OBJECT-TYPE
      SYNTAX AgnCFlipNetEventsEntry
      MAX-ACCESS not-accessible
      STATUS current
	DESCRIPTION  "An entry in table."
	INDEX {agnCFlipNetEventsCnfgIdx, agnCFlipNetEventIdx}
      ::= {agnCFlipNetEventsTable 1}

AgnCFlipNetEventsEntry ::=
      SEQUENCE {
    agnCFlipNetEventsCnfgIdx   INTEGER,
                agnCFlipNetEventIdx        Integer32,
                agnCFlipNetEventActive     INTEGER,
                agnCFlipNetEventType       INTEGER,
                agnCFlipNetEventNo         Integer32,
                agnCFlipNetEventSlot       INTEGER,
                agnCFlipNetEventPort       Integer32,
                agnCFlipNetEventISD        Integer32,
                agnCFlipNetEventOSD        Integer32,
                agnCFlipNetEventDayType    INTEGER,
                agnCFlipNetEventStartTime  DisplayString (SIZE (5)),
                agnCFlipNetEventEndTime    DisplayString (SIZE (5))
               }

agnCFlipNetEventsCnfgIdx OBJECT-TYPE
      SYNTAX  INTEGER
              {
                active    (1),
                temporary  (255)
              }
      MAX-ACCESS  read-only
      STATUS  current
      DESCRIPTION
      "Active or Temporary Net Events Table.
       Both configurations can be read but only the Temporary can
       be written to."
      ::= {agnCFlipNetEventsEntry 1}

agnCFlipNetEventIdx OBJECT-TYPE
      SYNTAX  Integer32  (1..10)
      MAX-ACCESS  read-only
      STATUS  current
      DESCRIPTION
      "Entry within the table"
      ::= {agnCFlipNetEventsEntry 2}

agnCFlipNetEventActive     OBJECT-TYPE
      SYNTAX  INTEGER
              {
                no  (2),
                yes (3)
              }
      MAX-ACCESS  read-write
      STATUS  current
      DESCRIPTION
      "Indicates if the entry is valid.
       In order to Add/Modify parameters of an entry, this object
       should be set to Yes.
       In order to delete an entry, this object should be Set to No."
      ::= {agnCFlipNetEventsEntry 3}


agnCFlipNetEventType OBJECT-TYPE
      SYNTAX  INTEGER
              {
                time       (1),
                linkDown   (2),
                congestion (3)   -- MP3000 Only
              }
      MAX-ACCESS  read-write
      STATUS  current
      DESCRIPTION
      "The Net Event type "
      ::= {agnCFlipNetEventsEntry 4}

agnCFlipNetEventNo OBJECT-TYPE
      SYNTAX  Integer32  (1..512)
      MAX-ACCESS  read-write
      STATUS  current
      DESCRIPTION
      "The Net Event No. (Bit Index)"
      ::= {agnCFlipNetEventsEntry 5}

agnCFlipNetEventSlot OBJECT-TYPE
      SYNTAX  INTEGER
              {
                notApplicable   (1),
                io1   (5),
                io2   (6),
                io3   (7),
                io4   (8),
                io5   (9),
                io6  (10),
                io7  (11),
                io8  (12),
                io9  (13),
                io10 (14),
                io11 (15),
                io12 (16)
              }
      MAX-ACCESS  read-write
      STATUS  current
      DESCRIPTION
      "The slot to which the net event relates .
       Not applicable for time event"
      ::= {agnCFlipNetEventsEntry 6}

agnCFlipNetEventPort OBJECT-TYPE
      SYNTAX  Integer32
      MAX-ACCESS  read-write
      STATUS  current
      DESCRIPTION
      "The port within the relevant slot.
	   Valid values:
	   - extPrt1(1)..exPrt16(16) 
	   - notApplicable(100)
	   - inPrt1(101)..inPrt48(148)"
      ::= {agnCFlipNetEventsEntry 7}

agnCFlipNetEventISD OBJECT-TYPE
      SYNTAX  Integer32  (1..999)
      MAX-ACCESS  read-write
      STATUS  current
      DESCRIPTION
      "The time in seconds since the Net Event was reported as ON
       until it is considered as ON.
       Not relevant for time events."
      ::= {agnCFlipNetEventsEntry 8}

agnCFlipNetEventOSD OBJECT-TYPE
      SYNTAX  Integer32  (1..999)
      MAX-ACCESS  read-write
      STATUS  current
      DESCRIPTION
      "The time in seconds since the net event was reported as OFF
       until it is considered as OFF.
       Not relevant for time events."
      ::= {agnCFlipNetEventsEntry 9}

agnCFlipNetEventDayType OBJECT-TYPE
      SYNTAX  INTEGER
              {
                notApplicable  (1),
                fullWorkday    (2),
                partialWorkday (3),
    weekend        (4)
              }
      MAX-ACCESS  read-write
      STATUS  current
      DESCRIPTION
      "The time event relates to all days defined in this category in
       the agnCAgendaTable.
       Applicable only for time event"
      ::= {agnCFlipNetEventsEntry 10}

agnCFlipNetEventStartTime    OBJECT-TYPE
      SYNTAX    DisplayString (SIZE (5))
      MAX-ACCESS  read-write
      STATUS  current
      DESCRIPTION
      "The time event will be activated at this time.
       The format is hh:mm."
      ::= {agnCFlipNetEventsEntry 11}

agnCFlipNetEventEndTime     OBJECT-TYPE
      SYNTAX    DisplayString (SIZE (5))
      MAX-ACCESS  read-write
      STATUS  current
      DESCRIPTION
      "The time event will be deactivated at this time.
       The format is hh:mm."
      ::= {agnCFlipNetEventsEntry 12}


--         agnCFlipTable :
--

agnCFlipTable OBJECT-TYPE
     SYNTAX SEQUENCE OF AgnCFlipEntry
     MAX-ACCESS not-accessible
     STATUS  current
     DESCRIPTION
     "The DB Flip Decisions Table"
     ::= {agnFlipDb 3}

agnCFlipEntry OBJECT-TYPE
     SYNTAX AgnCFlipEntry
     MAX-ACCESS not-accessible
     STATUS current
	DESCRIPTION  "An entry in table."
	INDEX {agnCFlipCnfgIdx, agnCFlipIdx}
     ::= {agnCFlipTable 1}

AgnCFlipEntry ::=
     SEQUENCE {
               agnCFlipCnfgIdx    INTEGER,
               agnCFlipIdx         Integer32,
               agnCFlipActive      INTEGER,
               agnCFlipLogicalExp  DisplayString (SIZE (1..20)),
               agnCFlipDbNo        Integer32,
               agnCFlipDiscardDe   INTEGER
              }

agnCFlipCnfgIdx OBJECT-TYPE
      SYNTAX  INTEGER
              {
                active     (1),
                temporary  (255)
              }
      MAX-ACCESS  read-only
      STATUS  current
      DESCRIPTION
      "Active or Temporary Flip Decisions Table.
       Both configurations can be read but only the Temporary can
       be written to."
      ::= {agnCFlipEntry 1}



agnCFlipIdx OBJECT-TYPE
     SYNTAX  Integer32  (1..10)
     MAX-ACCESS  read-only
     STATUS  current
     DESCRIPTION
     "Entry number within the table"
     ::= {agnCFlipEntry 2}

agnCFlipActive     OBJECT-TYPE
     SYNTAX  INTEGER
             {
               no  (2),
               yes (3)
             }
     MAX-ACCESS  read-write
     STATUS  current
     DESCRIPTION
     "Indicates if the entry is valid.
      In order to Add/Modify parameters of an entry this object
      should be Set to Yes.
      In order to delete an entry, this object should be Set to No."
     ::= {agnCFlipEntry 3}

agnCFlipLogicalExp    OBJECT-TYPE
     SYNTAX    DisplayString (SIZE (1..20))
     MAX-ACCESS  read-write
     STATUS  current
     DESCRIPTION
     "A logical expression composed of events numbers (which were
      configured in the 'AgnCFlipNetEvantsTable') and logical operators
      ('|', '&', '!', '(', ')') between them.
      e.g - (1 & !2) | (121 & 230)"
     ::= {agnCFlipEntry 4}

agnCFlipDbNo OBJECT-TYPE
     SYNTAX  Integer32  (1..10)
     MAX-ACCESS  read-write
     STATUS  current
     DESCRIPTION
     "The ID of the required DB "
     ::= {agnCFlipEntry 5}

agnCFlipDiscardDe     OBJECT-TYPE
     SYNTAX  INTEGER
             {
               notApplicable (1),
               no            (2),
               yes           (3)
             }
     MAX-ACCESS  read-write
     STATUS  current
     DESCRIPTION
     "Indicates whether the Mux should start discarding
      all DE. (MP3000 Only)."
     ::= {agnCFlipEntry 6}

--  Commands concerning the Flip DB

agnFlipDbControls    OBJECT IDENTIFIER ::= {agnFlipDb 4}


agnCFlipDbSanityCheckCmd OBJECT-TYPE
     SYNTAX  INTEGER
             {
               off(2),
               on (3)
             }
     MAX-ACCESS  read-write
     STATUS  current
     DESCRIPTION
     "Setting this attribute to on(3) will initiate the process
      of Sanity check on the Temp Flip Db and automatically be
      changed to off(2)."
     ::= { agnFlipDbControls 1 }

agnCSaveFlipDbCmd OBJECT-TYPE
     SYNTAX  INTEGER
             {
               off(2),
               on (3)
             }
     MAX-ACCESS  read-write
     STATUS  current
     DESCRIPTION
     "Setting this attribute to on(3) will initiate the process
      of Sanity check on the Temp Flip Db and if it is OK, it will
      save the Flip Db in the NVRAM, activating the new  Flip DB .
      If check detects errors, the save will not be performed.
      Afterwards, the object's value will change automatically to off(2)."
     ::= { agnFlipDbControls 2 }

agnCSaveNetCnfgIdxCmd OBJECT-TYPE
     SYNTAX  Integer32   (1..10)
     MAX-ACCESS  read-write
     STATUS  current
     DESCRIPTION
     "This attribute specifies the Id of the target NVRAM Cnfg to
      which the TmpCnfg should be transferred. Upon set command the
      MUX will initiate the Sanity-Check  process first. If
      successful, the actual transfer will be performed. If warnings
      are detected, the user will have to perform the command again
      to confirm the operation. Setting this object a second time
      to the same value without performing any change in the database,
      will cause the result: agnSSanityCheckStatus = unknown.
      This attribute doesn't cause actual Flip."
     ::= { agnFlipDbControls 3 }

agnCSaveNetFlipDbCmd OBJECT-TYPE
     SYNTAX  INTEGER
             {
               off(2),
               on (3)
             }
     MAX-ACCESS  read-write
     STATUS  current
     DESCRIPTION
     "Setting this attribute to on(3) will save the Temp Flip DB
      Into the NVRAM without actual flip."
     ::= { agnFlipDbControls 4 }

agnCNetGoCmd OBJECT-TYPE
     SYNTAX  INTEGER
             {
               off(2),
               on (3)
             }
     MAX-ACCESS  read-write
     STATUS  current
     DESCRIPTION
     "Setting this attribute to On will broadcast a 'GO' command
      to the network.  When a Mux receives a 'GO' command it issues
      a delay for 'agnCNetDelay' seconds and then activates
      the DB which was pre-defined by one of the commands :
      'agnCSaveNetCnfgIdxCmd' or 'agnCSaveNetFlipDbCmd'."
     ::= { agnFlipDbControls 5 }

agnCNetDelay OBJECT-TYPE
     SYNTAX  Integer32 (1..999)
     MAX-ACCESS  read-write
     STATUS  current
     DESCRIPTION
     "This attribute determines the period of time in seconds that
      takes for a message to be transferred over all the network.
      After a 'GO' command the MUX issues a delay of
      'agnCNetDelay' before activating the appropriate DB.
      The delay will be applied only after performing
      agnCSaveFlipDbCmd."
     ::= { agnFlipDbControls 6 }

agnCNetEventsBcast OBJECT-TYPE
     SYNTAX  INTEGER
             {
               disabled(2),
               enabled (3)
             }
     MAX-ACCESS  read-write
     STATUS  current
     DESCRIPTION
     "This object determines if the Net Events will be Broadcasted to
      other Muxes of the Net or not.
      disabled - Net Events will NOT be Broadcasted
      enabled  - Net Events will be Broadcasted.
   Default=disabled.
      The value will be applied only after performing
      agnCSaveFlipDbCmd."
     ::= { agnFlipDbControls 7 }

agnCNetEventsBcastInterval OBJECT-TYPE
     SYNTAX  Integer32 (10..60)
     MAX-ACCESS  read-write
     STATUS  current
     DESCRIPTION
     "When agnCNetEventsBcast is enabled, this object determines
      the interval of time in seconds, between two consecutive
      Net Events transferred over the network.
   Default=40 sec.
      The interval will be applied only after performing
      agnCSaveFlipDbCmd."
     ::= { agnFlipDbControls 8 }

--
-- agnSa = agent Stand-Alone (not HUB) specific objects
--
agnSaSwchStatus OBJECT-TYPE
     SYNTAX  Integer32
     MAX-ACCESS  read-only
     STATUS  current
     DESCRIPTION
  "This object indicates the status of the switches on the
   stand-alone unit.
   Each switch is represented by a bit. The status is a sum of
   2**n, according to the bits:
   bit 0   NMS (LSB)
   bit 1   Terminal    '1' = forces the DCE to be terminal with
         Rate=9600bps, Data bits=8,
         Stop bits=1
   bit 2   Xray
   bit 3   SW-Load      '1' = when SW is loaded
   bit 4   DBS
   Default of all bits=0
   When the status of these switches is unknown, the value of
   this object is 255."
     ::= { agnSa 1 }

--Decoding Table: Code vs. Description

agnListDecodingTable  OBJECT-TYPE
      SYNTAX SEQUENCE OF AgnListDecodingEntry
      MAX-ACCESS not-accessible
      STATUS  current
   DESCRIPTION
      "A decoding table . For each type of list, a description is
       given for each existing code."
      ::= { agnListDecoding 1 }

agnListDecodingEntry OBJECT-TYPE
      SYNTAX AgnListDecodingEntry
      MAX-ACCESS not-accessible
      STATUS current
	DESCRIPTION  "An entry in table."
	INDEX { agnListDecodingType, agnListDecodingCode }
      ::= { agnListDecodingTable 1}

AgnListDecodingEntry ::=
      SEQUENCE {
     agnListDecodingType        INTEGER,
     agnListDecodingCode  Integer32,
     agnListDecodingDescription DisplayString (SIZE (0..255)),
     agnListDecodingDefState    INTEGER,
     agnListDecodingSeverity    INTEGER,
     agnListDecodingAcmRelaySlt INTEGER,
     agnListDecodingAcmRelayPrt INTEGER
      }

agnListDecodingType OBJECT-TYPE
      SYNTAX  INTEGER
       {
       alr      (1),
       sanity   (2)
       }
      MAX-ACCESS  read-only
      STATUS  current
      DESCRIPTION
      "The type of list the decoding data refers to.
       alr - Alarms list
       sanity - Sanity Check Error list. "
      ::= { agnListDecodingEntry 1}

agnListDecodingCode OBJECT-TYPE
      SYNTAX  Integer32
      MAX-ACCESS  read-only
      STATUS  current
      DESCRIPTION
      "The specific code for which decoding is needed. "
      ::= { agnListDecodingEntry 2}

agnListDecodingDescription OBJECT-TYPE
      SYNTAX  DisplayString (SIZE (0..255))
      MAX-ACCESS  read-only
      STATUS  current
      DESCRIPTION
      "The description fitting the specific code and type of list
       required. "
      ::= { agnListDecodingEntry 3}

agnListDecodingDefState OBJECT-TYPE
      SYNTAX  INTEGER
       {
  notApplicable (1),
  event    (3),
  minor    (4),
  major    (5),
  warning  (6),
  critical (7)
       }
      MAX-ACCESS  read-only
      STATUS  current
      DESCRIPTION
      "This object is applicable only for agnListDecodingType=alr.
       It reports the default state/severity of each alarm.
       User can change the  severity of the alarms defined by
       this default via the agnListDecodingSeverity object."
      ::= { agnListDecodingEntry 4}

agnListDecodingSeverity OBJECT-TYPE
      SYNTAX  INTEGER
       {
  notApplicable (1),
  event    (3),
  minor    (4),
  major    (5),
  warning  (6),
  critical (7)
       }
      MAX-ACCESS  read-write
      STATUS  current
      DESCRIPTION
      "This object is applicable only for agnListDecodingType=alr.
       It enables the user to select a severity for each alarm.
    The severity is set per alarm code (same for all slots/ports
    using this code).
    event - can be set only for an alarm that is defined by
            default as 'event'.
       User can change the  severity of the alarms defined by
       default as minor or major.
       The severity of an event may be set to another severity,
       but the change will actually happen only if the event
       threshold is active and passed the Set/ON condition.
       An event alarm that passed the threshold and changed its
       severity, will return automatically to event severity when
       meeting its Reset/OFF condition."
      ::= { agnListDecodingEntry 5}

agnListDecodingAcmRelaySlt OBJECT-TYPE
      SYNTAX  INTEGER
     { none  (1),
       io1   (5),
       io2   (6),
       io3   (7),
       io4   (8),
       io5   (9),
       io6  (10),
       io7  (11),
       io8  (12),
       io9  (13),
       io10 (14),
       io11 (15),
       io12 (16),
	   notApplicable(255)
	    }
      MAX-ACCESS  read-write
      STATUS  current
      DESCRIPTION
      "This object indicates the ACM slot, desired for outbound relay
       (report) for the selected alarm.
       In the ?004 Unit the entries io6(10)..io12(16) are not valid.
	   none - when agnListDecodingType=alr AND the selected
                       alarm should not be reported by an ACM card.
       notApplicable - when agnListDecodingType=sanity OR when
             [agnListDecodingType=alr and there is no ACM card installed in the Mux]."
      ::= { agnListDecodingEntry 6}

agnListDecodingAcmRelayPrt OBJECT-TYPE
      SYNTAX  INTEGER
       {
      exPrt1    (1) ,
      exPrt2    (2) ,
      exPrt3    (3) ,
      exPrt4    (4) ,
      notApplicable(255)
	    }
      MAX-ACCESS  read-write
      STATUS  current
      DESCRIPTION
      "This object indicates the ACM port within the slot, desired for outbound relay
       (report) for the selected alarm.
       notApplicable - when agnListDecodingType=sanity OR when
                       agnListDecodingAcmRelaySlt=notApplicable."
      ::= { agnListDecodingEntry 7}


-- Dlci Table from system point of view
agnDlciTable  OBJECT-TYPE
     SYNTAX SEQUENCE OF AgnDlciEntry
     MAX-ACCESS not-accessible
     STATUS  current
     DESCRIPTION
      "The write operation into the Table Objects is valid only
       to the TmpCnfg entry."
     ::= { agnSystemDlci 1}

agnDlciEntry OBJECT-TYPE
      SYNTAX AgnDlciEntry
      MAX-ACCESS not-accessible
      STATUS current
	DESCRIPTION  "An entry in table."
	INDEX {agnDlciCnfgIdx, agnDlciLSltIdx, agnDlciLPrtIdx, agnDlciHIdx,
         agnDlciHSltIdx, agnDlciHPrtIdx, agnDlciLIdx }
      ::= { agnDlciTable 1}

AgnDlciEntry ::=
      SEQUENCE {
 	agnDlciCnfgIdx 	 Integer32,
 	agnDlciLSltIdx 	 INTEGER,
    agnDlciLPrtIdx	 Integer32,
    agnDlciLIdx		 Integer32,
	agnDlciHSltIdx	 INTEGER,
    agnDlciHPrtIdx	 Integer32,
    agnDlciHIdx		 Integer32,
	agnDlciTxBc	     INTEGER,
    agnDlciTxBe      INTEGER,
    agnDlciRxBc      INTEGER,
    agnDlciRxBe      INTEGER,
	agnDlciPriority  Integer32,
	agnDlciStatus    INTEGER,
	agnDlciSpoofing  INTEGER,
	agnDlciFunnelEnable INTEGER,
	agnDlciRoutingProtocol INTEGER,
	agnDlciRowStatus RowStatus
      }

agnDlciCnfgIdx OBJECT-TYPE
      SYNTAX  Integer32 (1..255)
      MAX-ACCESS  read-only
      STATUS  current
      DESCRIPTION
      "This attribute indicates the Idx of the Cnfg (1..100) being
       accessed.
       Idx 255 relates to the TmpCnfg. "
      ::= { agnDlciEntry 1}
-- In phase I only the values 1 (Cnfg1) and 255 (temp) are valid.

agnDlciLSltIdx OBJECT-TYPE
      SYNTAX  INTEGER
     { cl(3),
       io1   (5),
       io2   (6),
       io3   (7),
       io4   (8),
       io5   (9),
       io6  (10),
       io7  (11),
       io8  (12),
       io9  (13),
       io10 (14),
       io11 (15),
       io12 (16),
	   vs  (254),
	   notApplicable(255)
	    }
      MAX-ACCESS  read-only
      STATUS  current
      DESCRIPTION
      "This attribute indicates a unique  slot  position where
       the card is inserted.
	   vs=Voice Switching
       In the ?004 Unit the entries io6(10)..io16) are not valid.
       For ISDN BRI ports of MX300/30 units:
           io1(5) = isdn1(5) and io2(6) = isdn2(6)
       LSlotIdx is defined according one of the following possiblities:
 1. LSlotIdx is < HSlotIdx.
 2. LSlotIdx is = HSlotIdx and LPrtIdx is < HPrtIdx.
 3. LSlotIdx is = HSlotIdx and LPrtIdx is = HPrtIdx but LIdx is < HIdx."
      ::= { agnDlciEntry 2}

agnDlciLPrtIdx OBJECT-TYPE
      SYNTAX  Integer32
      MAX-ACCESS  read-only
      STATUS  current
      DESCRIPTION
      "This attribute indicates a unique external or internal port number,
       including linkSelector or encapsulator.
	   100=noConnect  (for voice switching)
        LPrtIdx is defined according one of the following possiblities:
	1. LSlotIdx is < HSlotIdx.
	2. LSlotIdx is = HSlotIdx and LPrtIdx is < HPrtIdx.
	3. LSlotIdx is = HSlotIdx and LPrtIdx is = HPrtIdx but LIdx is < HIdx."
   ::= { agnDlciEntry 3}

agnDlciLIdx OBJECT-TYPE
      SYNTAX  Integer32 (0..991)
      MAX-ACCESS  read-only
      STATUS  current
      DESCRIPTION
      "This attribute indicates a unique index for each possible
       used dlci(16..991).
       0=notApplicable (for voice switching)
       LIdx is defined according one of the following possiblities:
 1. LSlotIdx is < HSlotIdx.
 2. LSlotIdx is = HSlotIdx and LPrtIdx is < HPrtIdx.
 3. LSlotIdx is = HSlotIdx and LPrtIdx is = HPrtIdx but LIdx is < HIdx."
      ::= { agnDlciEntry 4}

agnDlciHSltIdx OBJECT-TYPE
      SYNTAX  INTEGER
 {   cl    (3),
       io1   (5),
       io2   (6),
       io3   (7),
       io4   (8),
       io5   (9),
       io6  (10),
       io7  (11),
       io8  (12),
       io9  (13),
       io10 (14),
       io11 (15),
       io12 (16),
       notApplicable(255)
       }
      MAX-ACCESS  read-only
      STATUS  current
      DESCRIPTION
      "This attribute indicates a unique slot position In the Mux
       (Agent) where the dlci is routed to.
       For ISDN BRI ports of MX300/30 units:
           io1(5) = isdn1(5) and io2(6) = isdn2(6)
       In the ?004 Unit the entries io6(10)..io16) are not valid"
      ::= { agnDlciEntry 5}

agnDlciHPrtIdx OBJECT-TYPE
      SYNTAX  Integer32
      MAX-ACCESS  read-only
      STATUS  current
      DESCRIPTION
      "This attribute indicates a unique port id which the dlci is
       routed to."
      ::= { agnDlciEntry 6}

agnDlciHIdx OBJECT-TYPE
      SYNTAX  Integer32    (1..991)
      MAX-ACCESS  read-only
      STATUS  current
      DESCRIPTION
      "This attribute indicates a unique internal connection dlci
       number which the src dlci is routed to."
      ::= { agnDlciEntry 7}

agnDlciTxBc OBJECT-TYPE
      SYNTAX  INTEGER
        {
         full           (1),
         zero           (2),
         txBc5100bps    (3),
         txBc6400bps    (4),
         txBc8300bps    (5),
         txBc9600bps    (6),
        txBc14400bps    (7),
        txBc19200bps    (8),
        txBc28800bps    (9),
        txBc32000bps   (10),
        txBc38400bps   (11),
        txBc48000bps   (12),
        txBc56000bps   (13),
        txBc57600bps   (14),
          txBc64Kbps   (15),
         txBc128Kbps   (16),
         txBc192Kbps   (17),
         txBc256Kbps   (18),
         txBc320Kbps   (19),
         txBc384Kbps   (20),
         txBc448Kbps   (21),
         txBc512Kbps   (22),
         txBc768Kbps   (23),
         txBc896Kbps   (24),
        txBc1024Kbps   (25),
        txBc1152Kbps   (26),
        txBc1280Kbps   (27),
        txBc1344Kbps   (28),
        txBc1472Kbps   (29),
        txBc1600Kbps   (30),
        txBc1728Kbps   (31),
        txBc1856Kbps   (32),
        txBc1920Kbps   (33),
        txBc1984Kbps   (34),
        txBc2048Kbps   (35),
		txBc16000bps   (36), -- Added here: No room between (7) and (8).

		-- For Mx 30/300
		txBc112Kbps    (37),
		txBc168Kbps    (38),
        txBc224Kbps    (39),
		txBc336Kbps    (40),
        txBc672Kbps    (41),
        txBc1536Kbps   (42),
        txBc1792Kbps   (43)
        }
      MAX-ACCESS  read-create
      STATUS  current
      DESCRIPTION
      "This attribute indicates a unique Tx committed bandwidth on
       the user transmit line or at the port receive line."
      DEFVAL { full }
      ::= { agnDlciEntry 8}

agnDlciTxBe OBJECT-TYPE
      SYNTAX  INTEGER
        {
         full           (1),
         zero           (2),
         txBe5100bps    (3),
         txBe6400bps    (4),
         txBe8300bps    (5),
         txBe9600bps    (6),
        txBe14400bps    (7),
        txBe19200bps    (8),
        txBe28800bps    (9),
        txBe32000bps   (10),
        txBe38400bps   (11),
        txBe48000bps   (12),
        txBe56000bps   (13),
        txBe57600bps   (14),
          txBe64Kbps   (15),
         txBe128Kbps   (16),
         txBe192Kbps   (17),
         txBe256Kbps   (18),
         txBe320Kbps   (19),
         txBe384Kbps   (20),
         txBe448Kbps   (21),
         txBe512Kbps   (22),
         txBe768Kbps   (23),
         txBe896Kbps   (24),
        txBe1024Kbps   (25),
        txBe1152Kbps   (26),
        txBe1280Kbps   (27),
        txBe1344Kbps   (28),
        txBe1472Kbps   (29),
        txBe1600Kbps   (30),
        txBe1728Kbps   (31),
        txBe1856Kbps   (32),
        txBe1920Kbps   (33),
        txBe1984Kbps   (34),
        txBe2048Kbps   (35),
		txBe16000bps   (36), -- Added here: No room between (7) and (8).

		-- For Mx 30/300
		txBe112Kbps    (37),
		txBe168Kbps    (38),
        txBe224Kbps    (39),
		txBe336Kbps    (40),
        txBe672Kbps    (41),
        txBe1536Kbps   (42),
        txBe1792Kbps   (43)
        }
      MAX-ACCESS  read-create
      STATUS  current
      DESCRIPTION
      "This attribute indicates a unique Tx excess bandwidth on the
      user transmit line or at the port receive line."
      DEFVAL { zero }
      ::= { agnDlciEntry 9}

agnDlciRxBc OBJECT-TYPE
      SYNTAX  INTEGER
        {
         full           (1),
         zero           (2),
         rxBc5100bps    (3),
         rxBc6400bps    (4),
         rxBc8300bps    (5),
         rxBc9600bps    (6),
        rxBc14400bps    (7),
        rxBc19200bps    (8),
        rxBc28800bps    (9),
        rxBc32000bps   (10),
        rxBc38400bps   (11),
        rxBc48000bps   (12),
        rxBc56000bps   (13),
        rxBc57600bps   (14),
          rxBc64Kbps   (15),
         rxBc128Kbps   (16),
         rxBc192Kbps   (17),
         rxBc256Kbps   (18),
         rxBc320Kbps   (19),
         rxBc384Kbps   (20),
         rxBc448Kbps   (21),
         rxBc512Kbps   (22),
         rxBc768Kbps   (23),
         rxBc896Kbps   (24),
        rxBc1024Kbps   (25),
        rxBc1152Kbps   (26),
        rxBc1280Kbps   (27),
        rxBc1344Kbps   (28),
        rxBc1472Kbps   (29),
        rxBc1600Kbps   (30),
        rxBc1728Kbps   (31),
        rxBc1856Kbps   (32),
        rxBc1920Kbps   (33),
        rxBc1984Kbps   (34),
        rxBc2048Kbps   (35),
		rxBc16000bps   (36), -- Added here: No room between (7) and (8).

				-- For Mx 30/300
		rxBc112Kbps    (37),
		rxBc168Kbps    (38),
        rxBc224Kbps    (39),
		rxBc336Kbps    (40),
        rxBc672Kbps    (41),
        rxBc1536Kbps   (42),
        rxBc1792Kbps   (43)
        }
      MAX-ACCESS  read-create
      STATUS  current
      DESCRIPTION
      "This attribute indicates a unique Rx committed bandwidth on
       the user receive line or at the port transmit line."
      DEFVAL { full }
      ::= { agnDlciEntry 10}

agnDlciRxBe OBJECT-TYPE
      SYNTAX  INTEGER
        {
         full           (1),
         zero           (2),
         rxBe5100bps    (3),
         rxBe6400bps    (4),
         rxBe8300bps    (5),
         rxBe9600bps    (6),
        rxBe14400bps    (7),
        rxBe19200bps    (8),
        rxBe28800bps    (9),
        rxBe32000bps   (10),
        rxBe38400bps   (11),
        rxBe48000bps   (12),
        rxBe56000bps   (13),
        rxBe57600bps   (14),
          rxBe64Kbps   (15),
         rxBe128Kbps   (16),
         rxBe192Kbps   (17),
         rxBe256Kbps   (18),
         rxBe320Kbps   (19),
         rxBe384Kbps   (20),
         rxBe448Kbps   (21),
         rxBe512Kbps   (22),
         rxBe768Kbps   (23),
         rxBe896Kbps   (24),
        rxBe1024Kbps   (25),
        rxBe1152Kbps   (26),
        rxBe1280Kbps   (27),
        rxBe1344Kbps   (28),
        rxBe1472Kbps   (29),
        rxBe1600Kbps   (30),
        rxBe1728Kbps   (31),
        rxBe1856Kbps   (32),
        rxBe1920Kbps   (33),
        rxBe1984Kbps   (34),
        rxBe2048Kbps   (35),
		rxBe16000bps   (36), -- Added here: No room between (7) and (8).

		-- For Mx 30/300
		rxBe112Kbps    (37),
		rxBe168Kbps    (38),
        rxBe224Kbps    (39),
		rxBe336Kbps    (40),
        rxBe672Kbps    (41),
        rxBe1536Kbps   (42),
        rxBe1792Kbps   (43)
		}
      MAX-ACCESS  read-create
      STATUS  current
      DESCRIPTION
      "This attribute indicates a unique Rx excess bandwidth on the
      user receive line or at the port transmit line."
      DEFVAL { zero }
      ::= { agnDlciEntry 11}

agnDlciPriority OBJECT-TYPE
      SYNTAX  Integer32  (1..8)
      MAX-ACCESS  read-create
      STATUS  current
      DESCRIPTION
      "This attribute indicates a unique priority of the pcv.
       1 is the lowest priority and 7 is the highest priority."
      ::= { agnDlciEntry 12}

agnDlciStatus OBJECT-TYPE
      SYNTAX  INTEGER
 {
          disconnected (1),
          connected    (2)
       }
      MAX-ACCESS  read-only
      STATUS  current
      DESCRIPTION
      "This attribute indicates the status of the pvc. The status is
       disconnected(1) when one of the sides is programmed as
       not connected"
      ::= { agnDlciEntry 13}

agnDlciSpoofing OBJECT-TYPE
      SYNTAX  INTEGER
      {   no     (2),
          yes    (3)
	      }
      MAX-ACCESS  read-create
      STATUS  current
      DESCRIPTION
      "This object refers to sending of RIP messages:
       - yes : RIP messages will be sent ONLY if there is a change in the Net.
	   - no  : RIP messages will be always sent.
	   This object is relevant only when one side of the DLCI is a CL-NMS interface.
	   Default=no. "
      ::= { agnDlciEntry 14}

agnDlciFunnelEnable OBJECT-TYPE
      SYNTAX  INTEGER
      {   disabled (2),
          enabled  (3)
	      }
      MAX-ACCESS  read-create
      STATUS  current
      DESCRIPTION
      "This object selects Funnel activation enable/disable:
       - disabled: Funnel operation disabled. The agnDlciTxBe and agnDlciTxBc
	               values are not used for funneling.
	   - enabled : Funnel operation enabled. The agnDlciTxBe and agnDlciTxBc
	               values are used for funneling calculations.
	   This object is relevant only for an encapsulating DLCI.

	   In case of a Link Selector DLCI, the agnDlciTxBe and agnDlciTxBc
	               values are used for bandwidth of Link Selector.
	   Default=disabled. "
      ::= { agnDlciEntry 15}

agnDlciRoutingProtocol OBJECT-TYPE
      SYNTAX  INTEGER
      {   notApplicable(1),
          rip (2),
          rip2(3),
          none(4)
	      }
      MAX-ACCESS  read-create
      STATUS  current
      DESCRIPTION
      "This object is relevant only when one side of the DLCI is a CL-NMS interface.
	   It defines which Routing Protocol will be used for management via CL-NMS port.
	   notApplicable will be used for all slots but CL.
	   rip is a proprietary rip protocol.

	   Default=rip. "
      ::= { agnDlciEntry 16}

agnDlciRowStatus OBJECT-TYPE
      SYNTAX  RowStatus
      MAX-ACCESS  read-create
      STATUS  current
      DESCRIPTION
      "This attribute allows to create/delete a row in this table.
       For creating a row, the NMS should set
	   agnRowStatus.255.id2.id3.id4.id5.id6.id7 = active(1).
       For destroying a row, the NMS should set:
	   agnRowStatus.255.id2.id3.id4.id5.id6.id7 = destroy(6).
       Only rows with status active(1) are relevant.
       The only possible supported RowStatus vaules are
       active (1) and destroy (6)."
      ::= { agnDlciEntry 17}


-- Voice Switching Configuration Support: agnVoiceSwitching group
agnVoiceSwConfTable  OBJECT-TYPE
      SYNTAX SEQUENCE OF AgnVoiceSwConfEntry
      MAX-ACCESS not-accessible
      STATUS  current
      DESCRIPTION
      "MXcess Configuration for Voice Switching."
     ::= { agnVoiceSwitching 1 }

agnVoiceSwConfEntry OBJECT-TYPE
      SYNTAX AgnVoiceSwConfEntry
      MAX-ACCESS not-accessible
      STATUS current
	DESCRIPTION  "An entry in table."
	INDEX { agnVoiceSwConfIdx }
      ::= { agnVoiceSwConfTable 1}

AgnVoiceSwConfEntry ::=
      SEQUENCE {
 agnVoiceSwConfIdx INTEGER,
 agnVoiceSwConfZoneId  DisplayString,
 agnVoiceSwConfNodeId  DisplayString,
 agnVoiceSwConfNoOfHops 	Integer32,
 agnVoiceSwConfSidt         Integer32,
 agnVoiceSwConfLidt         Integer32,
 agnVoiceSwConfDialPlan		INTEGER
	}

agnVoiceSwConfIdx OBJECT-TYPE
      SYNTAX  INTEGER {    active(1),  temporary(255)  }
      MAX-ACCESS  read-only
      STATUS  current
      DESCRIPTION
      "Active or Temporary Table.
       Both configurations can be read but only the Temporary can
       be written to."
      ::= { agnVoiceSwConfEntry 1}

agnVoiceSwConfZoneId OBJECT-TYPE
      SYNTAX  DisplayString(SIZE(1..2))
      MAX-ACCESS  read-write
      STATUS  current
      DESCRIPTION
      "1 or 2 digits, (0-9)(1-9)."
      ::= { agnVoiceSwConfEntry 2}

agnVoiceSwConfNodeId OBJECT-TYPE
      SYNTAX  DisplayString(SIZE(1..3))
      MAX-ACCESS  read-write
      STATUS  current
      DESCRIPTION
      "1, 2 or 3 digits, (1-9),(0-9),(0-9)."
      ::= { agnVoiceSwConfEntry 3}

agnVoiceSwConfNoOfHops OBJECT-TYPE
      SYNTAX  Integer32 (0..20)
      MAX-ACCESS  read-write
      STATUS  current
      DESCRIPTION
      "Number of hops the frame will go through the net before deciding to discard
       the frame (like time-to-live in IP).

       0 = notApplicable
       Default=20 ."
      ::= { agnVoiceSwConfEntry 4}

agnVoiceSwConfSidt OBJECT-TYPE
      SYNTAX  Integer32 (0..30)
      MAX-ACCESS  read-write
      STATUS  current
      DESCRIPTION
      "SIDT: Short Inter Digit Timeout used as timer (in sec.) between digits
       after routing is completed.
       The timeout indicates end of dialing and the call can then be setup.

       0 = notApplicable
       Default=2 sec."
      ::= { agnVoiceSwConfEntry 5}

agnVoiceSwConfLidt OBJECT-TYPE
      SYNTAX  Integer32 (0..30)
      MAX-ACCESS  read-write
      STATUS  current
      DESCRIPTION
      "LIDT: Long Inter Digit Timeout used as timer between digits before routing
       is completed. If no digits were dialed and LIDT expired then the user will get
       an error tone and the call will be disconnected.

       0 = notApplicable
       Default=15 sec."
      ::= { agnVoiceSwConfEntry 6}

agnVoiceSwConfDialPlan OBJECT-TYPE
      SYNTAX  INTEGER {
	   staticDialPlan(2),
	   staticDialPlanPlus(3),
	   flexDialPlan(4)
 	   }
      MAX-ACCESS  read-write
      STATUS  current
      DESCRIPTION
      "This is the Dialing Plan method that will be used in the Voice Switching.
      Static Dialing Plan - Routing is defined by the current device Zone and
                            Node ID in the Network.
      Static Dialing Plan Plus - Includes the Static Dialing Plan but contains an
                            addition of defining the number of dialed digits.
      Flexible Dialing Plan - Routing is defined in a flexible form.
                              In this plan the user can configure the extension number
                              of a local voice channel, Route a call to a remote
                              destination and enter the Number of Digits for a specific
                              dial prefix."
      ::= { agnVoiceSwConfEntry 7}


agnVoiceSwConfRtTable  OBJECT-TYPE
      SYNTAX SEQUENCE OF AgnVoiceSwConfRtEntry
      MAX-ACCESS not-accessible
      STATUS  current
      DESCRIPTION
      "Routing Table for Voice Switching."
     ::= { agnVoiceSwitching 2 }

agnVoiceSwConfRtEntry OBJECT-TYPE
      SYNTAX AgnVoiceSwConfRtEntry
      MAX-ACCESS not-accessible
      STATUS current
	DESCRIPTION  "An entry in table."
	INDEX { agnVoiceSwConfRtDbId, agnVoiceSwConfRtIdx }
      ::= { agnVoiceSwConfRtTable 1}

AgnVoiceSwConfRtEntry ::=
      SEQUENCE {
 agnVoiceSwConfRtDbId   INTEGER,
 agnVoiceSwConfRtIdx        Integer32,
 agnVoiceSwConfRtDigits  DisplayString,
 agnVoiceSwConfRtAction  INTEGER,
 agnVoiceSwConfRtData  DisplayString,
 agnVoiceSwConfRtSlot  INTEGER,
 agnVoiceSwConfRtPort  Integer32,
 agnVoiceSwConfRtDlci  Integer32,
 agnVoiceSwConfRtRowStatus RowStatus,
 agnVoiceSwConfRtMaxCalls  Integer32 
	}

agnVoiceSwConfRtDbId OBJECT-TYPE
      SYNTAX  INTEGER {    active(1),  temporary(255)  }
      MAX-ACCESS  read-only
      STATUS  current
      DESCRIPTION
      "Active or Temporary Table.
       Both configurations can be read but only the Temporary can
       be written to."
 ::= { agnVoiceSwConfRtEntry 1 }

agnVoiceSwConfRtIdx  OBJECT-TYPE
 SYNTAX  Integer32
 MAX-ACCESS read-only
 STATUS current
 DESCRIPTION
 " The Index of the row."
 ::= { agnVoiceSwConfRtEntry 2 }

agnVoiceSwConfRtDigits OBJECT-TYPE
 SYNTAX  DisplayString ( SIZE(1..7) )
 MAX-ACCESS read-create
 STATUS current
 DESCRIPTION
 " Dialed digits: Series of digits 0...9, '*', '#' or '%'.
   The '*' and '#' can have many uses according to the user's decision.
   For example, they can be used as part of the Dialed Number,
   they exist on the phone number panel.
   '*' can also be used instead of a series of numbers.
   The '%' means any digits (wildcard) and is used without a series of digits.
 
   When the agnVoiceSwConfRtAction is del (7), the series of digits that
   are configured via this MIB object will be deleted from the prefix of
   the dialed number."
 ::= { agnVoiceSwConfRtEntry 3 }

agnVoiceSwConfRtAction OBJECT-TYPE
 SYNTAX  INTEGER {
   notApplicable(1),
   zone(2),
   node(3),
   shortDialing(4), 
   in(5),  -- Internal switching
   hgr(6), -- Hunt Group
   del(7), -- Delete a prefix from the Dialed Number
   rep(8), -- Replace a prefix with a given string of digits
   pri(9), -- for ISDN
   bri(10),-- for ISDN
   numDigDP(11), -- Number of Digits user will dial according to Dialing Plan.
   route(12), -- Route to a Remote Destination
   ext(13) -- Extension to a local voice channel
 }
 MAX-ACCESS read-create
 STATUS current
 DESCRIPTION
 " Action that the system should perform for the digits:
   agnVoiceSwConfRtDigits.
   The action that is allowed depends on the Dialing Plan.
   Here is the list of the allowed actions:
   For Static Dialing Plan - zone, node, in, shortDialing, hgr, del, rep
   For Static Dialing Plan Plus - zone, node, in, shortDialing, hgr, del, rep, numDigDP
   For Flexible Dialing Plan - hgr, del, rep, numDigDP, route, ext"
 DEFVAL { notApplicable }
 ::= { agnVoiceSwConfRtEntry 4 }

agnVoiceSwConfRtData   OBJECT-TYPE
 SYNTAX  DisplayString(SIZE(1..7))
 MAX-ACCESS read-create
 STATUS current
 DESCRIPTION
 " This field is relevant for actions hgr(6), and rep(8), numDigDP(11)
   and contains the following information:
   For hgr - the number of the Hunt Group.
   For rep - the number of digits to be replaced with.
   For numDigDP - the number of digits collected before establishing the call.
                  0 indicates no defined length. In this case SIDT will be used."
-- DEFVAL {"0" }
 ::= { agnVoiceSwConfRtEntry 5 }

agnVoiceSwConfRtSlot OBJECT-TYPE
 SYNTAX  INTEGER{
       noConnect(2),
       cl    (3),
       io1   (5),
       io2   (6),
       io3   (7),
       io4   (8),
       io5   (9),
       io6  (10),
       io7  (11),
       io8  (12),
       io9  (13),
       io10 (14),
       io11 (15),
       io12 (16),
       notApplicable(255)
       }
 MAX-ACCESS read-create
 STATUS current
 DESCRIPTION
 " Routing Slot- Relevant for actions zone(2), node(3), shortDialing(4),
   route(12), ext(13)."
 DEFVAL { noConnect }
 ::= { agnVoiceSwConfRtEntry 6 }

agnVoiceSwConfRtPort OBJECT-TYPE
 SYNTAX  Integer32
 MAX-ACCESS read-create
 STATUS current
 DESCRIPTION
	" Routing Port- Relevant for actions zone(2), node(3), shortDialing(4),
      route(12), ext(13).
	  100=noConnect (for non-routing case)."
 DEFVAL { 0 }
 ::= { agnVoiceSwConfRtEntry 7 }

agnVoiceSwConfRtDlci OBJECT-TYPE
	SYNTAX 	Integer32
	MAX-ACCESS	read-create
	STATUS	current
	DESCRIPTION
	" Routing DLCI- Relevant for actions zone(2), node(3), shortDialing(4),
      route(12), ext(13). 
	  Valid values:
	  0=notApplicable (for non-routing case).
	  1, 16..991 "
    DEFVAL { 15 }
	::= { agnVoiceSwConfRtEntry 8 }

agnVoiceSwConfRtRowStatus OBJECT-TYPE
 SYNTAX  RowStatus
 MAX-ACCESS read-create
 STATUS current
 DESCRIPTION
 " Status of the row for creating/deleting entries in the table.
   The only possible supported RowStatus vaules are
   active (1), notInService (2), notReady(3), createAndGo(4),
   createAndWait(5) and destroy(6)."
 ::= { agnVoiceSwConfRtEntry 9 }

agnVoiceSwConfRtMaxCalls OBJECT-TYPE
      SYNTAX  Integer32 
      MAX-ACCESS  read-create
      STATUS  current
      DESCRIPTION
      "Maximum no. of simultaneous voice calls that are allowed in the direction
       defined by the current entry.

       Default=0 (No Limit)."
      ::= { agnVoiceSwConfRtEntry 10}


agnVoiceSwConfHGTable  OBJECT-TYPE
      SYNTAX SEQUENCE OF AgnVoiceSwConfHGEntry
      MAX-ACCESS not-accessible
      STATUS  current
      DESCRIPTION
      "Table of Hunt Groups."
     ::= { agnVoiceSwitching 5 }

agnVoiceSwConfHGEntry OBJECT-TYPE
      SYNTAX AgnVoiceSwConfHGEntry
      MAX-ACCESS not-accessible
      STATUS current
	DESCRIPTION  "An entry in table."
	INDEX { agnVoiceSwConfHGdbIdx, agnVoiceSwConfHGIdx }
      ::= { agnVoiceSwConfHGTable 1}

AgnVoiceSwConfHGEntry ::=
      SEQUENCE {
 agnVoiceSwConfHGdbIdx INTEGER,
 agnVoiceSwConfHGIdx  Integer32,
 agnVoiceSwConfHGConnect INTEGER,
 agnVoiceSwConfHGExt  Integer32 
	}

agnVoiceSwConfHGdbIdx OBJECT-TYPE
      SYNTAX  INTEGER {    active(1),  temporary(255)  }
      MAX-ACCESS  read-only
      STATUS  current
      DESCRIPTION
      "Active or Temporary Table.
       Both configurations can be read but only the Temporary can
       be written to."
      ::= { agnVoiceSwConfHGEntry 1}

agnVoiceSwConfHGIdx OBJECT-TYPE
      SYNTAX  Integer32(1..10)
      MAX-ACCESS  read-only
      STATUS  current
      DESCRIPTION
      "There may be up to 10 Hunt Groups per MXcess. That's the
       index of the hunt group relevant to this row."
      ::= { agnVoiceSwConfHGEntry 2}

agnVoiceSwConfHGConnect OBJECT-TYPE
      SYNTAX  INTEGER {  no(2),  yes(3)   }
      MAX-ACCESS  read-write
      STATUS  current
      DESCRIPTION
      "This attribute indicates whether the  hunt group  should be
       considered in any of the mux algorithms."
      ::= { agnVoiceSwConfHGEntry 3}

agnVoiceSwConfHGExt OBJECT-TYPE
      SYNTAX  Integer32(0..99)
      MAX-ACCESS  read-write
      STATUS  current
      DESCRIPTION
      "This is the extension number of the hunt group.
       0 is for not valid. The allowed range is 10 - 99."
      DEFVAL { 0 }
      ::= { agnVoiceSwConfHGEntry 4}


--
-- Signaling Profiles for MP-2200 and MP-2100
--
-- Legacy Profile Table

agnSigProfileTable  OBJECT-TYPE
     SYNTAX SEQUENCE OF AgnSigProfileEntry
     MAX-ACCESS not-accessible
     STATUS  current
     DESCRIPTION
      "The write operation into the Table Objects is valid only
       to the TmpCnfg entry.
       The table includes signaling profile parameters for Legacy Profiles."
     ::= { agnSigProfile 1}

agnSigProfileEntry OBJECT-TYPE
      SYNTAX AgnSigProfileEntry
      MAX-ACCESS not-accessible
      STATUS current
	DESCRIPTION  "An entry in table."
	INDEX {agnSigProfileCnfgIdx, agnSigProfileIdx, agnSigProfileRxTx}
      ::= { agnSigProfileTable 1}

AgnSigProfileEntry ::=
      SEQUENCE {
      agnSigProfileCnfgIdx Integer32,
      agnSigProfileIdx     Integer32,
      agnSigProfileRxTx    INTEGER,
      agnSigProfileABCD    OCTET STRING
      }


agnSigProfileCnfgIdx OBJECT-TYPE
      SYNTAX  Integer32 (1..255)
      MAX-ACCESS  read-only
      STATUS  current
      DESCRIPTION
      "This attribute indicates the Idx of the Cnfg (1..100) being
       accessed.
       Idx 255 relates to the TmpCnfg.
       The write operation is valid only to the TmpCnfg."
      ::= { agnSigProfileEntry 1}

agnSigProfileIdx OBJECT-TYPE
      SYNTAX  Integer32 (1..5)
      MAX-ACCESS  read-only
      STATUS  current
      DESCRIPTION
      "This attribute indicates the Signaling Profile (1..5)."
      ::= { agnSigProfileEntry 2}

agnSigProfileRxTx OBJECT-TYPE
      SYNTAX  INTEGER
       {
       rx   (1),
       tx   (2)
       }
      MAX-ACCESS  read-only
      STATUS  current
      DESCRIPTION
      "This attribute indicates if the following objects refer to:
       Rx or Tx translation.
       Rx : ML->IO
       Tx : IO->ML  ."
      ::= { agnSigProfileEntry 3}

agnSigProfileABCD OBJECT-TYPE
      SYNTAX  OCTET STRING
      MAX-ACCESS  read-write
      STATUS  current
      DESCRIPTION
      "This object represents 6 parameters, by 3 Octets :
       Busy  Code-MSB nibble, - applicable only for Rx translation
       Idle  Code-    nibble, - applicable only for Rx translation
       D Bit Code-    nibble,
       C Bit Code-    nibble,
       B Bit Code-    nibble,
       A Bit Code-LSB nibble.

       Each of Busy and Idle Code nibble will have the valid values:
       0000 .. FFFF.

       Each of A,B,C,D Bit Code nibble represents:
       0 hex = 0000 = 0
       1 hex = 0001 = 1
       2 hex = 0010 = A bit
       3 hex = 0011 = B bit
       4 hex = 0100 = C bit
       5 hex = 0101 = D bit
       6 hex = 0110 = A bit inverse
       7 hex = 0111 = B bit inverse
       8 hex = 1000 = C bit inverse
       9 hex = 1001 = D bit inverse
       A-F hex - not used (invalid values)
       
       When the object is not applicable, the Octet String will have 0 bytes."
      ::= { agnSigProfileEntry 4}

-- General Profile Table

agnSigProfTable  OBJECT-TYPE
     SYNTAX SEQUENCE OF AgnSigProfEntry
     MAX-ACCESS not-accessible
     STATUS  current
     DESCRIPTION
      "The write operation into the Table Objects is valid only
       to the TmpCnfg entry. This is the general table of signaling profiles."
     ::= { agnSigProfile 2}

agnSigProfEntry OBJECT-TYPE
      SYNTAX AgnSigProfEntry
      MAX-ACCESS not-accessible
      STATUS current
	DESCRIPTION  "An entry in table."
	INDEX {agnSigProfCnfgIdx, agnSigProfIdx}
      ::= { agnSigProfTable 1}

AgnSigProfEntry ::=
      SEQUENCE {
      agnSigProfCnfgIdx Integer32,
      agnSigProfIdx     Integer32,
      agnSigProfName    DisplayString,
	  agnSigProfType    INTEGER
      }

agnSigProfCnfgIdx OBJECT-TYPE
      SYNTAX  Integer32 (1..255)
      MAX-ACCESS  read-only
      STATUS  current
      DESCRIPTION
      "This attribute indicates the Idx of the Cnfg (1..100) being
       accessed.
       Idx 255 relates to the TmpCnfg.
       The write operation is valid only to the TmpCnfg."
      ::= { agnSigProfEntry 1}

agnSigProfIdx OBJECT-TYPE
      SYNTAX  Integer32 (1..5)
      MAX-ACCESS  read-only
      STATUS  current
      DESCRIPTION
      "This attribute indicates the Signaling Profile (1..5)."
      ::= { agnSigProfEntry 2}

agnSigProfName   OBJECT-TYPE
      SYNTAX  DisplayString(SIZE(0..12))
      MAX-ACCESS read-write
      STATUS current
      DESCRIPTION
      "Profile Name given by user."
      ::= { agnSigProfEntry 3 }

agnSigProfType OBJECT-TYPE
      SYNTAX  INTEGER 
       {
          notApplicable (1),
          legacy        (2),
          r2Cas         (3)
       }
      MAX-ACCESS  read-write
      STATUS  current
      DESCRIPTION
      "Profile Type.
       legacy - usual signaling. The parameters for the Legacy Profiles 
                are detailed in the agnSigProfileTable, above.
       r2Cas  - R2 signaling. The parameters for the R2 Profiles are detailed
                in the r2 ProfileCnfg tables (belong to r2If).   "
      ::= { agnSigProfEntry 4 }


--
-- TS Assignment Table from system point of view
--
-- agnTsTable  OBJECT-TYPE ::= { agnSystemTs 1}
--
-- For this table see tsa.txt file.


-- General System Voice parameters
--
systemVoiceTable  OBJECT-TYPE
      SYNTAX SEQUENCE OF SystemVoiceEntry
      MAX-ACCESS not-accessible
      STATUS  current
      DESCRIPTION
      "General Parameters for voice - system level."
     ::= { systemVoice 1 }

systemVoiceEntry OBJECT-TYPE
      SYNTAX SystemVoiceEntry
      MAX-ACCESS not-accessible
      STATUS current
	DESCRIPTION  "An entry in table."
	INDEX { systemVoiceConfIdx }
      ::= { systemVoiceTable 1}

SystemVoiceEntry ::=
      SEQUENCE {
 systemVoiceConfIdx      Integer32,
 systemVoiceNationalTone INTEGER
 }

systemVoiceConfIdx OBJECT-TYPE
      SYNTAX  Integer32 
      MAX-ACCESS  read-only
      STATUS  current
      DESCRIPTION
      "This attribute indicates the Idx of the Cnfg (1..100) being
       accessed - Active or Temporary Configurations.
       Idx  255 relates to the temporary TmpCnfg.
       All configurations can be read but only the Temporary can
       be written to."
      ::= { systemVoiceEntry 1}

systemVoiceNationalTone OBJECT-TYPE
      SYNTAX  INTEGER 
       {
          notApplicable (1),
          usa           (2),
          australia     (3),
		  brazil        (4),
		  canada        (5),
		  france        (6),
		  germany       (7),
		  israel        (8),
		  mexico        (9),
		  portugal      (10),
		  russia        (11),
		  spain         (12),
		  unitedKingdom (13),
		  czech         (14),
		  china         (15)
       }
      MAX-ACCESS  read-write
      STATUS  current
      DESCRIPTION
      "Tone Characteristics (Amplitude, Frequency, delays etc.).
       These characteristics are defined according to the country."
      ::= { systemVoiceEntry 2}

--
-- Wan installed module status general information
--
mdlSInstTable  OBJECT-TYPE
      SYNTAX SEQUENCE OF MdlSInstEntry
      MAX-ACCESS not-accessible
      STATUS current
	DESCRIPTION  "A table."
	::=  { statMdlGen 1 }

mdlSInstEntry OBJECT-TYPE
      SYNTAX MdlSInstEntry
      MAX-ACCESS not-accessible
      STATUS current
	DESCRIPTION  "An entry in table."
	INDEX { mdlSInstSltIdx }
      ::= { mdlSInstTable 1}

MdlSInstEntry ::=
      SEQUENCE {
     mdlSInstSltIdx        INTEGER,
     mdlSInstCardType      INTEGER,
     mdlSHwVersion         DisplayString (SIZE (0..255)),
     mdlSSwVersion         DisplayString (SIZE (0..255)),
     mdlSAlrStatus         INTEGER,
     mdlSAlrStatusAll      INTEGER,
     mdlSMaskedAlrStat     INTEGER,
     mdlSMaskedAlrStatAll  INTEGER,
     mdlSTstStatusAll      INTEGER,
     mdlSClearAlrCmd       INTEGER,
     mdlSClearAllAlrCmd    INTEGER
      }

mdlSInstSltIdx OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16)
       }
      MAX-ACCESS  read-only
      STATUS  current
      DESCRIPTION
      "A unique number to identify a slot position in the mux.
       In the ?004 Unit the entries PsB(2),ClB(4),io6(10)..io(16)
       are not valid.
       For the Vmux2100 Main Board clA  (3) is used."
      ::= { mdlSInstEntry 1}


mdlSInstCardType OBJECT-TYPE
      SYNTAX  INTEGER
       {
  --
  -- General types
  --		 
         unknown        (1),
         empty          (2),

  -- (3)..(7) are reserved ; they appear in the compress structure

		 acm            (9), --alarm module
  --
  -- Power Supply Modules
  --
        ps60W          (10),
        ps100W         (11),

  --
  -- Cl Modules
  --
        cl1            (20),
        clEth          (21),
        cl2            (22),
		cl2Eth         (23),
        cl3            (24),
		cl3Eth         (25),

  --
  -- Packet Cards of Megaplex
  --
        mPh1            (31),
        mPh3            (32),
        mPh1T1DSU       (33),
        mPh1T1CSU       (34),
        mPh1E1DSU       (35),
        mPh1E1LTU       (36),

  -- TDM Cards

        mtmlFT1         (37),
        mtmlFE1         (38),
		mtmlH4E1        (39),
		mtmlH4E12W      (40),
		mtmlH4T1        (41),
		mtmlH4T12W      (42),
		mtHsh4E1        (43),
		mtHsh4E12W      (44),
		mtHsh4T1        (45),
		mtHsh4T12W      (46),
		mtmlH2E1        (47),
		mtmlH2E12W      (48),
		mtmlH2T1        (49),
		mtmlH2T12W      (50),
		hsh2E1          (51),
		hsh2E12W        (52),
		hsh2T1          (53),
		hsh2T12W        (54),
		mlIp            (55),
		mtml4Ip         (56),

  -- Packet Cards of Megaplex

        mPl6            (60),
        mPl3            (61),

  -- Vmux-2100 Main Link cards 
	    ml2E1           (68),
	    ml4E1           (69),
        ml2T1           (70),
	    ml4T1           (71),

        mPv4            (72),

  --
  -- TDM Cards
  --
      vc16A             (73),
      vc8EandM          (74),
      vc8Fxo            (75),
      vc8Fxs            (76),
      vc16EandM         (77),
      vc16Fxo           (78),
      vc16Fxs           (79),

      vf3EandM          (80),
      vf3Fxs            (81),
      vf3Fxo            (82),

      vfPbx             (83),
      vfPbxT1           (84),
      vfPbxE1           (85),

	  mtMlE2S           (86), --Single Link
	  mtMlE2D           (87), --Dual Link 
      mtMlF2T1          (88),
      mtMlF2E1          (89),
      mtMlT1Fiber       (90),
      mtMlE1Fiber       (91),
      mtMlT1FiberFb     (92),
      mtMlE1FiberFb     (93),
      mtmlHE1           (94),
      mtmlH1E1          (95),
      mtmlHSE1          (96),
      ml20              (97),
      mtMl4T1           (98),
      mtMl4E1           (99),

      mtMl1T1DSU       (100),
      mtMl1T1CSU       (101),
      mtMl1E1DSU       (102),
      mtMl1E1LTU       (103),
      mtMl1T1DSUfb     (104),
      mtMl1T1CSUfb     (105),
      mtMl1E1DSUfb     (106),
      mtMl1E1LTUfb     (107),
      mtMl2T1          (108),
      mtMl2E1          (109),

       ls2CcittX50     (110),
       ls2CcittX58     (111),
       ls2ATandTSdm    (112),
       ls2ACcittX50    (113),
       ls2ACcittX58    (114),
       ls2AATandTSdm   (115),
       ls2A2Ts         (116),
       ls2M            (117),

      mtMlT1           (118),
      mtMlE1           (119),

       hs2             (120),
       hs3             (121),
       hsq             (122),
       hs703           (123),
       hsQM            (124),
       hsqN            (125),
       hs6             (126),
       hs12            (127),
	   hsDp            (128),
	   hsp             (129), 

       hs4T1           (130),
       hs4E1           (131),
       hs4             (132),

       hsEth           (133),

  --  Vmux-2100  Voice cards 
       vc2E1           (136),
       vc4E1           (137),
       vc2T1           (138),
       vc4T1           (139), 
  
       vc2EandM        (140),
       vc2Fxs1Plar     (141),
       vc2Fxo1         (142),
       vc2Fxs2         (143),
       vc2Fxo2         (144),
       vc2Fxs3         (145),
       vc2Fxo3         (146),
       vc26EandM       (147),
       mtvc2           (148),
       vc2R2Fxs        (149),

       hsu             (150),

       mbeA            (151),
       mbeB            (152),
       mbeU            (153),
       tre             (154),

       hsuI            (155),
       hsr             (156),
       hss             (157),
       hsu1            (158),

       ls12            (159),
       ls6             (160),
       ls6V1EandM      (161),
       ls6V1Fxo        (162),
       ls6V1Fxs        (163),
       ls6V2EandM      (164),
       ls6V2Fxo        (165),
       ls6V2Fxs        (166),
       ls6VfEandM      (167),
       ls6VfFxo        (168),
       ls6VfFxs        (169),

       vc3EandM        (170),
       vc3Fxo          (171),
       vc3Fxs          (172),

       vcPbx           (173),
       vcPbxT1         (174),
       vcPbxE1         (175),

       vc6EandM        (176),
       vc6Fxo          (177),
       vc6Fxs          (178),

       vcq             (179),

       ls6n            (180),


  --
  -- Packet Cards of MAXcess and Hybrid
  --

        -- High speed cards

        mhs1V36          (181),
        mhs1V35          (182),
        mhs1G703         (183),
        mhs1DDS          (184),
        mhs3             (185),
        mhs1X21          (186),
        mhs1V24          (187),
		mhs4             (188),
        mhsE1Hs          (189),
		mhsT1Hs          (190),
		mhsHyE1Hs        (191), -- 2 HS ports + 1 Hybrid E1 port
		mhsHyT1Hs        (192), -- 2 HS ports + 1 Hybrid T1 port
        mlfHybE1Hs       (193), -- Fiber Optic Hybrid: 2 HS + 1 Hybrid E1 port
        mlfHybT1Hs       (194), -- Fiber Optic Hybrid: 2 HS + 1 Hybrid T1 port 


        -- T1/E1 cards

        mhs2e1			 (195),
		mhs2t1           (196),
		mhsHy2e1         (197), -- 2 Hybrid E1 ports
		mhsHy2t1         (198), -- 2 Hybrid T1 ports
        mlfHybE12        (199), -- Fiber Optic Hybrid: 2 E1 ports
        

        -- Low speed cards

        mls6             (200),
        mls3             (201),


        -- More  T1/E1 cards

        mlHybAtmE1       (202), -- Hybrid ATM E1
        mlHybAtmT1       (203), -- Hybrid ATM T1
        mlfHybT12        (204), -- Fiber Optic Hybrid: 2 T1 ports


		--  Voice cards

        mvc8             (205), -- MVC-8 name in marketing: MVC-4N
        mvc8PbxE1        (206),
        mvc8PbxT1Dsu     (207),
        mvc8PbxT1Csu     (208),
        mvc8PbxE1Slave   (209),

        mvc4             (210),
        mvc4PbxE1        (211),
        mvc4PbxT1Dsu     (212),
        mvc4PbxT1Csu     (213),
        mvc4PbxE1Slave   (214),
        mvc4PbxT1Slave   (215),
 
        mvc8PbxT1Slave   (216),	-- MVC-8 T1 Slave is here
        mvc8ExtAnalog    (217), -- MVC-8 with 8 External ports
		mvcE1            (218), -- 8 External ports & 30 Internals
		mvcT1            (219), -- 8 External ports & 24 Internals

		-- ISDN for Maxcess
        mhsS             (220),
        mhsU             (221),
        mhsPriE1         (222),
        mhsPriT1         (223),

        -- CCS for Maxcess & MPH
        mPriE1FramerCcs  (225),
        mPriT1FramerCcs  (226),
        mPriE1SlaveCcs   (227),
        mPriT1SlaveCcs   (228),
		mDualBri         (229),

        --Voice cards for MP
        vc12EandM        (230),
        vc12Fxo          (231),
        vc12Fxs          (232),
		vc6aEandM        (233),
        vc6aFxo          (234),
        vc6aFxs          (235),
        vc6AgFxo         (236),
        vc6AgFxs         (237),
        vc6a4LB          (238),

        --ISDN cards for MP
		hsu12            (240),
		hsu6             (241),
		hss12            (242),
		hss6             (243),

        -- More Hybrid cards + IP cards for MPH        
    	mhsHyE1          (247),          -- 1 Hybrid E1 port
		mhsHyT1          (248),          -- 1 Hybrid T1 port         
        mhsIp            (249),          -- 1 Eth  port + 1 HS port
        mlIpHs           (250),          -- 1 Eth  port + 3 HS ports
        mlHybIpE1        (251),          -- 1 Eth  port + 1 HS port + 1 E1
        mlHybIpT1        (252),          -- 1 Eth  port + 1 HS port + 1 T1

        -- VOIP cards for MPH & MX
        mvg1Lan          (253),
        mvg2Lan          (254)
          }
      MAX-ACCESS  read-only
      STATUS  current
      DESCRIPTION
      "This attribute indicates the type of card installed
       in the specific slot position.
       Only PS cards are possible in the PS slots.
       Only CL cards are possible in the CL slots.
       Only IO cards are possible in the IO slots."
      ::= { mdlSInstEntry 2}

mdlSHwVersion OBJECT-TYPE
      SYNTAX  DisplayString (SIZE (0..255))
      MAX-ACCESS  read-only
      STATUS  current
      DESCRIPTION
      "This attribute indicates the Hardware version of the
       installed card in the specific slot position."
      ::= { mdlSInstEntry 3 }

mdlSSwVersion OBJECT-TYPE
      SYNTAX  DisplayString (SIZE (0..255))
      MAX-ACCESS  read-only
      STATUS  current
      DESCRIPTION
      "This attribute indicates the Software version of the
       installed card in the specific slot position."
      ::= {mdlSInstEntry 4}


mdlSAlrStatus OBJECT-TYPE
      SYNTAX  INTEGER
       {
  off      (2),
  event    (3),
  minor    (4),
  major    (5),
     warning  (6),
  critical (7)
       }
      MAX-ACCESS  read-only
      STATUS  current
      DESCRIPTION
      "Indicates the alarm state at module level, i.e. lower level
      (port alarms) status is not included.
      This attribute will be set to:
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
       ::= { mdlSInstEntry 5 }

mdlSAlrStatusAll OBJECT-TYPE
      SYNTAX  INTEGER
       {
  off      (2),
  event    (3),
  minor    (4),
  major    (5),
     warning  (6),
  critical (7)
       }
      MAX-ACCESS  read-only
      STATUS  current
      DESCRIPTION
      "Indicates the alarm state in the module-all level, i.e. lower level
      (port alarms) included.
      This attribute will be set to:
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
       ::= { mdlSInstEntry 6 }

mdlSMaskedAlrStat OBJECT-TYPE
      SYNTAX  INTEGER
       {
  off      (2),
  event    (3),
  minor    (4),
  major    (5),
     warning  (6),
  critical (7)
       }
      MAX-ACCESS  read-only
      STATUS  current
      DESCRIPTION
      "Indicates the alarm state at module level, [i.e. lower level
      (port alarms) status is not included],including Masked alarms.
      This attribute will be set to:
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
       ::= { mdlSInstEntry 7 }

mdlSMaskedAlrStatAll OBJECT-TYPE
      SYNTAX  INTEGER
       {
  off      (2),
  event    (3),
  minor    (4),
  major    (5),
     warning  (6),
  critical (7)
       }
      MAX-ACCESS  read-only
      STATUS  current
      DESCRIPTION
      "Indicates the alarm state in the module-all level, i.e. lower level
      (port alarms) included, including Masked alarms.
      This attribute will be set to:
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
       ::= { mdlSInstEntry 8 }

mdlSTstStatusAll OBJECT-TYPE
      SYNTAX  INTEGER
       {
  off(2),
  on (3)
       }
      MAX-ACCESS  read-only
      STATUS  current
      DESCRIPTION
      "This attribute will be set to on(3) when there is at least
       one test in progress on a channel of the card, otherwise
       the value will be off(2)."
      ::= { mdlSInstEntry 9 }


mdlSClearAlrCmd  OBJECT-TYPE
      SYNTAX  INTEGER
       {
  off(2),
  on (3)
       }
      MAX-ACCESS  read-write
      STATUS  current
      DESCRIPTION
      "Setting this command to ON, enforces a clear of all the
       alarms in the given slot, excluding alarms of port level.
       The clear operation will not be applied for masked/inverted
       alarms."
      ::= { mdlSInstEntry 10 }

mdlSClearAllAlrCmd  OBJECT-TYPE
      SYNTAX  INTEGER
       {
  off(2),
  on (3)
       }
      MAX-ACCESS  read-write
      STATUS  current
      DESCRIPTION
      "Setting this command to ON, enforces a  clear of all the
       alarms in the given slot, including all its ports alarms.
       The clear operation will not be applied for masked/inverted
       alarms."
      ::= { mdlSInstEntry 11 }

mdlSAlrTable OBJECT-TYPE
      SYNTAX SEQUENCE OF MdlSAlrEntry
      MAX-ACCESS not-accessible
      STATUS current
      DESCRIPTION
      "The list of card agent alarms ; includes also an alarm
       indicating existence of alarms on its ports if there are any."
      ::= { statMdlGen 2 }

mdlSAlrEntry OBJECT-TYPE
      SYNTAX MdlSAlrEntry
      MAX-ACCESS not-accessible
      STATUS current
	DESCRIPTION  "An entry in table."
	INDEX {mdlSAlrSltIdx , mdlSAlrIdx}
      ::= { mdlSAlrTable 1}

MdlSAlrEntry ::=
      SEQUENCE {
  mdlSAlrSltIdx           INTEGER,
  mdlSAlrIdx              Integer32,
  mdlSAlrCodeDescription  DisplayString (SIZE (0..255)),
  mdlSAlrCode             Integer32,
  mdlSAlrSeverity         INTEGER,
  mdlSAlrState            INTEGER,
  mdlSAlrCounter          Integer32,
  mdlSAlrMask             INTEGER,
  mdlSAlrInvert           INTEGER
      }

mdlSAlrIdx OBJECT-TYPE
      SYNTAX  Integer32
      MAX-ACCESS  read-only
      STATUS  current
      DESCRIPTION
      "A unique number to identify an entry in the alarm status table.
       Users should use the get next function to read this table because
       the indexes are not consecutive."
      ::= { mdlSAlrEntry 1}

mdlSAlrSltIdx OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16)
       }
      MAX-ACCESS  read-only
      STATUS  current
      DESCRIPTION
      "This attribute indicates the  desired slot position.
       In the ?004 Unit the entries PsB(2),ClB(4),io6(10)..io12(16)
       are not valid.
       For the Vmux2100 Main Board clA  (3) is used."
      ::= { mdlSAlrEntry 2}

mdlSAlrCodeDescription OBJECT-TYPE
      SYNTAX  DisplayString (SIZE (0..255))
      MAX-ACCESS  read-only
      STATUS  current
      DESCRIPTION
      "This attribute is a full text description of the alarm .
       The alarm description includes the following information:
       alarm code, alarm text, alarm severity, Masked or Inverted
       flag and counter."
      ::= { mdlSAlrEntry 3}

mdlSAlrCode OBJECT-TYPE
      SYNTAX  Integer32
      MAX-ACCESS  read-only
      STATUS  current
      DESCRIPTION
      "A code identifying the alarm of an entry in the alarm status
       table at card level."
      ::= { mdlSAlrEntry 4 }

mdlSAlrSeverity OBJECT-TYPE
      SYNTAX  INTEGER
       {
  event    (3),
  minor    (4),
  major    (5),
  warning  (6),
  critical (7)
       }
      MAX-ACCESS  read-only
      STATUS  current
      DESCRIPTION
      "The severity of the alarm."
      ::= { mdlSAlrEntry 5 }

mdlSAlrState  OBJECT-TYPE
      SYNTAX  INTEGER
       {
  off(2),
  on (3)
       }
      MAX-ACCESS  read-only
      STATUS  current
      DESCRIPTION
      "State of the alarm."
      ::= { mdlSAlrEntry 6 }

mdlSAlrCounter OBJECT-TYPE
      SYNTAX  Integer32
      MAX-ACCESS  read-only
      STATUS  current
      DESCRIPTION
      "A counter - how many times the alarm occured since last
       clear operation.
       ON and OFF Alarm will be counted separately."
      ::= { mdlSAlrEntry 7 }

mdlSAlrMask  OBJECT-TYPE
      SYNTAX  INTEGER
       {
  off(2),
  on (3)
       }
      MAX-ACCESS  read-only
      STATUS  current
      DESCRIPTION
      "Alarm mask : on/off."
      ::= { mdlSAlrEntry 8 }

mdlSAlrInvert  OBJECT-TYPE
      SYNTAX  INTEGER
       {
  off(2),
  on (3)
       }
      MAX-ACCESS  read-only
      STATUS  current
      DESCRIPTION
      "Alarm invert : on/off."
      ::= { mdlSAlrEntry 9 }


--
-- Wan module configuration information
--
mdlCPrgTable  OBJECT-TYPE
      SYNTAX SEQUENCE OF MdlCPrgEntry
      MAX-ACCESS not-accessible
      STATUS current
	DESCRIPTION  "A table."
	::=  { cnfgMdlGen 1 }

mdlCPrgEntry OBJECT-TYPE
      SYNTAX MdlCPrgEntry
      MAX-ACCESS not-accessible
      STATUS current
	DESCRIPTION  "An entry in table."
	INDEX { mdlCCnfgIdx, mdlCSltIdx  }
      ::= { mdlCPrgTable 1}

MdlCPrgEntry ::=
      SEQUENCE {
   		mdlCCnfgIdx           Integer32,
      	mdlCSltIdx            INTEGER,
   		mdlCPrgCardType       INTEGER,
   		mdlCNoOfExternPrt     Integer32,   -- RO
   		mdlCNoOfInternPrt     Integer32,   -- RO
		mdlCWorkMode          INTEGER
      }

mdlCCnfgIdx OBJECT-TYPE
      SYNTAX  Integer32 (1..255)
      MAX-ACCESS  read-only
      STATUS  current
      DESCRIPTION
      "This attribute indicates the Idx of the Cnfg(1..100) being
       referred.
       Value  255 specifies the TmpCnfg "
      ::= { mdlCPrgEntry 1}
-- In phase I only the values 1 (Cnfg1) and 255 (temp) are valid.

mdlCSltIdx OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16)
       }
      MAX-ACCESS  read-only
      STATUS  current
      DESCRIPTION
      "This attribute indicates a unique number of  the slot
       position where the card is inserted.
       In the ?004 Unit the entries psB(2),clB(4),io6(10)..io(16)
       are not valid."
      ::= { mdlCPrgEntry 2}

mdlCPrgCardType OBJECT-TYPE
      SYNTAX  INTEGER
       {
  --
  -- General types
  --
        unknown         (1),
        empty           (2),

  -- (3)..(7) are reserved ; they appear in the compress structure

		 acm            (9), --alarm module

  --
  -- Power Supply Modules
  --
        ps48x60W       (10),
        ps48x100W      (11),
        ps110x60W      (12),
        ps110x100W     (13),
        ps220x60W      (14),
        ps220x100W     (15),
        ps180W         (16),

  --
  -- Cl Modules
  --
        cl1            (20),
        clEth          (21),
        cl2            (22),
		cl2Eth         (23),
        cl3            (24),
		cl3Eth         (25),

  --
  -- Packet Cards of Megaplex
  --
        mPh1            (31),
        mPh3            (32),
        mPh1T1DSU       (33),
        mPh1T1CSU       (34),
        mPh1E1DSU       (35),
        mPh1E1LTU       (36),

  -- TDM Cards

        mtmlFT1         (37),
        mtmlFE1         (38),
		mtmlH4E1        (39),
		mtmlH4E12W      (40),
		mtmlH4T1        (41),
		mtmlH4T12W      (42),
		mtHsh4E1        (43),
		mtHsh4E12W      (44),
		mtHsh4T1        (45),
		mtHsh4T12W      (46),
		mtmlH2E1        (47),
		mtmlH2E12W      (48),
		mtmlH2T1        (49),
		mtmlH2T12W      (50),
		hsh2E1          (51),
		hsh2E12W        (52),
		hsh2T1          (53),
		hsh2T12W        (54),
		mlIp            (55),
		mtml4Ip         (56),

  -- Packet Cards of Megaplex

        mPl6            (60),
--      mPl3            (61),

  -- Vmux-2100 Main Link cards 
	    ml2E1           (68),
	    ml4E1           (69),
        ml2T1           (70),
	    ml4T1           (71),

--      mPv4            (72),


  --
  -- TDM Cards
  --
      vc16A             (73),
      vc8EandM          (74),
      vc8Fxo            (75),
      vc8Fxs            (76),
      vc16EandM         (77),
      vc16Fxo           (78),
      vc16Fxs           (79),

      vf3EandM          (80),
      vf3Fxs            (81),
      vf3Fxo            (82),

      vfPbx             (83),
      vfPbxT1           (84),
      vfPbxE1           (85),

	  mtMlE2S           (86), --Single Link
	  mtMlE2D           (87), --Dual Link 
      mtMlF2T1          (88),
      mtMlF2E1          (89),
      mtMlT1Fiber       (90),
      mtMlE1Fiber       (91),
      mtMlT1FiberFb     (92),
      mtMlE1FiberFb     (93),
      mtmlHE1           (94),
      mtmlH1E1          (95),
      mtmlHSE1          (96),
      ml20              (97),
      mtMl4T1           (98),
      mtMl4E1           (99),

      mtMl1T1DSU       (100),
      mtMl1T1CSU       (101),
      mtMl1E1DSU       (102),
      mtMl1E1LTU       (103),
      mtMl1T1DSUfb     (104),
      mtMl1T1CSUfb     (105),
      mtMl1E1DSUfb     (106),
      mtMl1E1LTUfb     (107),
      mtMl2T1          (108),
      mtMl2E1          (109),

      ls2CcittX50      (110),
      ls2CcittX58      (111),
      ls2ATandTSdm     (112),
      ls2ACcittX50     (113),
      ls2ACcittX58     (114),
      ls2AATandTSdm    (115),
      ls2A2Ts          (116),
      ls2M             (117),

      mtMlT1           (118),
      mtMlE1           (119),

      hs2              (120),
      hs3              (121),
      hsq              (122),
      hs703            (123),
      hsQM             (124),
      hsqN             (125),
      hs6              (126),
      hs12             (127),
	  hsDp             (128), 
	  hsp              (129), 

      hs4T1            (130),
      hs4E1            (131),

      hsEth            (133),

       vc2E1           (136),
       vc4E1           (137),
       vc2T1           (138),
       vc4T1           (139), 

      vc2EandM         (140),
      vc2Fxs1Plar      (141),
      vc2Fxo1          (142),
      vc2Fxs2          (143),
      vc2Fxo2          (144),
      vc2Fxs3          (145),
      vc2Fxo3          (146),
      vc26EandM        (147),
      mtvc2            (148),
      vc2R2Fxs         (149),

      hsu              (150),

      mbeA             (151),
      mbeB             (152),
      mbeU             (153),
      tre              (154),

      hsuI             (155),
      hsr              (156),
      hss              (157),
      hsu1             (158),

      ls12            (159),
      ls6             (160),
      ls6V1EandM      (161),
      ls6V1Fxo        (162),
      ls6V1Fxs        (163),
      ls6V2EandM      (164),
      ls6V2Fxo        (165),
      ls6V2Fxs        (166),
      ls6VfEandM      (167),
      ls6VfFxo        (168),
      ls6VfFxs        (169),

      vc3EandM        (170),
      vc3Fxo          (171),
      vc3Fxs          (172),

      vcPbx           (173),
      vcPbxT1         (174),
      vcPbxE1         (175),

      vc6EandM        (176),
      vc6Fxo          (177),
      vc6Fxs          (178),

      vcq             (179),

      ls6n            (180),

  --
  -- Packet Cards of Maxcess and Hybrid
  --

        -- High speed cards

        mhs1V36          (181),
        mhs1V35          (182),
        mhs1G703         (183),
        mhs1DDS          (184),
        mhs3             (185),
        mhs1X21          (186),
        mhs1V24          (187),
		mhs4             (188),
        mhsE1Hs          (189),
		mhsT1Hs          (190),
		mhsHyE1Hs        (191), -- 2 HS ports + 1 Hybrid E1 port
		mhsHyT1Hs        (192), -- 2 HS ports + 1 Hybrid T1 port
        mlfHybE1Hs       (193), -- Fiber Optic Hybrid: 2 HS + 1 Hybrid E1 port
        mlfHybT1Hs       (194), -- Fiber Optic Hybrid: 2 HS + 1 Hybrid T1 port 

        -- T1/E1 cards

        mhs2e1			 (195),
		mhs2t1           (196),
		mhsHy2e1         (197), -- 2 Hybrid E1 ports
		mhsHy2t1         (198), -- 2 Hybrid T1 ports
        mlfHybE12        (199), -- Fiber Optic Hybrid: 2 E1 ports

        -- Low speed cards

        mls6             (200),
        mls3             (201),


        -- More  T1/E1 cards
        mlHybAtmE1       (202), -- Hybrid ATM E1
        mlHybAtmT1       (203), -- Hybrid ATM T1
        mlfHybT12        (204), -- Fiber Optic Hybrid: 2 T1 ports

		--  Voice cards

        mvc8             (205), -- MVC-8 name in marketing: MVC-4N
        mvc8PbxE1        (206),
        mvc8PbxT1Dsu     (207),
        mvc8PbxT1Csu     (208),
        mvc8PbxE1Slave   (209),

  
        mvc4             (210),
        mvc4PbxE1        (211),
        mvc4PbxT1Dsu     (212),
        mvc4PbxT1Csu     (213),
        mvc4PbxE1Slave   (214),
        mvc4PbxT1Slave   (215),

        mvc8PbxT1Slave   (216),	-- MVC-8 T1 Slave is here 
        mvc8ExtAnalog    (217), -- MVC-8 with 8 External ports
		mvcE1            (218), -- 8 External ports & 30 Internals
		mvcT1            (219), -- 8 External ports & 24 Internals

		-- ISDN for Maxcess
        mhsS             (220),
        mhsU             (221),
        mhsPriE1         (222),
        mhsPriT1         (223),

        -- CCS for Maxcess & MPH
        mPriE1FramerCcs  (225),
        mPriT1FramerCcs  (226),
        mpriE1SlaveCcs   (227),
        mpriT1SlaveCcs   (228),
		mDualBri         (229),

        --Voice cards for MP
        vc12EandM        (230),
        vc12Fxo          (231),
        vc12Fxs          (232),
		vc6aEandM        (233),
        vc6aFxo          (234),
        vc6aFxs          (235),
        vc6AgFxo         (236),
        vc6AgFxs         (237),
        vc6a4LB          (238),

        --ISDN cards for MP
		hsu12            (240),
		hsu6             (241),
		hss12            (242),
		hss6             (243),

        -- More Hybrid cards + IP cards for MPH        
    	mhsHyE1          (247),          -- 1 Hybrid E1 port
		mhsHyT1          (248),          -- 1 Hybrid T1 port         
        mhsIp            (249),          -- 1 Eth  port + 1 HS port
        mlIpHs           (250),          -- 1 Eth  port + 3 HS ports
        mlHybIpE1        (251),          -- 1 Eth  port + 1 HS port + 1 E1
        mlHybIpT1        (252),          -- 1 Eth  port + 1 HS port + 1 T1

    -- VOIP cards for MPH & MX
        mvg1Lan          (253),
        mvg2Lan          (254)
		
        }
      MAX-ACCESS  read-write
      STATUS  current
      DESCRIPTION
      "This attribute indicates the type of card assigned to the
       specific slot in the common configuration.
       This object is identical in all the configurations (1..100).
       Only the TmpCnf(255) may have different value.
       The write operation is valid only to the TmpCnfg entry."
      ::= { mdlCPrgEntry 3}

mdlCNoOfExternPrt OBJECT-TYPE
      SYNTAX  Integer32
      MAX-ACCESS  read-only
      STATUS  current
      DESCRIPTION
      "Number of external ports in the programmed card of the
       specific slot position"
      ::= { mdlCPrgEntry 4}

mdlCNoOfInternPrt OBJECT-TYPE
      SYNTAX  Integer32
      MAX-ACCESS  read-only
      STATUS  current
      DESCRIPTION
      "Number of internal ports in the programmed card of the
       specific slot position."
      ::= { mdlCPrgEntry 5}

mdlCWorkMode OBJECT-TYPE
      SYNTAX  INTEGER
       {
       notApplicable (1),
	   standAlone    (2),
	   integrated    (3)
       }
      MAX-ACCESS  read-write
      STATUS  current
      DESCRIPTION
      "Working mode of the card.
       The user may configure the card to work in a stand alone mode or integrated
       with the device.
       
	   Example for use in MHS-IP cards:

       - standAlone - in this mode, the router works so that data is received
         via the LAN (Eth) port and is transmitted via the WAN (HS) external port
         without going through the MPH device.

       - integrated - in this mode, the router works so that it is integrated in the MPH
         and routes DLCIs into the device."
      ::= { mdlCPrgEntry 6}


--
-- Compressed information.
--
-- Specially for RadView management station
--
mdlCmprTable  OBJECT-TYPE
      SYNTAX SEQUENCE OF MdlCmprEntry
      MAX-ACCESS not-accessible
      STATUS current
	DESCRIPTION  "A table."
	::=  { cmprMdlGen 1 }

mdlCmprEntry OBJECT-TYPE
      SYNTAX MdlCmprEntry
      MAX-ACCESS not-accessible
      STATUS current
	DESCRIPTION  "An entry in table."
	INDEX { mdlCmprTypIdx, mdlCmprCnfgIdx ,mdlCmprVersion,mdlCmprSltIdx }
      ::= {mdlCmprTable  1}

MdlCmprEntry ::=
      SEQUENCE {
  mdlCmprTypIdx     Integer32,
  mdlCmprCnfgIdx    Integer32,
  mdlCmprVersion    Integer32,
  mdlCmprSltIdx     INTEGER,
  mdlCmprObj        OCTET STRING
      }

mdlCmprTypIdx OBJECT-TYPE
      SYNTAX  Integer32
      MAX-ACCESS  read-only
      STATUS  current
      DESCRIPTION
      "This attribute indicates the Type of the Compressed being
       referred."
      ::= { mdlCmprEntry 1}

mdlCmprCnfgIdx OBJECT-TYPE
      SYNTAX  Integer32
      MAX-ACCESS  read-only
      STATUS  current
      DESCRIPTION
      "This attribute indicates the configuration to which the
       Compressed information is  related."
      ::= { mdlCmprEntry 2}

mdlCmprVersion OBJECT-TYPE
      SYNTAX  Integer32
      MAX-ACCESS  read-only
      STATUS  current
      DESCRIPTION
      "This attribute indicates the version of the internal format
       of the Compressed data"
      ::= { mdlCmprEntry 3}

mdlCmprSltIdx  OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16)
       }
      MAX-ACCESS  read-only
      STATUS  current
      DESCRIPTION
      "This attribute indicates a unique number of  the slot
       position where the card is inserted.
       In the ?004 Unit the entries psB(2),clB(4),io6(10)..io(16)
       are not valid."
      ::= { mdlCmprEntry 4}

mdlCmprObj OBJECT-TYPE
      SYNTAX  OCTET STRING
      MAX-ACCESS  read-write
      STATUS  current
      DESCRIPTION
      "This attribute is the compressed information itself."
      ::= { mdlCmprEntry 5}

-- Compressed Alarm table at Card level
-- The only way of reading this table is by the command 'GET NEXT'

mdlAlarmsCmprTable  OBJECT-TYPE
      SYNTAX SEQUENCE OF MdlAlarmsCmprEntry
      MAX-ACCESS not-accessible
      STATUS current
	DESCRIPTION  "A table."
	::=  {cmprMdlGen 2}

mdlAlarmsCmprEntry OBJECT-TYPE
      SYNTAX MdlAlarmsCmprEntry
      MAX-ACCESS not-accessible
      STATUS current
	DESCRIPTION  "An entry in table."
	INDEX {mdlAlarmsCmprVersion,
             mdlAlarmsCmprAlarmSlot,mdlAlarmsCmprAlarmIdx}
      ::= {mdlAlarmsCmprTable  1}

MdlAlarmsCmprEntry ::=
      SEQUENCE {
     mdlAlarmsCmprVersion      Integer32,
     mdlAlarmsCmprAlarmSlot    Integer32,
     mdlAlarmsCmprAlarmIdx     Integer32,
     mdlAlarmsCmprObj          OCTET STRING
      }

mdlAlarmsCmprVersion OBJECT-TYPE
      SYNTAX  Integer32
      MAX-ACCESS  read-only
      STATUS  current
      DESCRIPTION
      "This attribute indicates the version of the internal format
       of the Compressed data"
      ::= { mdlAlarmsCmprEntry 1}

mdlAlarmsCmprAlarmSlot  OBJECT-TYPE
      SYNTAX  Integer32
      MAX-ACCESS  read-only
      STATUS  current
      DESCRIPTION
      "This attribute indicates the  desired slot position.
       In the ?004 Unit the entries PsB(2),ClB(4),io6(10)..io(16)
       are not valid."
      ::= { mdlAlarmsCmprEntry 2}

mdlAlarmsCmprAlarmIdx  OBJECT-TYPE
      SYNTAX  Integer32
      MAX-ACCESS  read-only
      STATUS  current
      DESCRIPTION
      "A unique number to identify an entry in the alarm status table
       of the agent."
      ::= { mdlAlarmsCmprEntry 3}

mdlAlarmsCmprObj OBJECT-TYPE
      SYNTAX  OCTET STRING
      MAX-ACCESS  read-write
      STATUS  current
      DESCRIPTION
      "This attribute is the compressed information itself."
      ::= { mdlAlarmsCmprEntry 4}


--
-- Wan port status general information
--
prtSInstTable  OBJECT-TYPE
      SYNTAX SEQUENCE OF PrtSInstEntry
      MAX-ACCESS not-accessible
      STATUS current
	DESCRIPTION  "A table."
	::=  { statPrtGen 1 }

prtSInstEntry OBJECT-TYPE
      SYNTAX PrtSInstEntry
      MAX-ACCESS not-accessible
      STATUS current
	DESCRIPTION  "An entry in table."
	INDEX { prtSInstSltIdx, prtSInstPrtIdx }
      ::= { prtSInstTable 1}

PrtSInstEntry ::=
      SEQUENCE {
        prtSInstSltIdx       INTEGER,
        prtSInstPrtIdx       Integer32,
        prtSInstPrtType      INTEGER,
        prtSInstIfIndex      Integer32,
        prtSActiveStatus     INTEGER,
        prtSAlrStatus        INTEGER,
        prtSMaskedAlrStat    INTEGER,
        prtSClearAlrCmd      INTEGER,
        prtSTestMask         Integer32,
--        prtSTstStatus        INTEGER,
        prtSTstCmd           INTEGER,
        prtSTstDuration      Integer32,
        prtSBertClrCmd       INTEGER,
        prtSBertTstRslt      Integer32,
        prtSInterfaceType    DisplayString (SIZE (0..255)),
        prtSParamStatus      OCTET STRING
      }

prtSInstSltIdx OBJECT-TYPE
      SYNTAX  INTEGER
       {
       clA   (3),
       clB   (4),
       io1   (5),
       io2   (6),
       io3   (7),
       io4   (8),
       io5   (9),
       io6  (10),
       io7  (11),
       io8  (12),
       io9  (13),
       io10 (14),
       io11 (15),
       io12 (16),
       notApplicable (255)
       }
      MAX-ACCESS  read-only
      STATUS  current
      DESCRIPTION
      "This attribute indicates a unique number to identify the
       slot where the card is inserted.
       In the ?004 Unit the entries io6(10)..io(16) are not valid.
       For the Vmux2100 Main Board clA  (3) is used."
      ::= { prtSInstEntry 1}

prtSInstPrtIdx OBJECT-TYPE
      SYNTAX  Integer32
      MAX-ACCESS  read-only
      STATUS  current
      DESCRIPTION
      "This attribute indicates a unique number to identify a port
       in a specific card.
       The valid ports depend on the installed card:
       the valid external ports (interfaces) are (1..mdlCNoOfExternPrt) if any,
       and the valid internal ports are (101..100+mdlCNoOfInternPrt) if any.
       Generally:  exPrt1 (1) .. exPrt16  (16),inPrt1 (101) .. inPrt48 (148)

	   For the Vmux-2100 device:
	   This index will have values of 1...4 for the physical ports & values
	   of ifIndex for the bundles. "
      ::= { prtSInstEntry 2}

prtSInstPrtType  OBJECT-TYPE
      SYNTAX  INTEGER
       {
  external      (2),
  internal      (3),
  highSpeedV35  (4),
  highSpeedV24  (5),
  highSpeedV36  (6),
  highSpeedX21  (7),
  highSpeedG703 (8),
  highSpeedDDS  (9),
  lowSpeed      (10),
  voice         (11),
  cl            (12),
  isdns         (13),
  isdnu         (14),
  ethernet      (15),
  voiceS0       (16),
  voiceU        (17),
  voiceQsigS    (18),
  voiceQsigU    (19)
       }
      MAX-ACCESS  read-only
      STATUS  current
      DESCRIPTION
       "This attribute describes the type of the designated port.
	   In MX 3000 only external & internal options are used.
	   All the other options are only for MX 30/300 which need special handling.
	   In order to support interface types in MX 3000, return an ascii string for
	   prtSInterfaceType in this table or support the general RAD value of
       physicalConnector.

       External port - is a port with  a physical connector.
       Internal port - might be of two types:
         a) A composite port which collects a few external ports
            data into a common bandwidth (usually routed through
            DS1 link)
         b) A port which gets only part of the external ports
            (usually a few DS0's)
    The following types are used when all ports are external/
    internal and the connector/interface type is necessary
    (for example, stand-alone units):
       High Speed port types
       Low  Speed port types
       Voice port types, CL port types.
       
       ISDN Voice in MX 30/300 Phase 4: voiceS0   (16), voiceU     (17) should be used.
       ISDN Voice in MX 30/300 Phase 5: voiceQsigS(18), voiceQsigU (19) should be used."
      ::= { prtSInstEntry 3}

prtSInstIfIndex  OBJECT-TYPE
      SYNTAX  Integer32
      MAX-ACCESS  read-only
      STATUS  current
      DESCRIPTION
      "This attribute indicates the  unique  interface number
       assigned to the port. The specific interface of this
       attribute is the same as the interface identified by the
       value of ifindex  in MIB-II.If there is no interface for
       the specific prtIdx the value will be '7fffffff'h."
      ::= { prtSInstEntry 4}

prtSActiveStatus   OBJECT-TYPE
      SYNTAX  INTEGER
       {
         unknown           (1),
         notUsed           (2),
         offLine           (3),
         onLine            (4),
         offLineRedundancy (5),
         onLineRedundancy  (6)
       }
      MAX-ACCESS  read-only
      STATUS  current
      DESCRIPTION
      "This attribute describes the activity status of the port.
       unknown(1) indicates that the information is not supported.
       notUsed(2) indicates that the ch is not connected according
                  to the active config.
       offLine(3) indicates that the ch is down (not working)
                  because of any problem.
       onLine(4)  indicates that the ch is up (working)
       offLineRedundancy(5) indicates that the ch is down, because
                            it is redundant port.
       onLineRedundancy(6)  indicates that the ch is up, and it is
                            the active link"
      ::= { prtSInstEntry 5}

prtSAlrStatus OBJECT-TYPE
      SYNTAX  INTEGER
       {
  off      (2),
  event    (3),
  minor    (4),
  major    (5),
  warning  (6),
  critical (7)
       }
      MAX-ACCESS  read-only
      STATUS  current
      DESCRIPTION
      "Indicates the alarm state in the port(ch) agent level.
      This attribute will be set to:
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
      ::= { prtSInstEntry 6}

prtSMaskedAlrStat OBJECT-TYPE
      SYNTAX  INTEGER
       {
  off      (2),
  event    (3),
  minor    (4),
  major    (5),
  warning  (6),
  critical (7)
       }
      MAX-ACCESS  read-only
      STATUS  current
      DESCRIPTION
      "Indicates the alarm state in the port(ch) agent level,
       including Masked alarms.
       This attribute will be set to:
    critical(7) - when there is at least one active (state ON)
                  critical alarm,
                  otherwise it will be set to
       major(5) - when there is at least one active (state ON)
                  major alarm,
                  otherwise it will be set to
       minor(4) - if there is at least one active (state ON) minor
                  alarm,
                  otherwise it will be set to
       warning(6) - if there is at least one active (state ON)
                  warning alarm,
                  otherwise it will be set to
       event(3) - if there was at least one alarm event (including
                  state on,off events) since the last clear operation."
 ::= {prtSInstEntry 7}

prtSClearAlrCmd  OBJECT-TYPE
      SYNTAX  INTEGER
       {
  off(2),
  on (3)
       }
      MAX-ACCESS  read-write
      STATUS  current
      DESCRIPTION
      "Setting this attribute to on(3) enforces a clear operation
       of the alarm status events in the given port. The clear
       operation will not be applied for masked/inverted alarms."
      ::= { prtSInstEntry 8}

prtSTestMask OBJECT-TYPE
      SYNTAX  Integer32
      MAX-ACCESS  read-only
      STATUS  current
      DESCRIPTION
      "This is a mask which indicates which tests from the
       'prtSTstCmd' list are allowed for the requested port.
       If a specific test is allowed, its respective bit
       will be SET in the mask :

         TEST                  BIT
        -----------            ---
        local-loop              1
        remote-loop             2
        loc-and-rem-main-loops  3
        remote-analog-loop      4
        remote-digital-loop     5
        rem-loop-on-ext-unit    6
        bert                    7
        tone-injection          8
        dlci local-loop         9
        all dlci local-loop    10
        dlci remote-loop       11
        all dlci remote-loop   12
        bert-and-rem-loop-on-rem-unit 13
        rem-loop-on-rem-unit   14
        block                  15
        backward-tone-inject   16
        llb                    17
        rlb                    18

        ft1Enable              21
		lbbd                   22  --for 2B+D
		lb1                    23  --for B1
		lb2                    24  --for B2
		llb-on-rem-unit        25
		bert-on-rem-unit       26
		bert-on-rem-and-llb-on-rem-unit 27
		local-and-bert-on-rem-unit 28
		local-loop-on-rem-unit 29
		localBert              30  --towards IO ports
		test-per-TS            31

        e.g : If the return value is 3 -> 0000000000000011  ->
              Bits 1 & 2 are set -> the allowed tests are :
                                           local-loop
                                           remote-loop
        "
      ::= { prtSInstEntry 9}

-- prtSTstStatus OBJECT-TYPE
--      SYNTAX  INTEGER
--          {
--        off(2),
--        on (3)
--          }
--      MAX-ACCESS  read-only
--      STATUS  current
--      DESCRIPTION
--      "This attribute will be set to on(3) when there is at least
--       one test in progress in the port, otherwise the value
--       will be off(2)."
--      ::= { prtSInstEntry 10}
--


prtSTstCmd OBJECT-TYPE
      SYNTAX  INTEGER
       {
        none                 (1),
        localLoop            (2),
        remoteLoop           (3),
        locAndRemMainLoops   (4),
        remoteAnalogLoop     (5),
        remoteDigitalLoop    (6),
        remLoopOnExtUnit     (7),
        bert                 (8),
        toneInjection        (9),
        dlciLocalLoop        (10),
        allDlciLocalLoop     (11),
        dlciRemoteLoop       (12),
        allDlciRemoteLoop    (13),
        extInitLocalLoop     (14),
        bertAndRemLoopOnRemUnit (15),
        remLoopOnRemUnit     (16),
        block                (17),
        backwardToneInject   (18),
        llb                  (19),
        rlb                  (20),
        ft1Enable            (21),
		lbbd                 (22),	--for 2B+D
		lb1                  (23),	--for B1
		lb2                  (24),	--for B2
		llbOnRemUnit         (25),
		bertOnRemUnit        (26),
		bertOnRemAndLlbOnRemUnit (27),
		localAndBertOnRemUnit(28),
		localLoopOnRemUnit   (29),
		localBert            (30),
		testPerTS            (31)
       }
      MAX-ACCESS  read-write
      STATUS  current
      DESCRIPTION
      "Setting this attribute to any of the above values will
       initiate a test on the specific port if the operation is
       legal. If the operation is not legal, the mux will ignore
       the operation.
	   testPerTS(31) - when this test is selected, the selection of tests
	                   for each TS is done via the prtExPh1MlTsTest object. 
       If a test time out is needed, the test will be set with a
       default timeout of 2 minutes until the user will set the
       parameter 'prtSTstDuration' to the required time out.
       If no time out is needed , the test will be set with infinite
       timeout until the user will set the parameter
       'prtSTstDuration' to the required time out."
      ::= { prtSInstEntry 10}

prtSTstDuration OBJECT-TYPE
      SYNTAX  Integer32
      MAX-ACCESS  read-write
      STATUS  current
      DESCRIPTION
      "This attribute indicates the maximum duration of executing
      a test on the specific port. This entry applies to all the
      test operations. The resolution will be a minute, and the
      maximum duration is limited to 30 minutes .
      A zero  value specifies no time limitation.
      When the test isn't active, the agent initiates this object to
      2 when the duration is needed and to 0 if its not required.
      The user should set this parameter after setting the
      'prtSTstCmd' parameter."
      ::= { prtSInstEntry 11}

prtSBertClrCmd  OBJECT-TYPE
      SYNTAX  INTEGER {
      off(2),
      on (3)
      }
      MAX-ACCESS  read-write
      STATUS  current
      DESCRIPTION
      "Setting this attribute initiates bert count clear operation.
       It is valid only when bert test is active on the specific
       port."
      ::= { prtSInstEntry 12}

prtSBertTstRslt   OBJECT-TYPE
      SYNTAX  Integer32
      MAX-ACCESS  read-only
      STATUS  current
      DESCRIPTION
      "This attribute indicates the number of Bit Error Rate
       indicated during the BERT operation.
       It is valid only when bert test is active on the specific
       port."
      ::= { prtSInstEntry 13}

prtSInterfaceType OBJECT-TYPE
      SYNTAX  DisplayString (SIZE (0..255))
      MAX-ACCESS  read-only
      STATUS  current
      DESCRIPTION
      "This attribute indicates a unique HW interface type of the
       selected port."
      ::= { prtSInstEntry 14}


prtSParamStatus OBJECT-TYPE
      SYNTAX  OCTET STRING
      MAX-ACCESS  read-only
      STATUS  current
      DESCRIPTION
      "This object indicates Status of parameters specific to the
       selected port.
       - For a port that has no special status or is supported
         by prtSExHsfStatTable - 1 Octet: 00hex

       - For VC-6, VC-6A, VC-6AG, VC-6A/4LB, VC-12, VC-12/6,  external ports - 1 Octet :
         Bit 7 (MSB)..Bit 2 = 0 (NA)
         Bit 1:       Tx Signaling '1'=On ; '0'=Off
         Bit 0 (LSB): Rx Signaling '1'=On ; '0'=Off

       - For VC-2/R2(FXS) external ports - 1 Octet :
         Bit  -   7 6 5 4 3 2 1 0
                  |_| |_________|
                  Call  Call State
             Direction

         Bit 7 (MSB) and Bit 6  : Call Direction
         00 - Incoming
         01 - Outgoing
         Bit 5..Bit 0: Call State
         000000 - Idle
         000001 - Seized
         000010 - Both-Way Conflict
         000011 - Seizure Ack
         000100 - Answered
         000101 - Clear Backward
         000110 - Clear Forward
         000111 - Blocked
         001000 - Fault
         001001 - Fault 3
         001010 - Fault 4
         001011 - Fault 5
         001100 - Fault 6
         001101 - Fault 7

       - For ML-20 external port - 3 Octets :
         - 1 MS Octet will represent the Real Rate used:
               Bit    - 7 6 5 4 3 2 1 0
                        |___| |_______|
                  spare  Rate

           Valid values: 0..31, meaning 0..31x64Kbps
           Invalid values: 32..255.
         - 2 LS Octets will represent the Status of 7 Control
           Signals:
           Signal - ---  CTS  DSR  DCD   RJ   TM   DTR  RTS
           Bit   - 7 6  5 4  3 2  1 0    7 6  5 4  3 2  1 0
           Octet  -          2                     3 (LS)
           '---' will always have the value 00
           Rest of the Signals (2 bits each) can have the following
           values:
           00=NA   ;  01=unused ; 10=Off  ; 11=On

       - For ML-H/E1, ML-H/1/E1, ML-H/S/E1 internal port - 1 Octet
         Bit    - 7 6 5 4 3 2 1 0
                  |___________|
                    spare       Mode of Operation

         Mode of Operation: '1'=Central  ; '0'=Remote

       - For ACM external port - 1 Octet
         Bit    - 7 6 5 4 3 2 1 0
                  |_________|
                    spare       Alarm State

         Alarm State: according to bits 1,0:
         00=NA   ;  01=unused ; 10=Off  ; 11=On

       - For HS-U/1 external port - 1 Octet
	     Bit 7  6  5  4  3  2  1  0 LSB
             |________|  |__|  |__|
               spare     modem  sync  
               
         modem: 00 = other         sync:  00 = not sync
                01 = unknown              01 = sync
                10 = ASMi-31/2            10 = reserved
                11 = reserved             11 = reserved
		 
	   - For MTML-2  external ports, MTML-E2 internal ports - 1 Octet :
	     Bit 7  6  5  4  3  2  1  0 LSB
                                  |
                     			 BERT State
		 BERT State (Bit 0):
		 0 = OFF (BERT is not running on this port or any of its TSs/Bits)
		 1 = ON  (BERT is running on this port OR on one of its TSs/Bits)"
      ::= { prtSInstEntry 15}


prtSAlrTable OBJECT-TYPE
      SYNTAX SEQUENCE OF PrtSAlrEntry
      MAX-ACCESS not-accessible
      STATUS current
      DESCRIPTION
      "The list of port agent alarms."
      ::= { statPrtGen 2 }

prtSAlrEntry OBJECT-TYPE
      SYNTAX PrtSAlrEntry
      MAX-ACCESS not-accessible
      STATUS current
	DESCRIPTION  "An entry in table."
	INDEX { prtSAlrSltIdx, prtSAlrPrtIdx, prtSAlrIdx}
      ::= { prtSAlrTable 1}

PrtSAlrEntry ::=
      SEQUENCE {
  prtSAlrSltIdx            INTEGER,
  prtSAlrPrtIdx            Integer32,
  prtSAlrIdx               Integer32,
  prtSAlrCodeDescription   DisplayString (SIZE (0..255)),
  prtSAlrCode              Integer32,
  prtSAlrSeverity          INTEGER,
  prtSAlrState             INTEGER,
  prtSAlrCounter           Integer32,
  prtSAlrMask              INTEGER,
  prtSAlrInvert            INTEGER
      }

prtSAlrIdx OBJECT-TYPE
      SYNTAX  Integer32
      MAX-ACCESS  read-only
      STATUS  current
      DESCRIPTION
      "A unique number to identify an entry in the alarm status table.
       Users should use the get next function to read this table because
       the indexes are not consecutive"
      ::= { prtSAlrEntry 1}

prtSAlrSltIdx OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16),
    notApplicable (255)
       }
      MAX-ACCESS  read-only
      STATUS  current
      DESCRIPTION
      "This attribute indicates a unique identifier of  the slot
       where the card is inserted.
       In the ?004 Unit the entries PsB(2),ClB(4),io6(10)..io12(16)
       are not valid.
       For the Vmux2100 Main Board clA  (3) is used."
    ::= { prtSAlrEntry 2}

prtSAlrPrtIdx OBJECT-TYPE
      SYNTAX  Integer32
      MAX-ACCESS  read-only
      STATUS  current
      DESCRIPTION
      "This attribute indicates a unique identifier of  the port
       the alarm applies to.
       All the values are valid. No alarms exist for a port
       which does not exist.
       Valid values: exPrt1    (1) .. exPrt16  (16) ,
                     inPrt1  (101) .. inPrt48 (148),
                     IP Bundles."
    ::= { prtSAlrEntry 3}

prtSAlrCodeDescription OBJECT-TYPE
      SYNTAX  DisplayString (SIZE (0..255))
      MAX-ACCESS  read-only
      STATUS  current
      DESCRIPTION
      "This attribute is a full text description of the alarm.
       The alarm description includes the following information:
       alarm code, alarm text, alarm severity, Masked  or Inverted
       flag and counter."
       ::= { prtSAlrEntry 4}

prtSAlrCode OBJECT-TYPE
      SYNTAX  Integer32
      MAX-ACCESS  read-only
      STATUS  current
      DESCRIPTION
      "A code identifying the alarm of an entry in the alarm status
       table at port level."
      ::= { prtSAlrEntry 5 }

prtSAlrSeverity OBJECT-TYPE
      SYNTAX  INTEGER
       {
  event    (3),
  minor    (4),
  major    (5),
     warning  (6),
  critical (7)
       }
      MAX-ACCESS  read-only
      STATUS  current
      DESCRIPTION
      "The severity of the alarm."
      ::= { prtSAlrEntry 6 }

prtSAlrState  OBJECT-TYPE
      SYNTAX  INTEGER
       {
  off(2),
  on (3)
       }
      MAX-ACCESS  read-only
      STATUS  current
      DESCRIPTION
      "State of the alarm."
      ::= { prtSAlrEntry 7 }

prtSAlrCounter OBJECT-TYPE
      SYNTAX  Integer32
      MAX-ACCESS  read-only
      STATUS  current
      DESCRIPTION
      "A counter - how many times the alarm occured since last
       clear operation.
       ON and OFF Alarm will be counted separately."
      ::= { prtSAlrEntry 8 }

prtSAlrMask  OBJECT-TYPE
      SYNTAX  INTEGER
       {
  off(2),
  on (3)
       }
      MAX-ACCESS  read-only
      STATUS  current
      DESCRIPTION
      "Alarm mask : on/off."
      ::= { prtSAlrEntry 9 }

prtSAlrInvert  OBJECT-TYPE
      SYNTAX  INTEGER
       {
  off(2),
  on (3)
       }
      MAX-ACCESS  read-only
      STATUS  current
      DESCRIPTION
      "Alarm invert : on/off."
      ::= { prtSAlrEntry 10 }

--
-- Statistics of Ports
--

statisPrtGen   OBJECT IDENTIFIER ::= {statPrtGen 3}

prtFrStatis    OBJECT IDENTIFIER ::= {statisPrtGen 1}
prtCrStatis    OBJECT IDENTIFIER ::= {statisPrtGen 2}
prtDlciStatis  OBJECT IDENTIFIER ::= {statisPrtGen 3}
prtT1Statis    OBJECT IDENTIFIER ::= {statisPrtGen 4}

--prtFrStatis - Port Statistics for (FR) Frame Relay protocol

prtFrStatisTable  OBJECT-TYPE
     SYNTAX SEQUENCE OF PrtFrStatisEntry
     MAX-ACCESS not-accessible
     STATUS  current
     DESCRIPTION
      "This table is applicable only for an active port running an
       FR protocol ."
  ::= { prtFrStatis 1}

prtFrStatisEntry OBJECT-TYPE
      SYNTAX PrtFrStatisEntry
      MAX-ACCESS not-accessible
      STATUS current
	DESCRIPTION  "An entry in table."
	INDEX {prtFrStatisSltIdx, prtFrStatisPrtIdx, prtFrStatisInvIdx}
      ::= { prtFrStatisTable 1}

PrtFrStatisEntry ::=
      SEQUENCE {
      prtFrStatisSltIdx    INTEGER,
      prtFrStatisPrtIdx    INTEGER,
   prtFrStatisInvIdx    INTEGER,
      prtFrTimeElapsed     Integer32,
      prtFrRxTotalFrames   Counter32,
      prtFrTxTotalFrames   Counter32,
      prtFrRxTotalBytes    Counter32,
      prtFrTxTotalBytes    Counter32,
      prtFrRxMngFrames     Counter32,
      prtFrTxMngFrames     Counter32,
      prtFrRxDeFrames      Counter32,
      prtFrTxDeFrames      Counter32,
      prtFrRxDcrdCongDeFr  Counter32,
      prtFrTxDcrdCongDeFr  Counter32,
      prtFrRxDcrdCongAllFr Counter32,
      prtFrTxDcrdCongAllFr Counter32,
      prtFrRxFecn     Counter32,
      prtFrTxFecn     Counter32,
      prtFrRxBecn     Counter32,
      prtFrTxBecn     Counter32,
      prtFrRxBeViol     Counter32,
      prtFrTxBeViol        Counter32,
      prtFrRxBcViol     Counter32,
      prtFrTxBcViol     Counter32
      }

prtFrStatisSltIdx    OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       notApplicable (255)
       }
      MAX-ACCESS  read-only
      STATUS  current
      DESCRIPTION
      "This attribute indicates a unique  slot  position where
       the module is inserted.
       In the ?004 Unit the entries io6(10)..io12(16) are not valid.
       For stand-alone units this index will be notApplicable (255)."
      ::= { prtFrStatisEntry 1}

prtFrStatisPrtIdx OBJECT-TYPE
      SYNTAX  INTEGER
      {
          exPrt1  (1) ,
          exPrt2  (2) ,
          exPrt3  (3) ,
          exPrt4  (4) ,
          exPrt5  (5) ,
          exPrt6  (6)
       }
      MAX-ACCESS  read-only
      STATUS  current
      DESCRIPTION
      "This attribute indicates a unique  port number."
      ::= { prtFrStatisEntry 2}

prtFrStatisInvIdx OBJECT-TYPE
      SYNTAX  INTEGER
       {
          currentInv (1),
    last       (2)
    }
      MAX-ACCESS  read-only
      STATUS  current
      DESCRIPTION
   "The Interval of 15 min. for which the following statistics
    counters are applicable."
      ::= { prtFrStatisEntry 3}

prtFrTimeElapsed OBJECT-TYPE
      SYNTAX  Integer32 (0..899)
      MAX-ACCESS  read-only
      STATUS  current
      DESCRIPTION
      "The number of seconds that have elapsed  since the
       beginning of the current error-measurement interval.
       This object is applicable mainly for the current interval.
       For other interval:
       - if data is available: value will be 899.
       - if data is not available: value will be 0."
      ::= { prtFrStatisEntry 4 }

prtFrRxTotalFrames OBJECT-TYPE
      SYNTAX   Counter32
      MAX-ACCESS   read-only
      STATUS   current
      DESCRIPTION
      "The total number of frames received by this port during the
       selected interval."
      ::= { prtFrStatisEntry 5 }

prtFrTxTotalFrames OBJECT-TYPE
      SYNTAX   Counter32
      MAX-ACCESS   read-only
      STATUS   current
      DESCRIPTION
      "The total number of frames sent by this port during the
       selected interval."
      ::= { prtFrStatisEntry 6 }

prtFrRxTotalBytes OBJECT-TYPE
      SYNTAX   Counter32
      MAX-ACCESS   read-only
      STATUS   current
      DESCRIPTION
      "The total number of bytes received by this port during the
       selected interval."
      ::= { prtFrStatisEntry 7 }

prtFrTxTotalBytes OBJECT-TYPE
      SYNTAX   Counter32
      MAX-ACCESS   read-only
      STATUS   current
      DESCRIPTION
      "The total number of bytes sent by this port during the
       selected interval."
      ::= { prtFrStatisEntry 8 }

prtFrRxMngFrames OBJECT-TYPE
      SYNTAX   Counter32
      MAX-ACCESS   read-only
      STATUS   current
      DESCRIPTION
      "The management number of frames received by this port
       during the selected interval."
      ::= { prtFrStatisEntry 9 }

prtFrTxMngFrames OBJECT-TYPE
      SYNTAX   Counter32
      MAX-ACCESS   read-only
      STATUS   current
      DESCRIPTION
      "The management number of frames sent by this port during the
       selected interval."
      ::= { prtFrStatisEntry 10 }

prtFrRxDeFrames OBJECT-TYPE
      SYNTAX   Counter32
      MAX-ACCESS   read-only
      STATUS   current
      DESCRIPTION
      "The number of De frames received by this port during the
       selected interval."
      ::= { prtFrStatisEntry 11 }

prtFrTxDeFrames OBJECT-TYPE
      SYNTAX   Counter32
      MAX-ACCESS   read-only
      STATUS   current
      DESCRIPTION
      "The number of De frames sent by this port during the
       selected interval."
      ::= { prtFrStatisEntry 12 }

prtFrRxDcrdCongDeFr OBJECT-TYPE
      SYNTAX   Counter32
      MAX-ACCESS   read-only
      STATUS   current
      DESCRIPTION
      "The number of De frames discarded due to congestion,
       received by this port during the selected interval."
      ::= { prtFrStatisEntry 13 }

prtFrTxDcrdCongDeFr OBJECT-TYPE
      SYNTAX   Counter32
      MAX-ACCESS   read-only
      STATUS   current
      DESCRIPTION
      "The number of De frames discarded due to congestion,
       sent by this port during the selected interval."
      ::= { prtFrStatisEntry 14 }

prtFrRxDcrdCongAllFr OBJECT-TYPE
      SYNTAX   Counter32
      MAX-ACCESS   read-only
      STATUS   current
      DESCRIPTION
      "All the frames discarded due to congestion,
       received by this port during the selected interval."
      ::= { prtFrStatisEntry 15 }

prtFrTxDcrdCongAllFr OBJECT-TYPE
      SYNTAX   Counter32
      MAX-ACCESS   read-only
      STATUS   current
      DESCRIPTION
      "All the frames discarded due to congestion,
       sent by this port during the selected interval."
      ::= { prtFrStatisEntry 16 }

prtFrRxFecn OBJECT-TYPE
      SYNTAX   Counter32
      MAX-ACCESS   read-only
      STATUS   current
      DESCRIPTION
      "Number of frames received by this port during the
       selected interval, indicating forward congestion."
      ::= { prtFrStatisEntry 17 }

prtFrTxFecn OBJECT-TYPE
      SYNTAX   Counter32
      MAX-ACCESS   read-only
      STATUS   current
      DESCRIPTION
      "Number of frames sent by this port during the
       selected interval, indicating forward congestion."
      ::= { prtFrStatisEntry 18 }

prtFrRxBecn OBJECT-TYPE
      SYNTAX   Counter32
      MAX-ACCESS   read-only
      STATUS   current
      DESCRIPTION
      "Number of frames received by this port during the
       selected interval, indicating backward congestion."
      ::= { prtFrStatisEntry 19 }

prtFrTxBecn OBJECT-TYPE
      SYNTAX   Counter32
      MAX-ACCESS   read-only
      STATUS   current
      DESCRIPTION
      "Number of frames sent by this port during the
       selected interval, indicating backward congestion."
      ::= { prtFrStatisEntry 20 }

prtFrRxBeViol OBJECT-TYPE
      SYNTAX   Counter32
      MAX-ACCESS   read-only
      STATUS   current
      DESCRIPTION
      "Number of data frames received by this port during the
       selected interval, exceeding the Burst Excess value."
      ::= { prtFrStatisEntry 21 }

prtFrTxBeViol OBJECT-TYPE
      SYNTAX   Counter32
      MAX-ACCESS   read-only
      STATUS   current
      DESCRIPTION
      "Number of data frames sent by this port during the
       selected interval, exceeding the Burst Excess value."
      ::= { prtFrStatisEntry 22 }

prtFrRxBcViol OBJECT-TYPE
      SYNTAX   Counter32
      MAX-ACCESS   read-only
      STATUS   current
      DESCRIPTION
      "Number of data frames received by this port during the
       selected interval, exceeding the Burst Committed value."
      ::= { prtFrStatisEntry 23 }

prtFrTxBcViol OBJECT-TYPE
      SYNTAX   Counter32
      MAX-ACCESS   read-only
      STATUS   current
      DESCRIPTION
      "Number of data frames sent by this port during the
       selected interval, exceeding the Burst Committed value."
      ::= { prtFrStatisEntry 24 }


--prtCrStatis - Port Statistics for (CR) Cell Relay protocol

prtCrStatisTable  OBJECT-TYPE
     SYNTAX SEQUENCE OF PrtCrStatisEntry
     MAX-ACCESS not-accessible
     STATUS  current
     DESCRIPTION
      "This table is applicable only for an active port running a
       CR protocol ."
  ::= { prtCrStatis 1}

prtCrStatisEntry OBJECT-TYPE
      SYNTAX PrtCrStatisEntry
      MAX-ACCESS not-accessible
      STATUS current
	DESCRIPTION  "An entry in table."
	INDEX {prtCrStatisSltIdx, prtCrStatisPrtIdx, prtCrStatisInvIdx}
      ::= { prtCrStatisTable 1}

PrtCrStatisEntry ::=
      SEQUENCE {
      prtCrStatisSltIdx    INTEGER,
      prtCrStatisPrtIdx    INTEGER,
      prtCrStatisInvIdx    INTEGER,
      prtCrTimeElapsed     Integer32,
      prtCrRxTotalCells    Counter32,
      prtCrTxTotalCells    Counter32,
      prtCrRxDataCells     Counter32,
      prtCrTxDataCells     Counter32
      }

prtCrStatisSltIdx    OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       notApplicable (255)
       }
      MAX-ACCESS  read-only
      STATUS  current
      DESCRIPTION
      "This attribute indicates a unique  slot  position where
       the module is inserted.
       In the ?004 Unit the entries io6(10)..io12(16) are not valid.
       For stand-alone units this index will be notApplicable (255)."
      ::= { prtCrStatisEntry 1}

prtCrStatisPrtIdx OBJECT-TYPE
      SYNTAX  INTEGER
      {
          exPrt1  (1) ,
          exPrt2  (2) ,
          exPrt3  (3) ,
          exPrt4  (4) ,
          exPrt5  (5) ,
          exPrt6  (6)
       }
      MAX-ACCESS  read-only
      STATUS  current
      DESCRIPTION
      "This attribute indicates a unique  port number."
      ::= { prtCrStatisEntry 2}

prtCrStatisInvIdx OBJECT-TYPE
      SYNTAX  INTEGER
       {
          currentInv (1),
    last       (2)
    }
      MAX-ACCESS  read-only
      STATUS  current
      DESCRIPTION
   "The Interval of 15 min. for which the following statistics
    counters are applicable."
      ::= { prtCrStatisEntry 3}

prtCrTimeElapsed OBJECT-TYPE
      SYNTAX  Integer32 (0..899)
      MAX-ACCESS  read-only
      STATUS  current
      DESCRIPTION
      "The number of seconds that have elapsed  since the
       beginning of the current error-measurement interval.
       This object is applicable mainly for the current interval.
       For other interval:
       - if data is available: value will be 899.
       - if data is not available: value will be 0."
      ::= { prtCrStatisEntry 4 }

prtCrRxTotalCells OBJECT-TYPE
      SYNTAX   Counter32
      MAX-ACCESS   read-only
      STATUS   current
      DESCRIPTION
      "The total number of cells received by this port during the
       selected interval."
      ::= { prtCrStatisEntry 5 }

prtCrTxTotalCells OBJECT-TYPE
      SYNTAX   Counter32
      MAX-ACCESS   read-only
      STATUS   current
      DESCRIPTION
      "The total number of cells sent by this port during the
       selected interval."
      ::= { prtCrStatisEntry 6 }

prtCrRxDataCells OBJECT-TYPE
      SYNTAX   Counter32
      MAX-ACCESS   read-only
      STATUS   current
      DESCRIPTION
      "The number of Data Cells received by this port during the
       selected interval."
      ::= { prtCrStatisEntry 7 }

prtCrTxDataCells OBJECT-TYPE
      SYNTAX   Counter32
      MAX-ACCESS   read-only
      STATUS   current
      DESCRIPTION
      "The number of Data Cells sent by this port during the
       selected interval."
      ::= { prtCrStatisEntry 8 }


--prtDlciStatis - Port DLCI Statistics for FR, FR+ and CR protocol

prtDlciStatisTable  OBJECT-TYPE
     SYNTAX SEQUENCE OF PrtDlciStatisEntry
     MAX-ACCESS not-accessible
     STATUS  current
     DESCRIPTION
      "This table is applicable only for an active port running an
       FR, FR+ or CR protocol, with valid DLCIs ."
  ::= { prtDlciStatis 1}

prtDlciStatisEntry OBJECT-TYPE
      SYNTAX PrtDlciStatisEntry
      MAX-ACCESS not-accessible
      STATUS current
	DESCRIPTION  "An entry in table."
	INDEX {prtDlciSltIdx, prtDlciPrtIdx, prtDlciIdx}
      ::= { prtDlciStatisTable 1}

PrtDlciStatisEntry ::=
      SEQUENCE {
      prtDlciSltIdx          INTEGER,
      prtDlciPrtIdx          INTEGER,
      prtDlciIdx             Integer32,
      prtDlciRxDeFrames      Counter32,
      prtDlciTxDeFrames      Counter32,
      prtDlciRxDcrdCongDeFr  Counter32,
      prtDlciTxDcrdCongDeFr  Counter32,
      prtDlciRxDcrdCongAllFr Counter32,
      prtDlciTxDcrdCongAllFr Counter32,
      prtDlciTxFecn       Counter32,
      prtDlciTxBecn       Counter32,
      prtDlciRxBeViol      Counter32,
      prtDlciTxBeViol        Counter32,
      prtDlciRxBcViol      Counter32,
      prtDlciTxBcViol       Counter32
      }

prtDlciSltIdx    OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       notApplicable (255)
       }
      MAX-ACCESS  read-only
      STATUS  current
      DESCRIPTION
      "This attribute indicates a unique  slot  position where
       the module is inserted.
       In the ?004 Unit the entries io6(10)..io12(16) are not valid.
       For stand-alone units this index will be notApplicable (255)."
      ::= { prtDlciStatisEntry 1}

prtDlciPrtIdx OBJECT-TYPE
      SYNTAX  INTEGER
      {
          exPrt1  (1) ,
          exPrt2  (2) ,
          exPrt3  (3) ,
          exPrt4  (4) ,
          exPrt5  (5) ,
          exPrt6  (6)
       }
      MAX-ACCESS  read-only
      STATUS  current
      DESCRIPTION
      "This attribute indicates a unique  port number."
      ::= { prtDlciStatisEntry 2}

prtDlciIdx OBJECT-TYPE
      SYNTAX  Integer32 (1..991)
      MAX-ACCESS  read-only
      STATUS  current
      DESCRIPTION
      "This attribute indicates a unique DLCI index for each valid
       DLCI (16..991). "
      ::= { prtDlciStatisEntry 3}

prtDlciRxDeFrames OBJECT-TYPE
      SYNTAX   Counter32
      MAX-ACCESS   read-only
      STATUS   current
      DESCRIPTION
      "The number of De frames received by this DLCI."
      ::= { prtDlciStatisEntry 4 }

prtDlciTxDeFrames OBJECT-TYPE
      SYNTAX   Counter32
      MAX-ACCESS   read-only
      STATUS   current
      DESCRIPTION
      "The number of De frames sent by this DLCI."
      ::= { prtDlciStatisEntry 5 }

prtDlciRxDcrdCongDeFr OBJECT-TYPE
      SYNTAX   Counter32
      MAX-ACCESS   read-only
      STATUS   current
      DESCRIPTION
      "The number of De frames discarded due to congestion,
       received by this DLCI."
      ::= { prtDlciStatisEntry 6 }

prtDlciTxDcrdCongDeFr OBJECT-TYPE
      SYNTAX   Counter32
      MAX-ACCESS   read-only
      STATUS   current
      DESCRIPTION
      "The number of De frames discarded due to congestion,
       sent by this DLCI."
      ::= { prtDlciStatisEntry 7 }

prtDlciRxDcrdCongAllFr OBJECT-TYPE
      SYNTAX   Counter32
      MAX-ACCESS   read-only
      STATUS   current
      DESCRIPTION
      "All the frames discarded due to congestion,
       received by this DLCI."
      ::= { prtDlciStatisEntry 8 }

prtDlciTxDcrdCongAllFr OBJECT-TYPE
      SYNTAX   Counter32
      MAX-ACCESS   read-only
      STATUS   current
      DESCRIPTION
      "All the frames discarded due to congestion,
       sent by this DLCI."
      ::= { prtDlciStatisEntry 9 }

prtDlciTxFecn OBJECT-TYPE
      SYNTAX   Counter32
      MAX-ACCESS   read-only
      STATUS   current
      DESCRIPTION
      "Number of frames sent by this DLCI, indicating forward
       congestion."
      ::= { prtDlciStatisEntry 10 }

prtDlciTxBecn OBJECT-TYPE
      SYNTAX   Counter32
      MAX-ACCESS   read-only
      STATUS   current
      DESCRIPTION
      "Number of frames sent by this DLCI, indicating backward
       congestion."
      ::= { prtDlciStatisEntry 11 }

prtDlciRxBeViol OBJECT-TYPE
      SYNTAX   Counter32
      MAX-ACCESS   read-only
      STATUS   current
      DESCRIPTION
      "Number of data frames received by this DLCI, exceeding the
       Burst Excess value."
      ::= { prtDlciStatisEntry 12 }

prtDlciTxBeViol OBJECT-TYPE
      SYNTAX   Counter32
      MAX-ACCESS   read-only
      STATUS   current
      DESCRIPTION
      "Number of data frames sent by this DLCI, exceeding the Burst
       Excess value."
      ::= { prtDlciStatisEntry 13 }

prtDlciRxBcViol OBJECT-TYPE
      SYNTAX   Counter32
      MAX-ACCESS   read-only
      STATUS   current
      DESCRIPTION
      "Number of data frames received by this DLCI, exceeding the
       Burst Committed value."
      ::= { prtDlciStatisEntry 14 }

prtDlciTxBcViol OBJECT-TYPE
      SYNTAX   Counter32
      MAX-ACCESS   read-only
      STATUS   current
      DESCRIPTION
      "Number of data frames sent by this DLCI, exceeding the Burst
       Committed value."
      ::= { prtDlciStatisEntry 15 }


--prtT1 Last FDL Message Table - Statistics

prtT1FdlMsgTable  OBJECT-TYPE
     SYNTAX SEQUENCE OF PrtT1FdlMsgEntry
     MAX-ACCESS not-accessible
     STATUS  current
     DESCRIPTION
      "This table is applicable for a T1 interface with 'esf'
       LineType ."
  ::= { prtT1Statis 1}

prtT1FdlMsgEntry OBJECT-TYPE
      SYNTAX PrtT1FdlMsgEntry
      MAX-ACCESS not-accessible
      STATUS current
	DESCRIPTION  "An entry in table."
	INDEX {prtT1FdlMsgSltIdx, prtT1FdlMsgPrtIdx, prtT1FdlMsgFdlTxRx}
      ::= { prtT1FdlMsgTable 1}

PrtT1FdlMsgEntry ::=
      SEQUENCE {
      prtT1FdlMsgSltIdx    INTEGER,
      prtT1FdlMsgPrtIdx    INTEGER,
      prtT1FdlMsgFdlTxRx   INTEGER,
      prtT1FdlMsg          OCTET STRING
      }

prtT1FdlMsgSltIdx    OBJECT-TYPE
      SYNTAX  INTEGER
       {
       io1   (5),
       io2   (6),
       io3   (7),
       io4   (8),
       io5   (9),
       io6  (10),
       io7  (11),
       io8  (12),
       io9  (13),
       io10 (14),
       io11 (15),
       io12 (16)
       }
      MAX-ACCESS  read-only
      STATUS  current
      DESCRIPTION
      "This attribute indicates a unique  slot  position where
       the module is inserted.
       In the ?004 Unit the entries io6(10)..io12(16) are not valid."
      ::= { prtT1FdlMsgEntry 1}

prtT1FdlMsgPrtIdx OBJECT-TYPE
      SYNTAX  INTEGER
       {
       exPrt1    (1)
       }
      MAX-ACCESS  read-only
      STATUS  current
      DESCRIPTION
      "This attribute indicates a unique  port number.
       MTML-1/T1 modules have just one external interface."
      ::= { prtT1FdlMsgEntry 2}

prtT1FdlMsgFdlTxRx OBJECT-TYPE
      SYNTAX  INTEGER
       {
          tx    (1),
          rx    (2)
    }
      MAX-ACCESS  read-only
      STATUS  current
      DESCRIPTION
   "The Fdl tx/rx reference of the Fdl message."
      ::= { prtT1FdlMsgEntry 3}


prtT1FdlMsg  OBJECT-TYPE
   SYNTAX  OCTET STRING
      MAX-ACCESS  read-only
      STATUS  current
      DESCRIPTION
      "FDL message."
      ::= { prtT1FdlMsgEntry 4}


--
-- Extension of the Time Slot Config Table of ML ports
--
-- Time Slot is split to 8 Bits


prtExTsSplitTable OBJECT-TYPE
     SYNTAX SEQUENCE OF PrtExTsSplitEntry
     MAX-ACCESS not-accessible
     STATUS  current
     DESCRIPTION
      "The write operation into the Table Objects is valid only
       to the TmpCnfg entry, except prtExTsBitTest that will be
       written directly to the Active Configuration."
     ::= {cnfgPrtGen 1}

prtExTsSplitEntry OBJECT-TYPE
      SYNTAX PrtExTsSplitEntry
      MAX-ACCESS not-accessible
      STATUS current
	DESCRIPTION  "An entry in table."
	INDEX {prtExTsCnfgIdx, prtExTsSltIdx, prtExTsPrtIdx,
             prtExTsIdx, prtExTsBit}
      ::= { prtExTsSplitTable 1}

PrtExTsSplitEntry ::=
      SEQUENCE {
      prtExTsCnfgIdx        Integer32,
      prtExTsSltIdx         INTEGER,
      prtExTsPrtIdx         Integer32,
      prtExTsIdx            Integer32,
      prtExTsBit            Integer32,
      prtExTsIConSlot       INTEGER,
      prtExTsIConPrt        Integer32,
	  prtExTsBitTest        INTEGER,
	  prtExTsTxSignaling    OCTET STRING,
	  prtExTsRxSignaling    OCTET STRING
      }

prtExTsCnfgIdx OBJECT-TYPE
      SYNTAX  Integer32  (1..255)
      MAX-ACCESS  read-only
      STATUS  current
      DESCRIPTION
      "This attribute indicates the Idx of the Cnfg (1..100) being
       accessed.
       Idx 255 relates to the TmpCnfg. "
      ::= { prtExTsSplitEntry 1}

prtExTsSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16),
          notApplicable (255)
        }
      MAX-ACCESS  read-only
      STATUS  current
      DESCRIPTION
      "This attribute indicates a unique  slot  position where
       the card is inserted.
       In the ?004 Unit the entries io6(10)..io12(16) are not valid.
       notApplicable - for stand-alone units."
      ::= { prtExTsSplitEntry 2}

prtExTsPrtIdx OBJECT-TYPE
      SYNTAX  Integer32
--  For MP:
--    {
--      exPrt1    (1),
--     inPrt1  (101)
--     }
      MAX-ACCESS  read-only
      STATUS  current
      DESCRIPTION
      "This attribute indicates a unique  port number.
       Most ML cards have only one external interface.
       inPrt1 - for MTML-H/E1 cards.
       For other products' index see their specification."
      ::= { prtExTsSplitEntry 3}

prtExTsIdx OBJECT-TYPE
      SYNTAX  Integer32
      MAX-ACCESS  read-only
      STATUS  current
      DESCRIPTION
      "This attribute indicates a unique time slot  position.
       The valid time slots are:
       1..24 for T1 Card and
       1..31 for E1 interface.
       In G732S-E1 lines, time slot 16 is not valid for data,
       it is dedicated to multiframe synchronization bits
       and voice signaling."
      ::= { prtExTsSplitEntry 4}

prtExTsBit OBJECT-TYPE
      SYNTAX  Integer32 (1..8)
      MAX-ACCESS  read-only
      STATUS  current
      DESCRIPTION
      "This attribute indicates a unique Bit within the time slot.
       The valid Bits are: 1..8."
      ::= { prtExTsSplitEntry 5}

prtExTsIConSlot OBJECT-TYPE
      SYNTAX  INTEGER
       {
       noConnect (2),
          io1       (5),
          io2       (6),
          io3       (7),
          io4       (8),
          io5       (9),
          io6      (10),
          io7      (11),
          io8      (12),
          io9      (13),
          io10     (14),
          io11     (15),
          io12     (16),
    notApplicable (255)
       }
      MAX-ACCESS  read-write
      STATUS  current
      DESCRIPTION
      "This attribute indicates whether the specified time slot is
       connected/routed internally in the Agent and to which card
       it is connected.
       In the ?004 Unit the entries io6(10)..io12(16) are not valid.
       notApplicable - for stand-alone units."
      ::= {prtExTsSplitEntry 6}

prtExTsIConPrt OBJECT-TYPE
      SYNTAX  Integer32
--    For MP:
--       {
--       exPrt1    (1) ,
--       exPrt2    (2) ,
--       exPrt3    (3) ,
--       exPrt4    (4) ,
--       exPrt5    (5) ,
--       exPrt6    (6) ,
--       exPrt7    (7) ,
--       exPrt8    (8) ,
--       exPrt9    (9) ,
--       exPrt10  (10) ,
--       exPrt11  (11) ,
--       exPrt12  (12) ,
--
--        noConnect (100),
--
--       inPrt1  (101) ,
--       inPrt2  (102) ,
--       inPrt3  (103) ,
--       inPrt4  (104) ,
--       inPrt5  (105) ,
--       inPrt6  (106) ,
--       inPrt7  (107) ,
--       inPrt8  (108) ,
--       inPrt9  (109) ,
--       inPrt10 (110) ,
--    inPrt11 (111) ,
--    inPrt12 (112)
--       }
      MAX-ACCESS  read-write
      STATUS  current
      DESCRIPTION
      "This attribute indicates the internally (In Mux)
       connected/routed port.
       For other products' index see their specification."
      ::= {prtExTsSplitEntry 7}

prtExTsBitTest OBJECT-TYPE
      SYNTAX  INTEGER
     {
       none                    (1),
       remoteBert              (8),
       localBert               (30),
       notApplicable           (255)
        }
      MAX-ACCESS  read-write
      STATUS  current
      DESCRIPTION
      "This attribute indicates a test to be activated on the selected Bit.
	   It is applicable only when prtExPh1MlTsTest=split(254).
	   none - no test is applied for the selected Bit.
       notApplicable - when prtExPh1MlTsTest is NOT split(254)."
      ::= { prtExTsSplitEntry 8}

prtExTsTxSignaling OBJECT-TYPE
        SYNTAX OCTET STRING
        MAX-ACCESS read-only
        STATUS current
        DESCRIPTION
        "Tx Signaling per TS, for TSs having TS Type=Voice
         (agnTsType=voice(2)). 
         It defines what is sent for the selected TS for A,B,C,D Signaling Bits.
         Bit 1= LSB
         Bit 8= MSB 
        Bit  1-2 = A Signaling Bit:  00='0'  ; 01='1' ; 10=not used ; 11=NA
        Bit  3-4 = B Signaling Bit:  00='0'  ; 01='1' ; 10=not used ; 11=NA
        Bit  5-6 = C Signaling Bit:  00='0'  ; 01='1' ; 10=not used ; 11=NA        
        Bit  7-8 = D Signaling Bit:  00='0'  ; 01='1' ; 10=not used ; 11=NA"
        ::= { prtExTsSplitEntry 9}

prtExTsRxSignaling OBJECT-TYPE
        SYNTAX OCTET STRING
        MAX-ACCESS read-only
        STATUS current
        DESCRIPTION
        "Tx Signaling per TS, for TSs having TS Type=Voice
         (agnTsType=voice(2)). 
         It defines what is sent for the selected TS for A,B,C,D Signaling Bits.
         Bit 1= LSB
         Bit 8= MSB 
        Bit  1-2 = A Signaling Bit:  00='0'  ; 01='1' ; 10=not used ; 11=NA
        Bit  3-4 = B Signaling Bit:  00='0'  ; 01='1' ; 10=not used ; 11=NA
        Bit  5-6 = C Signaling Bit:  00='0'  ; 01='1' ; 10=not used ; 11=NA        
        Bit  7-8 = D Signaling Bit:  00='0'  ; 01='1' ; 10=not used ; 11=NA"
        ::= { prtExTsSplitEntry 10}

prtCnfgAgenda OBJECT IDENTIFIER ::= {cnfgPrtGen 2}

prtAgendaBehaviourTable OBJECT-TYPE
     SYNTAX SEQUENCE OF PrtAgendaBehaviourEntry
     MAX-ACCESS not-accessible
     STATUS  current
     DESCRIPTION
      "The write operation into the Table Objects is valid only
       to the TmpCnfg entry."
     ::= { prtCnfgAgenda 1}

prtAgendaBehaviourEntry OBJECT-TYPE
      SYNTAX PrtAgendaBehaviourEntry
      MAX-ACCESS not-accessible
      STATUS current
	DESCRIPTION  "An entry in table."
	INDEX {prtAgendaBehaviourCnfgIdx, prtAgendaBehaviourSltIdx,
             prtAgendaBehaviourPrtIdx }
      ::= { prtAgendaBehaviourTable 1}

PrtAgendaBehaviourEntry ::=
      SEQUENCE {
      prtAgendaBehaviourCnfgIdx Integer32,
      prtAgendaBehaviourSltIdx  Integer32,
      prtAgendaBehaviourPrtIdx  Integer32,
      prtAgendaBehaviourOnOff   INTEGER
}

prtAgendaBehaviourCnfgIdx OBJECT-TYPE
      SYNTAX  Integer32  (1..255)
      MAX-ACCESS  read-only
      STATUS  current
      DESCRIPTION
      "This attribute indicates the Idx of the Cnfg (1..100) being
       accessed.
       Idx 255 relates to the TmpCnfg. "
      ::= { prtAgendaBehaviourEntry 1}

prtAgendaBehaviourSltIdx  OBJECT-TYPE
      SYNTAX  Integer32
      MAX-ACCESS  read-only
      STATUS  current
      DESCRIPTION
      "This parameter should be:
 - slot number for MX3000
 - 255 = N/A  for MX300/30. "
      ::= { prtAgendaBehaviourEntry 2 }

prtAgendaBehaviourPrtIdx  OBJECT-TYPE
      SYNTAX  Integer32
      MAX-ACCESS  read-only
      STATUS  current
      DESCRIPTION
      "This parameter should be:
 - port number for MX300/30
 - 100 = N/A  for MX3000. "
      ::= { prtAgendaBehaviourEntry 3 }

prtAgendaBehaviourOnOff   OBJECT-TYPE
      SYNTAX  INTEGER
              {
                notApplicable(1),
                off(2),
                on (3)
              }
      MAX-ACCESS  read-write
      STATUS  current
      DESCRIPTION
      "Setting this command to on(3) enables the agenda function
       at module (3000) or port (300/30) level."
      DEFVAL { off }
      ::= { prtAgendaBehaviourEntry 4 }

prtCnfgAgendaTable OBJECT-TYPE
     SYNTAX SEQUENCE OF PrtCnfgAgendaEntry
     MAX-ACCESS not-accessible
     STATUS  current
     DESCRIPTION
      "This table allows the user to schedule the time a session
        is active per week basis."
     ::= { prtCnfgAgenda 2}

prtCnfgAgendaEntry OBJECT-TYPE
      SYNTAX PrtCnfgAgendaEntry
      MAX-ACCESS not-accessible
      STATUS current
	DESCRIPTION  "An entry in table."
	INDEX { prtCnfgAgendaCnfgIdx, prtCnfgAgendaSltIdx,
 prtCnfgAgendaPrtIdx, prtCnfgAgendaDayIdx, prtCnfgAgendaSesId }
      ::= { prtCnfgAgendaTable 1}

PrtCnfgAgendaEntry ::=
      SEQUENCE {
      prtCnfgAgendaCnfgIdx        Integer32,
      prtCnfgAgendaSltIdx         Integer32,
      prtCnfgAgendaPrtIdx         Integer32,
      prtCnfgAgendaDayIdx         INTEGER,
      prtCnfgAgendaSesId          Integer32,
      prtCnfgAgendaFrom           Integer32,
      prtCnfgAgendaTo             Integer32 
	}

prtCnfgAgendaCnfgIdx OBJECT-TYPE
      SYNTAX  Integer32  (1..255)
      MAX-ACCESS  read-only
      STATUS  current
      DESCRIPTION
      "This attribute indicates the Idx of the Cnfg (1..100) being
       accessed.
       Idx 255 relates to the TmpCnfg. "
      ::= { prtCnfgAgendaEntry 1}

prtCnfgAgendaSltIdx OBJECT-TYPE
      SYNTAX  Integer32
      MAX-ACCESS  read-only
      STATUS  current
      DESCRIPTION
      "This attribute is equal to:
 -slot number for MX3000
 -255 = N/A for MX300/30"
      ::= { prtCnfgAgendaEntry 2}

prtCnfgAgendaPrtIdx OBJECT-TYPE
      SYNTAX  Integer32
      MAX-ACCESS  read-only
      STATUS  current
      DESCRIPTION
      "This attribute is equal to:
       - port number for MX300/30
	   - port number for MX3000. For example 1-4 in MHS-4 cards.
       - 100 = N/A for MX3000 when not used."
      ::= { prtCnfgAgendaEntry 3}


prtCnfgAgendaDayIdx OBJECT-TYPE
      SYNTAX  INTEGER {
                monday   (1),
                tuesday  (2),
                wednesday(3),
                thursday (4),
                friday   (5),
                saturday (6),
                sunday   (7)
        }
      MAX-ACCESS  read-only
      STATUS  current
      DESCRIPTION
      "This attribute for which day of the week this row applies."
      ::= { prtCnfgAgendaEntry 4 }


prtCnfgAgendaSesId OBJECT-TYPE
      SYNTAX  Integer32 (1..4)
      MAX-ACCESS  read-only
      STATUS  current
      DESCRIPTION
      "The user may define 4 different active intervals per day."
      ::= { prtCnfgAgendaEntry  5 }

prtCnfgAgendaFrom OBJECT-TYPE
      SYNTAX  Integer32 (0..86400)
      MAX-ACCESS  read-write
      STATUS  current
      DESCRIPTION
      "Start from time interval in seconds."
      DEFVAL {86400}
      ::= { prtCnfgAgendaEntry 6 }

prtCnfgAgendaTo OBJECT-TYPE
      SYNTAX  Integer32 (0..86400)
      MAX-ACCESS  read-write
      STATUS  current
      DESCRIPTION
      "To time interval in seconds."
      DEFVAL {86400}
      ::= { prtCnfgAgendaEntry 7 }

-- General Port Configuration parameters

prtGenCnfgTable OBJECT-TYPE
     SYNTAX SEQUENCE OF PrtGenCnfgEntry
     MAX-ACCESS not-accessible
     STATUS  current
     DESCRIPTION
      "This table allows the user to configure general
       port parameters."
     ::= {cnfgPrtGen 3}

prtGenCnfgEntry OBJECT-TYPE
      SYNTAX PrtGenCnfgEntry
      MAX-ACCESS not-accessible
      STATUS current
	DESCRIPTION  "An entry in table."
	INDEX { prtGenCnfgIdx, prtGenCnfgSltIdx, prtGenCnfgPrtIdx }
      ::= { prtGenCnfgTable 1}

PrtGenCnfgEntry ::=
      SEQUENCE {
      prtGenCnfgIdx            Integer32,
      prtGenCnfgSltIdx         INTEGER,
      prtGenCnfgPrtIdx         Integer32,
      prtGenCnfgLinkToSlot     INTEGER,
      prtGenCnfgLinkToPort     Integer32,
	  prtGenCnfgPortId         Integer32 
	}

prtGenCnfgIdx OBJECT-TYPE
      SYNTAX  Integer32  (1..255)
      MAX-ACCESS  read-only
      STATUS  current
      DESCRIPTION
      "This attribute indicates the Idx of the Cnfg (1..100) being
       accessed.
       Idx 255 relates to the TmpCnfg.
       The write operation is valid only to the TmpCnfg."
      ::= { prtGenCnfgEntry 1}

prtGenCnfgSltIdx OBJECT-TYPE
      SYNTAX  INTEGER
   {   io1   (5),
       io2   (6),
       io3   (7),
       io4   (8),
       io5   (9),
       io6  (10),
       io7  (11),
       io8  (12),
       io9  (13),
       io10 (14),
       io11 (15),
       io12 (16),
    notApplicable (255)
   }
      MAX-ACCESS  read-only
      STATUS  current
      DESCRIPTION
      "This attribute indicates a unique  slot  position where
       the card is inserted."
      ::= { prtGenCnfgEntry 2}

prtGenCnfgPrtIdx OBJECT-TYPE
      SYNTAX  Integer32
      MAX-ACCESS  read-only
      STATUS  current
      DESCRIPTION
      "This attribute indicates a unique external or internal port number.
     For MP:
     exPrt1    (1) .. exPrt16  (16) ,
     notApplicable(100),
     inPrt1  (101) .. inPrt48 (148) "
      ::= { prtGenCnfgEntry 3}

prtGenCnfgLinkToSlot OBJECT-TYPE
      SYNTAX  INTEGER
       {
       io1   (5),
       io2   (6),
       io3   (7),
       io4   (8),
       io5   (9),
       io6  (10),
       io7  (11),
       io8  (12),
       io9  (13),
       io10 (14),
       io11 (15),
       io12 (16),
    notApplicable (255)
       }
      MAX-ACCESS  read-write
      STATUS  current
      DESCRIPTION
      "This attribute indicates the slot of the ML card to which
       the IO port is mapped."
      ::= { prtGenCnfgEntry 4}

prtGenCnfgLinkToPort OBJECT-TYPE
      SYNTAX  Integer32
      MAX-ACCESS  read-write
      STATUS  current
      DESCRIPTION
      "This attribute indicates the port in the prtGenCnfgLinkToSlot of
       the ML card to which the IO port is mapped.
    For MP:
     exPrt1    (1) ,
     exPrt2    (2) ,
     exPrt3    (3) ,
     exPrt4    (4) ,
     inPrt1  (101) ,
     inPrt2  (102) ,
     inPrt3  (103) ,
     inPrt4  (104) ,
     notApplicable (255)"
      ::= { prtGenCnfgEntry 5}

prtGenCnfgPortId OBJECT-TYPE
      SYNTAX  Integer32 (0..16777215)
      MAX-ACCESS  read-write
      STATUS  current
      DESCRIPTION
      "IO Port Id for V5.1 use.
       This object is applicable only for part of the PSTN and ISDN IO ports.       
       Generally, 0 is a valid value.
       Nevertheless, for ports that do not support this object, the value
       will be: notApplicable= 0"
      ::= { prtGenCnfgEntry 6}

--
-- Compressed information.
--
-- Specially for RadView management station
--
prtCmprTable  OBJECT-TYPE
      SYNTAX SEQUENCE OF PrtCmprEntry
      MAX-ACCESS not-accessible
      STATUS current
	DESCRIPTION  "A table."
	::=  { cmprPrtGen 1 }

prtCmprEntry OBJECT-TYPE
      SYNTAX PrtCmprEntry
      MAX-ACCESS not-accessible
      STATUS current
	DESCRIPTION  "An entry in table."
	INDEX {prtCmprTypIdx, prtCmprCnfgIdx,prtCmprVersion,prtCmprSltIdx,prtCmprPrtIdx}
      ::= {prtCmprTable  1}

PrtCmprEntry ::=
      SEQUENCE {
     prtCmprTypIdx       Integer32,
     prtCmprCnfgIdx      Integer32,
     prtCmprVersion      Integer32,
     prtCmprSltIdx       INTEGER,
     prtCmprPrtIdx       Integer32,
     prtCmprObj          OCTET STRING,
	 prtCmprStatisticObj OCTET STRING
      }

prtCmprTypIdx OBJECT-TYPE
      SYNTAX  Integer32
      MAX-ACCESS  read-only
      STATUS  current
      DESCRIPTION
      "This attribute indicates the Type of the Compressed being
       referred."
      ::= { prtCmprEntry 1}

prtCmprCnfgIdx OBJECT-TYPE
      SYNTAX  Integer32
      MAX-ACCESS  read-only
      STATUS  current
      DESCRIPTION
      "This attribute indicates the configuration to which the
       Compressed information is  related."
      ::= { prtCmprEntry 2}

prtCmprVersion OBJECT-TYPE
      SYNTAX  Integer32
      MAX-ACCESS  read-only
      STATUS  current
      DESCRIPTION
      "This attribute indicates the version of the internal format of
       the Compressed data"
      ::= { prtCmprEntry 3}

prtCmprSltIdx  OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16),
    notApplicable (255)
       }
      MAX-ACCESS  read-only
      STATUS  current
      DESCRIPTION
      "This attribute indicates a unique number of the slot position
       where the card is inserted.
       In the ?004 Unit the entries psB(2),clB(4),io6(10)..io(16)
       are not valid."
      ::= { prtCmprEntry 4}

prtCmprPrtIdx  OBJECT-TYPE
      SYNTAX  Integer32
      MAX-ACCESS  read-only
      STATUS  current
      DESCRIPTION
      "This attribute indicates a unique identifier of  the port
       the compressed information relates to.
       Valid values: exPrt1    (1) .. exPrt16  (16) ,
                     inPrt1  (101) .. inPrt48 (148)."
      ::= { prtCmprEntry 5}

prtCmprObj OBJECT-TYPE
      SYNTAX  OCTET STRING
      MAX-ACCESS  read-write
      STATUS  current
      DESCRIPTION
      "This attribute is the compressed information itself."
      ::= { prtCmprEntry 6}

prtCmprStatisticObj OBJECT-TYPE
      SYNTAX  OCTET STRING
      MAX-ACCESS  read-only
      STATUS  current
      DESCRIPTION
      "This attribute is the compressed statistics information itself."
      ::= { prtCmprEntry 7}


-- Compressed Dlci table in the Port level
-- The only way of reading this table is by the command 'GET NEXT'

prtDlciCmprTable  OBJECT-TYPE
      SYNTAX SEQUENCE OF PrtDlciCmprEntry
      MAX-ACCESS not-accessible
      STATUS current
	DESCRIPTION  "A table."
	::=  { cmprPrtGen 2 }

prtDlciCmprEntry OBJECT-TYPE
      SYNTAX PrtDlciCmprEntry
      MAX-ACCESS not-accessible
      STATUS current
	DESCRIPTION  "An entry in table."
	INDEX {prtDlciCmprCnfgIdx,prtDlciCmprVersion,
             prtDlciCmprSltIdx,prtDlciCmprPrtIdx,prtDlciCmprDlciIdx}
      ::= {prtDlciCmprTable  1}

PrtDlciCmprEntry ::=
      SEQUENCE {
     prtDlciCmprCnfgIdx       Integer32,
     prtDlciCmprVersion    Integer32,
     prtDlciCmprSltIdx    INTEGER,
     prtDlciCmprPrtIdx    INTEGER,
     prtDlciCmprDlciIdx       Integer32,
     prtDlciCmprObj          OCTET STRING
      }

prtDlciCmprCnfgIdx OBJECT-TYPE
      SYNTAX  Integer32
      MAX-ACCESS  read-only
      STATUS  current
      DESCRIPTION
      "This attribute indicates the configuration to which the
       Compressed information is  related."
      ::= { prtDlciCmprEntry 1}

prtDlciCmprVersion OBJECT-TYPE
      SYNTAX  Integer32
      MAX-ACCESS  read-only
      STATUS  current
      DESCRIPTION
      "This attribute indicates the version of the internal format of
       the Compressed data"
      ::= { prtDlciCmprEntry 2}

prtDlciCmprSltIdx  OBJECT-TYPE
     SYNTAX  INTEGER
         {
         io1   (5),
         io2   (6),
         io3   (7),
         io4   (8),
         io5   (9),
         io6  (10),
         io7  (11),
         io8  (12),
         io9  (13),
         io10 (14),
         io11 (15),
         io12 (16),
      notApplicable (255)
         }
     MAX-ACCESS  read-only
     STATUS  current
     DESCRIPTION
     "This attribute indicates a unique number of the slot position
      where the module is inserted.
      In the ?004 Unit the entries psB(2),clB(4),io6(10)..io(16)
      are not valid."
     ::= { prtDlciCmprEntry 3}

prtDlciCmprPrtIdx  OBJECT-TYPE
     SYNTAX  INTEGER
     {
    exPrt1    (1) ,
    exPrt2    (2) ,
    exPrt3    (3) ,
    exPrt4    (4) ,
    exPrt5    (5) ,
    exPrt6    (6) ,
    exPrt7    (7) ,
    exPrt8    (8) ,
    exPrt9    (9) ,
    exPrt10  (10) ,
    inPrt1  (101) ,
    inPrt2  (102) ,
    inPrt3  (103) ,
    inPrt4  (104) ,
    inPrt5  (105) ,
    inPrt6  (106) ,
    inPrt7  (107) ,
    inPrt8  (108) ,
    inPrt9  (109) ,
    inPrt10 (110) ,
 inPrt11 (111) ,
 inPrt12 (112)
     }
     MAX-ACCESS  read-only
     STATUS  current
     DESCRIPTION
     "This attribute indicates a unique identifier of  the port
      the compressed information relates to.
      All the values are valid."
     ::= { prtDlciCmprEntry 4}

prtDlciCmprDlciIdx  OBJECT-TYPE
      SYNTAX  Integer32
      MAX-ACCESS  read-only
      STATUS  current
      DESCRIPTION
      "This attribute indicates a unique identifier of  the Dlci
       the compressed information relates to.
       The values are between 16 - 991."
      ::= { prtDlciCmprEntry 5}

prtDlciCmprObj OBJECT-TYPE
      SYNTAX  OCTET STRING
      MAX-ACCESS  read-write
      STATUS  current
      DESCRIPTION
      "This attribute is the compressed information itself."
      ::= { prtDlciCmprEntry 6}


-- Compressed Alarm table in the Port level
-- The only way of reading this table is by the command 'GET NEXT'

prtAlarmsCmprTable  OBJECT-TYPE
      SYNTAX SEQUENCE OF PrtAlarmsCmprEntry
      MAX-ACCESS not-accessible
      STATUS current
	DESCRIPTION  "A table."
	::=  {cmprPrtGen 3}

prtAlarmsCmprEntry OBJECT-TYPE
      SYNTAX PrtAlarmsCmprEntry
      MAX-ACCESS not-accessible
      STATUS current
	DESCRIPTION  "An entry in table."
	INDEX {prtAlarmsCmprVersion,prtAlarmsCmprAlarmSlot,
             prtAlarmsCmprAlarmPort,prtAlarmsCmprAlarmIdx}
      ::= {prtAlarmsCmprTable  1}

PrtAlarmsCmprEntry ::=
      SEQUENCE {
     prtAlarmsCmprVersion      Integer32,
     prtAlarmsCmprAlarmSlot    Integer32,
     prtAlarmsCmprAlarmPort    Integer32,
     prtAlarmsCmprAlarmIdx     Integer32,
     prtAlarmsCmprObj          OCTET STRING
      }

prtAlarmsCmprVersion OBJECT-TYPE
      SYNTAX  Integer32
      MAX-ACCESS  read-only
      STATUS  current
      DESCRIPTION
      "This attribute indicates the version of the internal format of
       the Compressed data"
      ::= { prtAlarmsCmprEntry 1}

prtAlarmsCmprAlarmSlot  OBJECT-TYPE
      SYNTAX  Integer32
      MAX-ACCESS  read-only
      STATUS  current
      DESCRIPTION
      "This attribute indicates the  desired slot position.
       In the ?004 Unit the entries PsB(2),ClB(4),io6(10)..io(16)
       are not valid.
       For Stand-alone units, notApplicable(255) will appear."
      ::= { prtAlarmsCmprEntry 2}

prtAlarmsCmprAlarmPort  OBJECT-TYPE
      SYNTAX  Integer32
      MAX-ACCESS  read-only
      STATUS  current
      DESCRIPTION
      "This attribute indicates a unique identifier of  the port
       the alarm applies to.
       All the values are valid. No alarms exist for a non-existing
       port. IP Bundles are considered a port too, for this matter."
      ::= { prtAlarmsCmprEntry 3}

prtAlarmsCmprAlarmIdx  OBJECT-TYPE
      SYNTAX  Integer32
      MAX-ACCESS  read-only
      STATUS  current
      DESCRIPTION
      "A unique number to identify an entry in the alarm status table
       of the agent."
      ::= { prtAlarmsCmprEntry 4}

prtAlarmsCmprObj OBJECT-TYPE
      SYNTAX  OCTET STRING
      MAX-ACCESS  read-only
      STATUS  current
      DESCRIPTION
      "This attribute is the compressed information itself."
      ::= { prtAlarmsCmprEntry 5}




--
-- Specific port status for each module Type
-- *****************************************
--

-- Megaplex?000/?004 port specific status for HS(TDM) modules
-- HS-2,HS-3,HS-Q, HS-6, HS-12
prtSExHsfStatTable OBJECT-TYPE
      SYNTAX SEQUENCE OF PrtSExHsfStatEntry
      MAX-ACCESS not-accessible
      STATUS current
	DESCRIPTION  "A table."
	::=  {statPrtMux 6}

prtSExHsfStatEntry OBJECT-TYPE
      SYNTAX PrtSExHsfStatEntry
      MAX-ACCESS not-accessible
      STATUS current
	DESCRIPTION  "An entry in table."
	INDEX {prtSExHsfSltIdx, prtSExHsfPrtIdx }
      ::= {prtSExHsfStatTable 1}

PrtSExHsfStatEntry ::=
      SEQUENCE {
      prtSExHsfSltIdx           INTEGER,
      prtSExHsfPrtIdx           INTEGER,
      prtSExHsfInterfaceTyp     INTEGER,
      prtSExHsfRts              INTEGER
      }


prtSExHsfSltIdx OBJECT-TYPE
      SYNTAX  INTEGER
        {
       io1   (5),
       io2   (6),
       io3   (7),
       io4   (8),
       io5   (9),
       io6  (10),
       io7  (11),
       io8  (12),
       io9  (13),
       io10 (14),
       io11 (15),
       io12 (16)
     }
      MAX-ACCESS  read-only
      STATUS  current
      DESCRIPTION
      "This attribute indicates a unique  slot  position where
       the card is inserted.
       In the ?004 Unit the entries io6(10)..io16) are not valid."
      ::= { prtSExHsfStatEntry 1}

prtSExHsfPrtIdx OBJECT-TYPE
      SYNTAX  INTEGER
      {
      exPrt1    (1) ,
      exPrt2    (2) ,
      exPrt3    (3) ,
      exPrt4    (4) ,
      exPrt5    (5) ,
      exPrt6    (6) ,
      exPrt7    (7) ,
      exPrt8    (8) ,
      exPrt9    (9) ,
      exPrt10  (10) ,
      exPrt11  (11) ,
      exPrt12  (12)
      }
      MAX-ACCESS  read-only
      STATUS  current
      DESCRIPTION
      "This attribute indicates a unique  port number. "
      ::= { prtSExHsfStatEntry 2}

prtSExHsfInterfaceTyp OBJECT-TYPE
      SYNTAX  INTEGER
        {
         unknown     (1),
         v35         (2),
         rs422       (3)
     }
      MAX-ACCESS  read-only
      STATUS  current
      DESCRIPTION
      "This attribute indicates a unique interface type of a
       selected port."
      ::= { prtSExHsfStatEntry 3}

prtSExHsfRts OBJECT-TYPE
      SYNTAX  INTEGER
        {
         unknown     (1),
         notActive   (2),
         active      (3)
     }
      MAX-ACCESS  read-only
      STATUS  current
      DESCRIPTION
      "This attribute indicates a unique  RTS control signal state."
      ::= { prtSExHsfStatEntry 4}

cnfgMdlMux         OBJECT IDENTIFIER ::= {mdlMux 1}
mdlPbxFramerCnfg   OBJECT IDENTIFIER ::= {cnfgMdlMux 1}

mdlPbxFramerCnfgTable   OBJECT-TYPE
        SYNTAX SEQUENCE OF MdlPbxFramerCnfgEntry
        MAX-ACCESS not-accessible
        STATUS current
        DESCRIPTION
        "This table contains parameters relevant to a module belonging to
         a digital voice system, except mdlPbxFraEnhEcho which is relevant
         also for analog cards."
::= {mdlPbxFramerCnfg 1}

mdlPbxFramerCnfgEntry  OBJECT-TYPE
        SYNTAX MdlPbxFramerCnfgEntry
        MAX-ACCESS not-accessible
        STATUS current
	DESCRIPTION  "An entry in table."
	INDEX { mdlPbxFraCnfgIdx, mdlPbxFraSltIdx }
        ::=  {mdlPbxFramerCnfgTable 1}

MdlPbxFramerCnfgEntry ::=
        SEQUENCE {
                mdlPbxFraCnfgIdx Integer32,
                mdlPbxFraSltIdx  INTEGER,
                mdlPbxFraEnhEcho INTEGER,
                mdlPbxFraTSGroupAss INTEGER,
                mdlPbxFraSignalMode INTEGER,
                mdlPbxFraSignalVector OCTET STRING,
                mdlPbxFraSignalMask   OCTET STRING,
	            mdlPbxFraFramerSlot INTEGER,
				mdlPbxFraSignaling  INTEGER,
				mdlPbxFraTransSigTs Integer32 
	}

mdlPbxFraCnfgIdx OBJECT-TYPE
SYNTAX Integer32
        MAX-ACCESS read-only
        STATUS current
        DESCRIPTION
      "This attribute indicates the Idx of the Cnfg (1..100) being
       accessed.
       Idx 255 relates to the TmpCnfg. "
        DEFVAL {1}
        ::= { mdlPbxFramerCnfgEntry 1}

mdlPbxFraSltIdx OBJECT-TYPE
        SYNTAX INTEGER{ io1(5), io2(6), io3(7), io4(8), io5(9),
                        io6(10), io7(11), io8(12), io9(13), io10(14),
                        io11(15), io12(16) }
        MAX-ACCESS read-only
        STATUS current
        DESCRIPTION
        "The slot relevant to this module."
        ::= { mdlPbxFramerCnfgEntry 2}

mdlPbxFraEnhEcho OBJECT-TYPE
 SYNTAX INTEGER     { notApplicable(1) ,
   disabled(2),
   ms16(3),
   ms32(4)
    }
        MAX-ACCESS read-write
        STATUS current
        DESCRIPTION
        "Refers to external ports of an analogue module
        and to the internal ports of the other mvc4 types
        of modules.
        ms16(3) means that the four voice ports have enhanced
                echo of 16ms.
        ms32(4) means that the two first ports have enhanced
                echo of 32 ms while the last two ports have no
                enhanced echo."
        ::= { mdlPbxFramerCnfgEntry 3}

mdlPbxFraTSGroupAss OBJECT-TYPE
        SYNTAX INTEGER{ group1(1), group2(2), group3(3), group4(4),
                        group5(5), group6(6), group7(7), group8(8),
                        notApplicable(255) }
        MAX-ACCESS read-write
        STATUS current
        DESCRIPTION
        "In case of T1 modules:
        group1=(1,2,3,4), ...., group6=(21,22,23,24)
        while in case of E1 modules:
		   - If prtExPh1MlLineType=g732sE1 or g732sE1CRC:
             group1=(1,2,3,4),..,group4=(13,14,15,17),
             group5=(18,19,20,21),...,group7=(26,27,28,29)
             group8=(30,31).
		   - If prtExPh1MlLineType=g732nE1 or g732nE1CRC:
             group1=(1,2,3,4),..,group4=(13,14,15,16),
             group5=(17,18,19,20),...,group7=(25,26,27,28)
             group8=(29,30,31)."
        ::= { mdlPbxFramerCnfgEntry 4}

mdlPbxFraSignalMode OBJECT-TYPE
        SYNTAX INTEGER { notApplicable(1),
			tieTrunk(2),
			tieInvert(3),
			casTrans(4),
            userDefined(5),
			ccsTrans(6),
			noSignaling(7)
			}
        MAX-ACCESS read-write
        STATUS current
        DESCRIPTION
        "Refers to the signaling mode of the Framer module.
         tieTrunk(2), tieInvert(3), casTrans(4) are standard
        coding of the signaling protocol.

        casTrans(4) is Channel Associated Signaling (the signaling is within the
        channels time slot).
		ccsTrans(6) is Transparent Common Channel Signaling (the signaling is not within
		the channels time slot - a TS for signaling is used).

        userDefined(5) allows the user to define the signaling
        protocol he wants. In this case, the next two MIB fields
        are relevant."
        DEFVAL { casTrans }
        ::= { mdlPbxFramerCnfgEntry 5}

mdlPbxFraSignalVector OBJECT-TYPE
        SYNTAX OCTET STRING
        MAX-ACCESS read-write
        STATUS current
        DESCRIPTION
        "In the case of mdlPbxFraSignalMode = userDefined(5), this
        field defines the A,B,C Bits. D bit is supplied for future
        versions.
        Bit  1 = Bit A ON Hook  - Local
        Bit  2 = Bit B ON Hook  - Local
        Bit  3 = Bit C ON Hook  - Local
        Bit  4 = Bit D ON Hook  - Local
        Bit  5 = Bit A OFF Hook - Local
        Bit  6 = Bit B OFF Hook - Local
        Bit  7 = Bit C OFF Hook - Local
        Bit  8 = Bit D OFF Hook - Local

        Bit  9 = Bit A ON Hook  - Remote
        Bit 10 = Bit B ON Hook  - Remote
        Bit 11 = Bit C ON Hook  - Remote
        Bit 12 = Bit D ON Hook  - Remote
        Bit 13 = Bit A OFF Hook - Remote
        Bit 14 = Bit B OFF Hook - Remote
        Bit 15 = Bit C OFF Hook - Remote
        Bit 16 = Bit D OFF Hook - Remote

        In conjunction with the Mask, mdlPbxFraSignalMask, it is
        possible to compute the signal mode."
        DEFVAL { '0000'H}
        ::= { mdlPbxFramerCnfgEntry 6}

mdlPbxFraSignalMask OBJECT-TYPE
        SYNTAX OCTET STRING
        MAX-ACCESS read-write
        STATUS current
        DESCRIPTION
        "In the case of mdlPbxFraSignalMode = userDefined(5), this
        field defines the 'don't care' A,B,C Bits. D bit is supplied
        for future versions.
        Bit  1 = Bit A ON Hook  - Local
        Bit  2 = Bit B ON Hook  - Local
        Bit  3 = Bit C ON Hook  - Local
        Bit  4 = Bit D ON Hook  - Local
        Bit  5 = Bit A OFF Hook - Local
        Bit  6 = Bit B OFF Hook - Local
        Bit  7 = Bit C OFF Hook - Local
        Bit  8 = Bit D OFF Hook - Local

        Bit  9 = Bit A ON Hook  - Remote
        Bit 10 = Bit B ON Hook  - Remote
        Bit 11 = Bit C ON Hook  - Remote
        Bit 12 = Bit D ON Hook  - Remote
        Bit 13 = Bit A OFF Hook - Remote
        Bit 14 = Bit B OFF Hook - Remote
        Bit 15 = Bit C OFF Hook - Remote
        Bit 16 = Bit D OFF Hook - Remote."
	DEFVAL { 'ffff'H }
        ::= { mdlPbxFramerCnfgEntry 7}

mdlPbxFraFramerSlot OBJECT-TYPE
        SYNTAX INTEGER { io1(5), io2(6), io3(7), io4(8), io5(9),
                        io6(10), io7(11), io8(12), io9(13), io10(14),
                        io11(15), io12(16) }
        MAX-ACCESS read-write
        STATUS current
        DESCRIPTION
        "Slot where is sitting the Framer."
     ::= { mdlPbxFramerCnfgEntry 8}

mdlPbxFraSignaling OBJECT-TYPE
        SYNTAX INTEGER {
            notApplicable   (1),
			endToEnd        (2),
			localTermination(3)
			}
        MAX-ACCESS read-write
        STATUS current
        DESCRIPTION
        "Signaling - describes the way the signaling ABCD bits pass from the
		             local extension to the remote extension and vice-versa.

         endToEnd = the signaling ABCD bits pass without change from local to
                    remote extension.
         localTermination = the signaling ABCD bits received from the local extension
                    are translated to different ON Hook/OFF Hook bit values and then
                    passed to remote extension. This is relevant when the Local
                    and Remote ON Hook/OFF Hook values are different."
        DEFVAL { endToEnd }
        ::= { mdlPbxFramerCnfgEntry 9}

mdlPbxFraTransSigTs OBJECT-TYPE
        SYNTAX Integer32 
        MAX-ACCESS read-write
        STATUS current
        DESCRIPTION
        "This is the Time Slot that is used for Transparent CCS signaling.
         The values of this TS are 1-24 for T1 & 1-31 for E1.
         The default for E1 is 16 & for T1 it is 24. If no signaling is used then
         the TS should be 255 (None)."
        ::= { mdlPbxFramerCnfgEntry 10}

--
-- Specific port config for each module Type
-- *****************************************

--
-- MPCL.1 configuration parameters
--
--prtExClCnfgTable   OBJECT IDENTIFIER ::= {prtClCnfg 1}
-- prtInClInbandTable OBJECT IDENTIFIER ::= {prtClCnfg 2}

prtExClCnfgTable OBJECT-TYPE
      SYNTAX SEQUENCE OF PrtExClCnfgEntry
      MAX-ACCESS not-accessible
      STATUS current
	DESCRIPTION  "A table."
	::=  {prtClCnfg 1}

prtExClCnfgEntry OBJECT-TYPE
      SYNTAX PrtExClCnfgEntry
      MAX-ACCESS not-accessible
      STATUS current
      DESCRIPTION
      "All the entries at this table are identical (have the same
       value) for all the configurations (1..100) except the
       TmpCnfg.
       The write operation into the Table Objects is valid only
       to the TmpCnfg entry."
      INDEX {prtExClCnfgIdx, prtExClSltIdx, prtExClPrtIdx }
      ::= { prtExClCnfgTable 1}

PrtExClCnfgEntry ::=
      SEQUENCE {
      prtExClCnfgIdx         Integer32,
      prtExClSltIdx          INTEGER,
      prtExClPrtIdx          INTEGER,
   prtExClUsage           INTEGER,
   prtExClRate            INTEGER,
   prtExClDataBits        INTEGER,
   prtExClParity          INTEGER,
   prtExClStopBits        INTEGER,
   prtExClRoutingProtocol INTEGER,
   prtExClEnabled         INTEGER
      }


prtExClCnfgIdx OBJECT-TYPE
      SYNTAX  Integer32 (1..255)
      MAX-ACCESS  read-only
      STATUS  current
      DESCRIPTION
      "This attribute indicates the Idx of the Cnfg (1..100) being
       accessed.
       Idx 255 relates to the TmpCnfg."
      ::= { prtExClCnfgEntry 1}
-- In phase I only the values 1 (Cnfg1) and 255 (temp) are valid.

prtExClSltIdx OBJECT-TYPE
      SYNTAX  INTEGER
        {
       clA   (3),
          clB   (4),
    notApplicable (255)
        }
      MAX-ACCESS  read-only
      STATUS  current
      DESCRIPTION
      "This attribute indicates a unique  slot  position where
       the card is inserted. Because the second Cl is only for
       redundancy, all the parameters are identical in the two
       modules, i.e. change of any parameter in one module will
       change automatically the value of the other module..
       In the ?004 Unit the entry clB(4) is not valid."
      ::= { prtExClCnfgEntry 2}

prtExClPrtIdx OBJECT-TYPE
      SYNTAX  INTEGER
      {
  exPrt1    (1) ,
  exPrt2    (2)
      }
      MAX-ACCESS  read-only
      STATUS  current
      DESCRIPTION
      "This attribute indicates a unique  port number. "
      ::= { prtExClCnfgEntry 3}

prtExClUsage OBJECT-TYPE
      SYNTAX  INTEGER
       {
  unknown (1),
  noUse   (2),
  nmsSlip (3),
  nmsPpp  (4),
  muxSlip (5),
  muxPpp  (6),
  terminal(7)
       }
      MAX-ACCESS  read-only
      STATUS  current
      DESCRIPTION
      "This attribute indicates what is the usage of the port."
      ::= { prtExClCnfgEntry 4}

prtExClRate OBJECT-TYPE
      SYNTAX  INTEGER
       {
        r300Bps (1),
        r1200Bps (2),
        r2400Bps (3),
        r4800Bps (4),
        r9600Bps (5),
        r19200Bps (6),
        r38400Bps (7),
        r57600Bps (8),
        r115200Bps (9)
       }
      MAX-ACCESS  read-only
      STATUS  current
      DESCRIPTION
      "This attribute indicates the operation rate of the port."
      ::= { prtExClCnfgEntry 5}

prtExClDataBits OBJECT-TYPE
      SYNTAX  INTEGER
       {
        dataBits7Bits (1),
        dataBits8Bits (2)
       }
      MAX-ACCESS  read-only
      STATUS  current
      DESCRIPTION
      "This attribute indicates the number of data bits in async
       frame"
      ::= { prtExClCnfgEntry 6}

prtExClParity OBJECT-TYPE
      SYNTAX  INTEGER
       {
        odd   (1),
        even  (2),
        none  (3)
       }
      MAX-ACCESS  read-only
      STATUS  current
      DESCRIPTION
      "This attribute indicates if the parity operation mode in
       async frame"
      ::= { prtExClCnfgEntry 7}

prtExClStopBits OBJECT-TYPE
      SYNTAX  INTEGER
       {
          stopBits1Bit      (1),
          stopBits1dot5Bits (2),
          stopBits2Bits     (3)
       }
      MAX-ACCESS  read-only
      STATUS  current
      DESCRIPTION
      "This attribute indicates the minimum number of stop bits in
       the tx async frame"
      ::= { prtExClCnfgEntry 8}

prtExClRoutingProtocol OBJECT-TYPE
      SYNTAX  INTEGER
       {
       none    (1),
       rip2    (2)
       }
      MAX-ACCESS  read-only
      STATUS  current
      DESCRIPTION
      "This attribute indicates the routing protocol of the port.
       When prtExClUsage is nmsSlip or nmsPpp - all values are
                                                applicable .
       Else - only 'none' is applicable."
      ::= { prtExClCnfgEntry 9}

prtExClEnabled OBJECT-TYPE
      SYNTAX  INTEGER
       {
      notApplicable(1),
      disabled     (2),
	  enabled      (3)
       }
      MAX-ACCESS  read-only
      STATUS  current
      DESCRIPTION
      "This attribute indicates if Ethernet port of CL
       is enabled or not for management.
       It is applicable only on the ETH port of the CL, when the 
       MP includes an ML-IP card.
       disabled - will happen when there is Inband Management via
	              the ML-IP link/s
	   enabled  - will happen when ML-IP link/s is not used for Inband 
	              Management, but CL's ETH port ."
      ::= { prtExClCnfgEntry 10}

--
-- MPH1.T1, MPH1.E1, MTML.1/T1 , MTML.1/E1, ML-20
-- TDM and Hybrid(TDM & Packet) Main Link Modules
--
--prtExPh1MlCnfgTable OBJECT IDENTIFIER ::= {prtPh1MlCnfg 1}
--prtExPh1MlTsTable   OBJECT IDENTIFIER ::= {prtPh1MlCnfg 2}
--prtInPh1MlCnfgTable OBJECT IDENTIFIER ::= {prtPh1MlCnfg 3}
--prtInPh1MlDlciTable OBJECT IDENTIFIER ::= {prtPh1MlCnfg 4}
--prtPhMlCnfgTable    OBJECT IDENTIFIER ::= {prtPh1MlCnfg 5}

--
-- T1/E1 Port Objects
--
prtExPh1MlCnfgTable  OBJECT-TYPE
     SYNTAX SEQUENCE OF PrtExPh1MlCnfgEntry
     MAX-ACCESS not-accessible
     STATUS  current
     DESCRIPTION
      "The write operation into the Table Objects is valid only
       to the TmpCnfg entry."
     ::= {prtPh1MlCnfg 1}

prtExPh1MlCnfgEntry OBJECT-TYPE
      SYNTAX PrtExPh1MlCnfgEntry
      MAX-ACCESS not-accessible
      STATUS current
	DESCRIPTION  "An entry in table."
	INDEX {prtExPh1MlCnfgIdx, prtExPh1MlSltIdx, prtExPh1MlPrtIdx }
      ::= { prtExPh1MlCnfgTable 1}

PrtExPh1MlCnfgEntry ::=
      SEQUENCE {
      prtExPh1MlCnfgIdx        Integer32,
      prtExPh1MlSltIdx         INTEGER,
      prtExPh1MlPrtIdx         INTEGER,
      prtExPh1MlConnect        INTEGER,
      prtExPh1MlLineType       INTEGER,
      prtExPh1MlLineCode       INTEGER,
      prtExPh1MlLineLen        INTEGER,
      prtExPh1MlRestoreTime    INTEGER,
      prtExPh1MlTxGain         INTEGER,
      prtExPh1MlRxSensitivity  INTEGER,
      prtExPh1MlIdleCode       Integer32,
      prtExPh1MlTdmTrunk       INTEGER,
      prtExPh1MlClkMode        INTEGER,
      prtExPh1MlMfClkSrcSlt    INTEGER,
      prtExPh1MlMfClkSrcPrt    INTEGER,
      prtExPh1MlFdlType        INTEGER,
      prtExPh1MlInbandMng      INTEGER,
      prtExPh1MlInbandMngRate  INTEGER,
      prtExPh1MlRedundType     INTEGER,
      prtExPh1MlRedundSlot     INTEGER,
      prtExPh1MlRedundPort     INTEGER,
      prtExPh1MlRedundRecTime  Integer32,
   prtExPh1MlInbandMngRoutProt INTEGER,
      prtExPh1MlIfType         INTEGER,
	  prtExPh1MlMultiplier     INTEGER,
	  prtExPh1MlSupportedTS    INTEGER
      }


prtExPh1MlCnfgIdx OBJECT-TYPE
      SYNTAX  Integer32 (1..255)
      MAX-ACCESS  read-only
      STATUS  current
      DESCRIPTION
      "This attribute indicates the Idx of the Cnfg (1..100) being
       accessed.
       Idx 255 relates to the TmpCnfg. "
      ::= { prtExPh1MlCnfgEntry 1}
-- In phase I only the values 1 (Cnfg1) and 255 (temp) are valid.

prtExPh1MlSltIdx OBJECT-TYPE
      SYNTAX  INTEGER
     {
       notApplicable (1),
       io1   (5),
       io2   (6),
       io3   (7),
       io4   (8),
       io5   (9),
       io6  (10),
       io7  (11),
       io8  (12),
       io9  (13),
       io10 (14),
       io11 (15),
       io12 (16)
     }
      MAX-ACCESS  read-only
      STATUS  current
      DESCRIPTION
      "This attribute indicates a unique  slot  position where
       the module is inserted.
       In the ?004 Unit the entries io6(10)..io16) are not valid.
       For the Vmux2100 Main Board notApplicable (1) is used."
      ::= { prtExPh1MlCnfgEntry 2}

prtExPh1MlPrtIdx OBJECT-TYPE
      SYNTAX  INTEGER
       {
       exPrt1    (1),
       exPrt2    (2),
       exPrt3    (3),
       exPrt4    (4),
       inPrt1  (101),
	   inPrt2  (102),
	   inPrt3  (103),
	   inPrt4  (104)
       }
      MAX-ACCESS  read-only
      STATUS  current
      DESCRIPTION
      "This attribute indicates a unique  port number.
       MTML-1/E1 and MTML-1/T1 cards have only one external interface.
       inPrt1, inPrt2 - for MTML-H/2E1 and HSH cards.
       inPrt1..inPrt4 - for MTML-E2 cards.
       exPrt2..exPrt4 - for MTML-4 cards and others."
      ::= { prtExPh1MlCnfgEntry 3}

prtExPh1MlConnect OBJECT-TYPE
      SYNTAX  INTEGER
       {
  no  (2),
  yes (3)
       }
      MAX-ACCESS  read-write
      STATUS  current
      DESCRIPTION
      "This attribute indicates whether the port should be considered
       in any of the mux  algorithms. It also affects all the card
       considerations because it may indicate that the module has only
       one physical interface."
      ::= {prtExPh1MlCnfgEntry 4}

prtExPh1MlLineType OBJECT-TYPE
      SYNTAX  INTEGER
       {
  esfT1          (2), --> dsx1ESF
  sfT1           (3), --> dsx1D4
  g732nE1        (4), --> dsx1E1
  g732nE1CRC     (5), --> dsx1E1-CRC
  g732sE1        (6), --> dsx1E1-MF
  g732sE1CRC     (7)  --> dsx1E1-MF-CRC
       }
      MAX-ACCESS  read-write
      STATUS  current
      DESCRIPTION
      "This attribute is the line type parameter for T1/E1 interface.
       The user should select only the parameters which are relevant
       to the specific card:
       T1 line code parameters for the MPH.1/T1
       E1 line code parameters for the MPH.1/E1.
       This parameter has the same values as dsx1LineType in T1/E1
       MIB (RFC-1406). The parameters in dsx1LineType are:
                     other          (1)
      esfT1          dsx1ESF        (2)
      sfT1           dsx1D4         (3)
      g732nE1        dsx1E1         (4)
      g732nE1CRC     dsx1E1-CRC     (5)
      g732sE1        dsx1E1-MF      (6)
      g732sE1CRC     dsx1E1-MF-CRC  (7)"
      ::= { prtExPh1MlCnfgEntry 5}


prtExPh1MlLineCode OBJECT-TYPE
      SYNTAX  INTEGER
       {
        b7T1   (1),  --> dsx1JBZS (for E1 & T1)
        b8zsT1 (2),  --> dsx1B8ZS (for E1 & T1)
        transT1(3),  --> dsx1AMI
        hdb3E1 (4),  --> dsx1HDB3 (for E1 & T1)
        notApplicable(255)
       }
      MAX-ACCESS  read-write
      STATUS  current
      DESCRIPTION
      "This attribute is the line code parameter used for T1/E1
       interface.
       The user should select only the parameters which are relevant
       to the specific card:
       T1 line code parameters for MPH.1/T1
       E1 line code parameters for MPH.1/E1.
       This parameter has the same values as dsx1LineCoding in T1/E1
       MIB (RFC-1406).  The parameters in dsx1LineCoding are:
     dsx1JBZS  (1)
     dsx1B8ZS  (2)
     dsx1HDB3  (3)
     dsx1ZBTSI (4)
     dsx1AMI   (5)
     other     (6)"
      ::= { prtExPh1MlCnfgEntry 6}

prtExPh1MlLineLen OBJECT-TYPE
      SYNTAX  INTEGER
       {
        unknown      (1),
        len0p133ft   (2),
        len134p266ft (3),
        len267p399ft (4),
        len400p533ft (5),
        len534p655ft (6),
        lenFcc68     (7),
  notApplicable(255)
       }
      MAX-ACCESS  read-write
      STATUS  current
      DESCRIPTION
      "This attribute is the line length parameter used only for T1/DSU
       interfaces.
       lenXXXpXXXft = len-XXX-XXXft."
      ::= { prtExPh1MlCnfgEntry 7}

prtExPh1MlRestoreTime OBJECT-TYPE
      SYNTAX  INTEGER
       {
        restoreT1secFast      (2),
        restoreT10sec62411    (3),
        ccittE1                (4)
       }
      MAX-ACCESS  read-write
      STATUS  current
      DESCRIPTION
      "The time passing from the disappearance of the loss of
       synchronization condition (red alarm) to the restoration of
       normal service. The options 1secFast(2) and 10sec62411(3)
       for E1 interfaces are proprietary implementation of the T1
       standard to the E1 interface."
      ::= { prtExPh1MlCnfgEntry 8}

prtExPh1MlTxGain OBJECT-TYPE
      SYNTAX  INTEGER
       {
          notApplicable(1),
          txGain0db         (2),
          txGain7dot5db     (3),
          txGain15db        (4),
          txGain22dot5db    (5)
       }
      MAX-ACCESS  read-write
      STATUS  current
      DESCRIPTION
      "This attribute is the tx gain parameter used only for
       T1/CSU interfaces."
      ::= { prtExPh1MlCnfgEntry 9}

prtExPh1MlRxSensitivity OBJECT-TYPE
      SYNTAX  INTEGER
       {
        notApplicable(1),
        low26dBm  (2),
        high36dBm (3),
		shortHaul (4),
		longHaul  (5)
       }
      MAX-ACCESS  read-write
      STATUS  current
      DESCRIPTION
      "This attribute is the rx line sensitivity parameter.
       low26dBm, high36dBm - applicable for T1-CSU
       shortHaul, longHaul - applicable for MTML-4 cards."
      ::= { prtExPh1MlCnfgEntry 10}

prtExPh1MlIdleCode OBJECT-TYPE
      SYNTAX  Integer32
      MAX-ACCESS  read-write
      STATUS  current
      DESCRIPTION
     "Determines the code for transmission in empty time slots.
      Type value(00-FFH), Excluding 0H,8H,10H,12H,21H,24H,42H,49H,
      84H,92H"
      ::= { prtExPh1MlCnfgEntry 11}

prtExPh1MlTdmTrunk  OBJECT-TYPE
      SYNTAX  INTEGER
       {
        linkA   (1),
        linkB   (2),
        none    (3),
  notApplicable (255)
       }
      MAX-ACCESS  read-write
      STATUS  current
      DESCRIPTION
      "This attribute indicates whether the port is used to transfer
       TDM cards data and through which Bus."
      ::= {prtExPh1MlCnfgEntry 12}

prtExPh1MlClkMode OBJECT-TYPE
      SYNTAX  INTEGER
       {
    internalLocal (1),
    loopBackLocal (2),
    nodalTiming   (3)
       }
      MAX-ACCESS  read-write
      STATUS  current
      DESCRIPTION
      "Defines the clock operation mode of the T1/E1 interface.
       Ports that are connected to the TDM Buses must be in
       nodalTiming(3) clock mode. "
      ::= {prtExPh1MlCnfgEntry 13}

prtExPh1MlMfClkSrcSlt  OBJECT-TYPE
      SYNTAX  INTEGER
       {
          notApplicable(1),
          local (2),
          io1   (5),
          io2   (6),
          io3   (7),
          io4   (8),
          io5   (9),
          io6  (10),
          io7  (11),
          io8  (12),
          io9  (13),
          io10 (14),
          io11 (15),
          io12 (16)
       }
      MAX-ACCESS  read-write
      STATUS  current
      DESCRIPTION
      "This attribute indicates whether the port Tx multiframe is
       synchronized with Rx multiframe of another port and the slot
       position of that port.
       This operation is required in order to bypass signaling of
       PCM voice channels. Its value is always local(2) when the port
       isn't connected to any TDM bus. When it's value is local(2)
       there is no meaning to 'prtExPh1MlMfClkSrcPrt' parameter.
       In the ?004 Unit the entries io6(10)..io16) are not valid"
      ::= {prtExPh1MlCnfgEntry 14}

prtExPh1MlMfClkSrcPrt  OBJECT-TYPE
      SYNTAX  INTEGER
       {
          exPrt1         (1),
		  exPrt2         (2),
          inPrt1       (101),
          notApplicable(255)
       }
      MAX-ACCESS  read-write
      STATUS  current
      DESCRIPTION
      "A unique number to identify a port position in the mux. It
       has no effect when the prtExPh1MlMfClkSrcSlt selected is Local.
       inPrt1 - for MTML-H/E1 cards."
    ::= {prtExPh1MlCnfgEntry 15}

prtExPh1MlFdlType  OBJECT-TYPE
      SYNTAX  INTEGER
       {
          notApplicable(1),
          response   (2),
          command    (3)
       }
      MAX-ACCESS  read-write
      STATUS  current
      DESCRIPTION
      "A unique number to identify  the side of the FDL operation.
      Normal: 'response' for the user side and 'command' for the PTT
      side.
      Applicable only when working with ESF-T1 link"
      ::= {prtExPh1MlCnfgEntry 16}

prtExPh1MlInbandMng  OBJECT-TYPE
      SYNTAX  INTEGER
       {
       off                 (2),
       fdlOrTs0            (3),
       dedicatedTs         (4),
       dedicatedPpp        (5),
       dedicatedFr         (6),
       notApplicable     (255)
       }
      MAX-ACCESS  read-write
      STATUS  current
      DESCRIPTION
      "A unique number to identify an Inband management over the
       link."
      ::= {prtExPh1MlCnfgEntry 17}

prtExPh1MlInbandMngRate  OBJECT-TYPE
      SYNTAX  INTEGER
       {
          notApplicable(1),
          r4k   (2),
          r8k   (3),
          r12k  (4),
          r16k  (5),
          r32k  (6),
          r64k  (7),
          r20k  (8)
       }
      MAX-ACCESS  read-write
      STATUS  current
      DESCRIPTION
      "A unique number to identify the rate of the Inband
       management.
       E1 port - it is not applicable when prtExPh1MlInbandMng
                 selected is off.
       T1 port - it is not applicable when prtExPh1MlInbandMng
                 selected is off OR fdlOrTs0."
      ::= {prtExPh1MlCnfgEntry 18}

prtExPh1MlRedundType  OBJECT-TYPE
      SYNTAX  INTEGER
       {
          none                (1),
          dualCableAIS        (2),
          yCable              (3),
    dualCableParallelTx (4)
       }
      MAX-ACCESS  read-write
      STATUS  current
      DESCRIPTION
      "This object determines the ML redundancy type:
       none - no ML redundacy
       dualCableAIS -        each ML card is connected by a separate
       dualCableParallelTx   cable to the other MUX (two cables
                             connect two MUXes).  There are two
                             types of dual redundancy.
       yCable - Y cable is connected to both ML cards (one cable
                connects two MUXes).
       Default=none
       When only one ML card exists, the type can be only 'none'.
       The value should be the same for both ML slots."
      ::= {prtExPh1MlCnfgEntry 19}

prtExPh1MlRedundSlot  OBJECT-TYPE
      SYNTAX  INTEGER
       {
          notApplicable (1),
          io1   (5),
          io2   (6),
          io3   (7),
          io4   (8),
          io5   (9),
          io6  (10),
          io7  (11),
          io8  (12),
          io9  (13),
          io10 (14),
          io11 (15),
          io12 (16)
       }
      MAX-ACCESS  read-write
      STATUS  current
      DESCRIPTION
      "This object indicates the slot containing the redundacy ML
    card, coupled with the current ML (prtExPh1MlSltIdx).
       When prtExPh1MlRedundType=none (no ML redundancy) this
       object will be 'notApplicable'.
       In the ?004 Unit the entries io6(10)..io12(16) are not valid
       When value is not 'none', it should be mutual to the
       redundant ML slot."
      ::= {prtExPh1MlCnfgEntry 20}

prtExPh1MlRedundPort  OBJECT-TYPE
      SYNTAX  INTEGER
       {
       exPrt1          (1),
       exPrt2          (2),
       exPrt3          (3),
       exPrt4          (4),
       inPrt1        (101),
       inPrt2        (102),
       inPrt3        (103),
       inPrt4        (104),
       notApplicable (255)
       }
      MAX-ACCESS  read-write
      STATUS  current
      DESCRIPTION
      "This object indicates the redundacy ML port, coupled with the
       current ML port (prtExPh1MlPrtIdx).
       When prtExPh1MlRedundType=none (no ML redundancy) this
       object will be 'notApplicable'.
       When value is not 'none', it should be mutual to the
       redundant ML port.
       inPrt1 - for MTML-H/E1 cards.
       inPrt1..inPrt4 - for MTML-E2 cards.
       exPrt2..exPrt4 - for MTML-4 cards."
      ::= {prtExPh1MlCnfgEntry 21}

prtExPh1MlRedundRecTime  OBJECT-TYPE
      SYNTAX  Integer32  (1..99)
      MAX-ACCESS  read-write
      STATUS  current
      DESCRIPTION
      "Redundancy Recovery Time (sec). After switching the ML card
       to the current (prtExPh1MlSltIdx), the next ML switch can
       be performed only after a minimum time, indicated by
       this object."
      ::= {prtExPh1MlCnfgEntry 22}

prtExPh1MlInbandMngRoutProt  OBJECT-TYPE
      SYNTAX  INTEGER
       {
  none    (1),
  rip2    (2),
  proprietary (3)
       }
      MAX-ACCESS  read-write
      STATUS  current
      DESCRIPTION
      "This attribute indicates the Inband Mng routing protocol of
       the port."
      ::= {prtExPh1MlCnfgEntry 23}

prtExPh1MlIfType  OBJECT-TYPE
      SYNTAX  INTEGER
       {
       notApplicable (1),
       csu    (2),
       dsu    (3),
	   ltu    (4)
       }
      MAX-ACCESS  read-write
      STATUS  current
      DESCRIPTION
      "Interface type of the port.
       For T1 - csu, dsu are the valid values
       For E1 - dsu, ltu are the valid values."
      ::= {prtExPh1MlCnfgEntry 24}

prtExPh1MlMultiplier  OBJECT-TYPE
             SYNTAX  INTEGER { 
                             notApplicable (1), 
                             br56 (2),
                             br64 (3)
              }
              MAX-ACCESS  read-write
              STATUS  current
              DESCRIPTION
                      "The data rate of each TS. The multiplier values
                       can be 56 kbps or 64 kbps."
      ::= {prtExPh1MlCnfgEntry 25}

prtExPh1MlSupportedTS  OBJECT-TYPE
      SYNTAX  INTEGER 
      MAX-ACCESS  read-only
      STATUS  current
      DESCRIPTION
      "Number of Supported Time Slots by the agent.
       For Vmux-110 there is HW that supports less than 31/24
       Time Slots for the E1/T1 port."
      ::= {prtExPh1MlCnfgEntry 26}



--
-- MPH1.T1 & MPH1.E1
-- Time Slot Assignment Table
--
prtExPh1MlTsTable  OBJECT-TYPE
     SYNTAX SEQUENCE OF PrtExPh1MlTsEntry
     MAX-ACCESS not-accessible
     STATUS  current
     DESCRIPTION
      "The write operation into the Table Objects is valid only
       to the TmpCnfg entry, except prtExPh1MlTsTest that will be written
       directly to the Active Configuration."
     ::= {prtPh1MlCnfg 2}

prtExPh1MlTsEntry OBJECT-TYPE
      SYNTAX PrtExPh1MlTsEntry
      MAX-ACCESS not-accessible
      STATUS current
	DESCRIPTION  "An entry in table."
	INDEX {prtExPh1MlTsCnfgIdx, prtExPh1MlTsSltIdx, prtExPh1MlTsPrtIdx, prtExPh1MlTsIdx }
      ::= { prtExPh1MlTsTable 1}

PrtExPh1MlTsEntry ::=
      SEQUENCE {
      prtExPh1MlTsCnfgIdx        Integer32,
      prtExPh1MlTsSltIdx         INTEGER,
      prtExPh1MlTsPrtIdx         INTEGER,
      prtExPh1MlTsIdx            Integer32,
      prtExPh1MlTsIConSlot       INTEGER,
      prtExPh1MlTsIConPrt        Integer32,
      prtExPh1MlTsIConTs         Integer32,
      prtExPh1MlTsExt    OBJECT IDENTIFIER,
	  prtExPh1MlTsTest           INTEGER,
	  prtExPh1MlTsType           INTEGER,
	  prtExPh1MlTsBundle         INTEGER,
	  prtExPh1MlTsTestDuration   Integer32
      }

prtExPh1MlTsCnfgIdx OBJECT-TYPE
      SYNTAX  Integer32  (1..255)
      MAX-ACCESS  read-only
      STATUS  current
      DESCRIPTION
      "This attribute indicates the Idx of the Cnfg (1..100) being
       accessed.
       Idx 255 relates to the TmpCnfg. "
      ::= { prtExPh1MlTsEntry 1}
-- In phase I only the values 1 (Cnfg1) and 255 (temp) are valid.

prtExPh1MlTsSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16),
	   notApplicable (255)
     }
      MAX-ACCESS  read-only
      STATUS  current
      DESCRIPTION
      "This attribute indicates a unique  slot  position where
       the card is inserted.
       In the ?004 Unit the entries io6(10)..io16) are not valid.
       For the Vmux2100 Main Board notApplicable (255) is used."
      ::= { prtExPh1MlTsEntry 2}

prtExPh1MlTsPrtIdx OBJECT-TYPE
      SYNTAX  INTEGER
	{
          exPrt1    (1),
		  exPrt2    (2),
		  exPrt3    (3),
		  exPrt4    (4),
		  inPrt1  (101)
	      }
      MAX-ACCESS  read-only
      STATUS  current
      DESCRIPTION
      "This attribute indicates a unique  port number.
       MPH.1/E1 and MPH.1/T1 cards have only one external interface.
	   exPrt2 - for ME1-2, MT1-2 and mhsPri cards.
	   exPrt3, exPrt4 - for mhsPri cards.
       inPrt1 - for MTML-H/E1 cards."
      ::= { prtExPh1MlTsEntry 3}

prtExPh1MlTsIdx OBJECT-TYPE
      SYNTAX  Integer32
      MAX-ACCESS  read-only
      STATUS  current
      DESCRIPTION
      "This attribute indicates a unique time slot  position.
       The valid time slots are 1..24 for T1 Card and
       1..31 for E1 interface. In G732S-E1 lines time slot 16 is not
       valid for data, it is dedicated for multiframe synchronization bits
       and voice signaling."
      ::= { prtExPh1MlTsEntry 4}

prtExPh1MlTsIConSlot OBJECT-TYPE
      SYNTAX  INTEGER
       {
          unknown   (1),		  
          noConnect (2),
          split     (4),
          io1       (5),
          io2       (6),
          io3       (7),
          io4       (8),
          io5       (9),
          io6      (10),
          io7      (11),
          io8      (12),
          io9      (13),
          io10     (14),
          io11     (15),
          io12     (16),
		  notApplicable (255)
       }
      MAX-ACCESS  read-write
      STATUS  current
      DESCRIPTION
      "This attribute indicates whether the specified time slot is
       connected/routed internally in the Agent and to which card
       it is connected.
       In the ?004 Unit the entries io6(10)..io16) are not valid.
       split - will be used when the Src TS is connected to more
               than one slot OR more than one port (each needing
               less than a whole TS)."
      ::= {prtExPh1MlTsEntry 5}

prtExPh1MlTsIConPrt OBJECT-TYPE
      SYNTAX  Integer32
      MAX-ACCESS  read-write
      STATUS  current
      DESCRIPTION
      "This attribute indicates the internally (In Mux)
       connected/routed port.
       For MP, the values will be:
       	      {
	      exPrt1    (1) ,
	      exPrt2    (2) ,
	      exPrt3    (3) ,
	      exPrt4    (4) ,
	      exPrt5    (5) ,
	      exPrt6    (6) ,
	      exPrt7    (7) ,
	      exPrt8    (8) ,
	      exPrt9    (9) ,
	      exPrt10  (10) ,
          exPrt11  (11) ,
          exPrt12  (12) ,

          noConnect (100),

	      inPrt1  (101) ,
	      inPrt2  (102) ,
	      inPrt3  (103) ,
	      inPrt4  (104) ,
	      inPrt5  (105) ,
	      inPrt6  (106) ,
	      inPrt7  (107) ,
	      inPrt8  (108) ,
	      inPrt9  (109) ,
	      inPrt10 (110)	,
		  inPrt11 (111) ,
		  inPrt12 (112)
	      }		   "
      ::= {prtExPh1MlTsEntry 6}

prtExPh1MlTsIConTs OBJECT-TYPE
      SYNTAX  Integer32
      MAX-ACCESS  read-write
      STATUS  current
      DESCRIPTION
      "This attribute indicates a unique time slot  position.
       The valid time slots are 1..24 for T1 Card and
       1..31 for E1 interface. In G732S-E1 lines time slot 16 is not
       valid for data, it is dedicated to multiframe synchronization
       and voice signaling."
      ::= {prtExPh1MlTsEntry 7}

prtExPh1MlTsExt OBJECT-TYPE
        SYNTAX  OBJECT IDENTIFIER
        MAX-ACCESS  read-only
        STATUS  current
        DESCRIPTION
             "A pointer to an extension of this table:
              prtExTsSplitTable.
              - If prtExPh1MlTsIConSlot='split', its value
                should be set to the OBJECT IDENTIFIER of the
                prtExTsSplitTable, with its relevant CnfgIdx,
                SltIdx, PrtIdx, TsIdx and 1st TsBit.
              - If prtExPh1MlTsIConSlot is not 'split', its value
                should be set to the OBJECT IDENTIFIER { 0 0 }. "
     ::= { prtExPh1MlTsEntry 8 }

prtExPh1MlTsTest OBJECT-TYPE
      SYNTAX  INTEGER
     {
       none                    (1),
       localLoop               (2),
       remoteLoop              (3),
       remoteBert              (8),	  -- BERT 
       localToneInjection      (9),	  -- Tone Injection
       remoteToneInjection     (18),  -- Backward Tone Injection
       localBert               (30),
	   split                   (254),
       notApplicable           (255)
        }
      MAX-ACCESS  read-write
      STATUS  current
      DESCRIPTION
      "This attribute indicates a test to be activated on the selected TS.
	   It is applicable only when prtSTstCmd=testPerTS(31).
	   notApplicable - when prtSTstCmd is NOT testPerTS(31).
	   none  - no test is applied for the selected TS.
       split - when the tests are per Bit of the selected TS."
      ::= { prtExPh1MlTsEntry 9 }

prtExPh1MlTsType OBJECT-TYPE
      SYNTAX  INTEGER
     {
       noConnect               (2),
       data                    (3),
       voice                   (4),
	   cas					   (5),
       notApplicable           (255)
        }
      MAX-ACCESS  read-write
      STATUS  current
      DESCRIPTION
      "The Time Slot Type. "
      ::= { prtExPh1MlTsEntry 10 }

prtExPh1MlTsBundle OBJECT-TYPE
      SYNTAX  INTEGER
      MAX-ACCESS  read-write
      STATUS  current
      DESCRIPTION
      "The number of the bundle containing this Time Slot.
       If no bundle exists for this TS or the bundle number
       is irrelevant, the value will be 0."
      ::= { prtExPh1MlTsEntry 11 }


prtExPh1MlTsTestDuration OBJECT-TYPE
      SYNTAX  Integer32
      MAX-ACCESS  read-write
      STATUS  current
      DESCRIPTION
       "This attribute indicates the maximum duration of executing
      a test on the specific TS. This entry applies to all the
      test operations. 

      For the Vmux2100 the values are:
      0 - 60 seconds.

      A zero  value specifies no time limitation.      
      When the test isn't active, the agent initiates this object to
      2 when the duration is needed and to 0 if its not required.
      The user should set this parameter after setting the
      'prtExPh1MlTsTest' parameter."
      ::= { prtExPh1MlTsEntry 12 }

--
-- MPH.1/T1 & MPH.1/E1
-- Internal port objects table
-- (only for the Hybrid modules)
--
prtInPh1MlCnfgTable  OBJECT-TYPE
     SYNTAX SEQUENCE OF PrtInPh1MlCnfgEntry
     MAX-ACCESS not-accessible
     STATUS  current
     DESCRIPTION
      "The write operation into the Table Objects is valid only
       to the TmpCnfg entry."
     ::= {prtPh1MlCnfg 3}

prtInPh1MlCnfgEntry OBJECT-TYPE
      SYNTAX PrtInPh1MlCnfgEntry
      MAX-ACCESS not-accessible
      STATUS current
	DESCRIPTION  "An entry in table."
	INDEX {prtInPh1MlCnfgIdx, prtInPh1MlSltType, prtInPh1MlPrtIdx }
      ::= { prtInPh1MlCnfgTable 1}

PrtInPh1MlCnfgEntry ::=
      SEQUENCE {
      prtInPh1MlCnfgIdx            Integer32,
      prtInPh1MlSltType            INTEGER,
      prtInPh1MlPrtIdx             Integer32,
      prtInPh1MlConnect            INTEGER,
      prtInPh1MlRate               INTEGER,
      prtInPh1MlProtocol           INTEGER,
      prtInPh1MlConnectionTyp      INTEGER,
      prtInPh1MlCongResponse       INTEGER,
      prtInPh1MlCongLevel          Integer32,
      prtInPh1MlTc                 INTEGER,
      prtInPh1MlFlowControl        INTEGER,
      prtInPh1MlSegment            INTEGER,
      prtInPh1MlFrMngProt          INTEGER,
      prtInPh1MlEnqPeriod          Integer32,
      prtInPh1MlFullRptPeriod      Integer32,
      prtInPh1MlFrWindowSize       Integer32,
      prtInPh1MlErrorsThreshold    Integer32,
      prtInPh1MlMaxIdleTime        Integer32,
	  prtInPh1MlBearerCh           INTEGER,
	  prtInPh1MlAssociatedExCh     INTEGER,
	  prtInPh1MlClockEncoding      INTEGER,
	  prtInPh1MlMinSeparators      Integer32,
	  prtInPh1MlCcittCrc           INTEGER,
	  prtInPh1MlFrameSeparator     INTEGER
      }


prtInPh1MlCnfgIdx OBJECT-TYPE
      SYNTAX  Integer32 (1..255)
      MAX-ACCESS  read-only
      STATUS  current
      DESCRIPTION
      "This attribute indicates the Idx of the Cnfg (1..100) being
       accessed.
       Idx 255 relates to the TmpCnfg. "
      ::= { prtInPh1MlCnfgEntry 1}
-- In phase I only the values 1 (Cnfg1) and 255 (temp) are valid.

prtInPh1MlSltType OBJECT-TYPE
      SYNTAX  INTEGER
     {
       io1   (5),
       io2   (6),
       io3   (7),
       io4   (8),
       io5   (9),
       io6  (10),
       io7  (11),
       io8  (12),
       io9  (13),
       io10 (14),
       io11 (15),
       io12 (16),
       notApplicable(255)
     }
      MAX-ACCESS  read-only
      STATUS  current
      DESCRIPTION
      "This attribute indicates a unique  slot  position where
       the card is inserted.
       For ISDN BRI port of MX300/30:
       io1(5) = isdn1(5) and io2(6) = isdn2(6)
       In the ?004 Unit the entries io6(10)..io12(16) are not valid"
      ::= { prtInPh1MlCnfgEntry 2}

prtInPh1MlPrtIdx OBJECT-TYPE
      SYNTAX  Integer32
      MAX-ACCESS read-only
      STATUS  current
      DESCRIPTION
      "This attribute indicates a unique port number.
       MPH.1/E1 and MPH.1/T1 cards have three internal interfaces.
       MX3000 modules may have up to 50 internal ports."
      ::= { prtInPh1MlCnfgEntry 3}

prtInPh1MlConnect OBJECT-TYPE
      SYNTAX  INTEGER
       {
  no  (2),
  yes (3)
       }
      MAX-ACCESS  read-write
      STATUS  current
      DESCRIPTION
      "This attribute indicates whether the port should be
       considered in any of the mux  algorithms."
      ::= { prtInPh1MlCnfgEntry 4}

prtInPh1MlRate OBJECT-TYPE
      SYNTAX  INTEGER
       {
        r1x56eq56Kbps    (1),
        r1x64eq64Kbps    (2),
        r2x56eq112Kbps   (3),
        r2x64eq128Kbps   (4),
        r3x56eq168Kbps   (5),
        r3x64eq192Kbps   (6),
        r4x56eq224Kbps   (7),
        r4x64eq256Kbps   (8),
        r5x56eq280Kbps   (9),
        r5x64eq320Kbps  (10),
        r6x56eq336Kbps  (11),
        r6x64eq384Kbps  (12),
        r7x56eq392Kbps  (13),
        r7x64eq448Kbps  (14),
        r8x56eq448Kbps  (15),
        r8x64eq512Kbps  (16),
        r9x56eq504Kbps  (17),
        r9x64eq576Kbps  (18),
        r10x56eq560Kbps (19),
        r10x64eq640Kbps (20),
        r11x56eq616Kbps (21),
        r11x64eq704Kbps (22),
        r12x56eq672Kbps (23),
        r12x64eq768Kbps (24),
        r13x56eq728Kbps (25),
        r13x64eq832Kbps (26),
        r14x56eq784Kbps (27),
        r14x64eq896Kbps (28),
        r15x56eq840Kbps (29),
        r15x64eq960Kbps (30),
        r16x56eq896Kbps (31),
        r16x64eq1024Kbps(32),
        r17x56eq952Kbps (33),
        r17x64eq1088Kbps(34),
        r18x56eq1008Kbps(35),
        r18x64eq1152Kbps(36),
        r19x56eq1064Kbps(37),
        r19x64eq1216Kbps(38),
        r20x56eq1120Kbps(39),
        r20x64eq1280Kbps(40),
        r21x56eq1176Kbps(41),
        r21x64eq1344Kbps(42),
        r22x56eq1232Kbps(43),
        r22x64eq1408Kbps(44),
        r23x56eq1288Kbps(45),
        r23x64eq1472Kbps(46),
        r24x56eq1344Kbps(47),
        r24x64eq1536Kbps(48),

        -- the next values are only for MPH.1/E1 modules

        r25x56eq1400Kbps(49),
        r25x64eq1600Kbps(50),
        r26x56eq1456Kbps(51),
        r26x64eq1664Kbps(52),
        r27x56eq1512Kbps(53),
        r27x64eq1728Kbps(54),
        r28x56eq1568Kbps(55),
        r28x64eq1792Kbps(56),
        r29x56eq1624Kbps(57),
        r29x64eq1856Kbps(58),
        r30x56eq1680Kbps(59),
        r30x64eq1920Kbps(60),
        r31x56eq1736Kbps(61),
        r31x64eq1984Kbps(62),
		noRate         (100)
     }
      MAX-ACCESS  read-write
      STATUS  current
      DESCRIPTION
      "This attribute indicates the port speed. "
      ::= { prtInPh1MlCnfgEntry 5}

prtInPh1MlProtocol OBJECT-TYPE
      SYNTAX  INTEGER
     {
        fr                 (1),
        frPlus             (2),
        pCellRelay         (3),
        hdlcSdlc           (4),
        transparentHdlc    (5)
     }
      MAX-ACCESS  read-write
      STATUS  current
      DESCRIPTION
      "This attribute indicates the applied protocol."
      ::= { prtInPh1MlCnfgEntry 6}

prtInPh1MlConnectionTyp OBJECT-TYPE
      SYNTAX  INTEGER
     {
	    sameNetManaged  (1),
	    sameNetNotMana  (2),
	    user            (3),
	    otherNet        (4),
	    pubNet          (5),
		notApplicable (255)
     }
      MAX-ACCESS  read-write
      STATUS  current
      DESCRIPTION
      "This attribute indicates the link connection type.
       It is required for three reasons:
     FR/CR Inband management operation (LMI,CLMM...).
     CIR check.
     NMS network management.

       SameNetManaged - indicates network internal line.
       SameNetNotMana - indicates network internal line, but the remote
               mux is not managed by the nms.

       User           - User to Network Interface.
       OtherNet       - Network To Network Interfce.
       PubNet         - Access Mux To PubNet Interface."
      ::= { prtInPh1MlCnfgEntry 7}

prtInPh1MlCongResponse OBJECT-TYPE
      SYNTAX  INTEGER
     {
     no              (2),
        flowControl     (3)
     }
      MAX-ACCESS  read-write
      STATUS  current
      DESCRIPTION
"This attribute indicates how to handle the congestion indication
 to/from the mux internal connection side (for example
 transmit/receive becn to/from the network).
   no           - do nothing
   FlowControl  - translate the congestion indication between the
                  port and the internal connection port according to
                  the definition of the prtInPh1MlFlowControl
                  parameters. The operation is done in both directions."
      ::= { prtInPh1MlCnfgEntry 8}

prtInPh1MlCongLevel OBJECT-TYPE
      SYNTAX  Integer32
      MAX-ACCESS  read-write
      STATUS  current
      DESCRIPTION
      "This attribute indicates the level of delayed data in
       precents of the total available dynamic memory,
       for which the port will start to operate .
       The resolution of the parameter is 5 percent.
	   Valid values: 10..70, 255.
       255=notApplicable."
      ::= { prtInPh1MlCnfgEntry 9}

prtInPh1MlTc OBJECT-TYPE
      SYNTAX  INTEGER
          {
          tc1sec  (1),
          tc2sec  (2),
          tc3sec  (3),
          tc4sec  (4),
		  notApplicable (255)
          }
      MAX-ACCESS  read-write
      STATUS  current
      DESCRIPTION
      "This attribute indicates the Tc parameter which is the time
       period of the sliding window in which the Bc/Be are tested.
       The value of this parameter is identical for all the ports in the
       specific card.
       255=notApplicable."
      ::= { prtInPh1MlCnfgEntry 10}

prtInPh1MlFlowControl OBJECT-TYPE
      SYNTAX  INTEGER
     {
        none                (2),
        fecnBecn            (3)
     }
      MAX-ACCESS  read-write
      STATUS  current
      DESCRIPTION
      "This attribute indicates the required flow control betweeen
       the port and the remote equipment."
      ::= { prtInPh1MlCnfgEntry 11}

prtInPh1MlSegment OBJECT-TYPE
      SYNTAX  INTEGER
   {
   notApplicable (1),
   s36Byte       (2),
   s150Byte      (3),
   s264Byte      (4),
   s378Byte      (5),
   s492Byte      (6),
   s236Byte      (7),
   s472Byte      (8),
   s708Byte      (9),
   s944Byte     (10),
   s1180Byte    (11)
   }
      MAX-ACCESS  read-write
      STATUS  current
      DESCRIPTION
      "This object is the Segmentation in Bytes.
	   In protocol FR+, ISDN internals, MX 30/300 the segmentation is:

       50 (2) ,158 (3) ,266 (4) ,376 (5), 484 (6)

       In  MX 3000/4:
       For protocol FR+ (internal ISDN ports of MHS.S, MHS.U, MHS.E1, MHS.T1
       cards) segmentation values are:

       236 (7),472 (8), 708 (9), 944 (10) ,1180 (11)"

    ::= { prtInPh1MlCnfgEntry 12}

prtInPh1MlFrMngProt OBJECT-TYPE
      SYNTAX  INTEGER
   {
   notApplicable (1),
   none          (2),
   lmi           (3),
   ansiT1        (4), --Annex D
   annexA        (5)
   }
      MAX-ACCESS  read-write
      STATUS  current
      DESCRIPTION
      "This object indicates the Frame-Relay management protocol.
       ansiT1 = ANSI T1.617 Annex D (this is the default value).
       This parameter is applicable only for FR and FR+ protocols.
       When prtInPh1MlConnectionTyp = sameNetManaged, this object
       will be RO (internally determined). "
      ::= { prtInPh1MlCnfgEntry 13}

prtInPh1MlEnqPeriod OBJECT-TYPE
      SYNTAX  Integer32 (0..30)
      MAX-ACCESS  read-write
      STATUS  current
      DESCRIPTION
      "This object is the Status Enquiry Period, in seconds.
       It determines the frequency of the Status Enquiry message
       as sent by the FR user side.
       At the FR network side, it determines the timeout for this
       message reception.
    Default = 4 seconds.
       This parameter is applicable only for FR and FR+ protocols
    AND
       only when prtInPh1MlFrMngProt is NOT (notApplicable or none).
       0=notApplicable."
    ::= { prtInPh1MlCnfgEntry 14}

prtInPh1MlFullRptPeriod OBJECT-TYPE
      SYNTAX  Integer32 (0..255)
      MAX-ACCESS  read-write
      STATUS  current
      DESCRIPTION
      "This object is the Full Report Frequency.
       It determines the number of the Status Enquiry messages
       sent by the FR user side, before a Full Report Request is
       sent.
       The units are : Status Enquiry messages (periods).
    Valid values: 1 .. 255.
       255 = infinite (never sent).
       This parameter is applicable only for FR and FR+ protocols
    AND
       only when prtInPh1MlFrMngProt is NOT (notApplicable or none).
       0=notApplicable."
    ::= { prtInPh1MlCnfgEntry 15}

prtInPh1MlFrWindowSize OBJECT-TYPE
      SYNTAX  Integer32 (0..10)
      MAX-ACCESS  read-write
      STATUS  current
      DESCRIPTION
      "This object is the FR Window Size.
       It determines the number of samplings in the sliding window
       that counts the errors.
       This parameter is applicable only for FR and FR+ protocols
    AND
       only when prtInPh1MlFrMngProt is NOT (notApplicable or none).
       0=notApplicable."
    ::= { prtInPh1MlCnfgEntry 16}

prtInPh1MlErrorsThreshold OBJECT-TYPE
      SYNTAX  Integer32 (0..10)
      MAX-ACCESS  read-write
      STATUS  current
      DESCRIPTION
      "This object is the Max Errors.
       It determines the number of Status Enquiry Errors that
       occured within the FR sliding window, before this port is
       considered DOWN (threshold).
       This parameter is applicable only for FR and FR+ protocols
    AND
       only when prtInPh1MlFrMngProt is NOT (notApplicable or none).
       0=notApplicable. "
    ::= { prtInPh1MlCnfgEntry 17}

prtInPh1MlMaxIdleTime OBJECT-TYPE
     SYNTAX  Integer32 (0..1800)
     MAX-ACCESS   read-write
     STATUS   current
     DESCRIPTION
     "Move to higher prioritized connected link	after this period of
      seconds of silence on the current link.
	  0=Never. Never move to higher prioritized connected link.
      UNIT is seconds.
      Valid values are: 0, 1, 2, 3, 4, 5, 10, 20, 30, 40, 50, 60, 120, 180, 240, 300,
      360, 420, 480, 540, 600, 900, 1200, 1500, 1800.
      Attempt to Set an invalid value will result in getting the default value."
     DEFVAL { 10 }
     ::= {prtInPh1MlCnfgEntry 18}

prtInPh1MlBearerCh OBJECT-TYPE
     SYNTAX  INTEGER
	 {
      notApplicable (1),
      channelB1     (3),
      channelB2     (4),
	  chB1andchB2   (5),
	  none          (255)
	       }
	 MAX-ACCESS   read-write
     STATUS   current
     DESCRIPTION
	 "Defines which B (bearer) channels are used for transferring ISDN data.
	  Default value is: none (255).
	  anyChannel (2) is skipped because it is not in use here."
	 ::= {prtInPh1MlCnfgEntry 19}

prtInPh1MlAssociatedExCh OBJECT-TYPE
      SYNTAX  INTEGER
     {
        exPrt1        (1),
        exPrt2        (2),
		exPrt3        (3),
		exPrt4        (4),
		notApplicable (255)
     }
      MAX-ACCESS  read-write
      STATUS  current
      DESCRIPTION
      "This object indicates the external port associated to this internal
       port. At present, it is used by the Hybrid (mp2100h), MHS-4 cards which
       can have up to 64 dynamic internal ports associated with External ports.

       For ISDN cards, the value will be: notApplicable (255).
       The associated external of an ISDN internal port is represented
       by the MIB object: prtIsdnDirectoryPrtNu."
      ::= { prtInPh1MlCnfgEntry 20}

prtInPh1MlClockEncoding OBJECT-TYPE
      SYNTAX  INTEGER
	  {
	  notApplicable (1),
	  nrz           (2),
	  nrzI          (3),
	  fm0           (4),
	  manchester    (5),
	  diffManchester(6)
	  }
      MAX-ACCESS  read-write
      STATUS  current
      DESCRIPTION
      "This object is the Encoding type of the Line.
       This parameter is applicable only for FR and FR+ protocols."
	   ::= { prtInPh1MlCnfgEntry 21}

prtInPh1MlMinSeparators OBJECT-TYPE
      SYNTAX  Integer32 (0..16)
      MAX-ACCESS  read-write
      STATUS  current
      DESCRIPTION
      "Minimum number of bytes separating between two adjacent frames (HDLC item).
       0 = notApplicable"
	   ::= { prtInPh1MlCnfgEntry 22}

prtInPh1MlCcittCrc OBJECT-TYPE
      SYNTAX  INTEGER
	  {
	  notApplicable (1),
	  crc16         (2),
	  crc32         (3)
	  }
      MAX-ACCESS  read-write
      STATUS  current
      DESCRIPTION
      "This object indicates how many Bits are used for CRC (HDLC item)."
	   ::= { prtInPh1MlCnfgEntry 23}

prtInPh1MlFrameSeparator OBJECT-TYPE
      SYNTAX  INTEGER
	  {
	  notApplicable (1),
	  idles         (2),
	  flags         (3)
	  }
      MAX-ACCESS  read-write
      STATUS  current
      DESCRIPTION
      "This object indicates what should be transferred on the line when there
       are no frames to pass (HDLC item).
       idles: mean that FF will pass on the line
       flags: mean that 7E will pass on the line."
	   ::= { prtInPh1MlCnfgEntry 24}


--
-- MPH1.T1 & MPH1.E1
-- Internal port Dlci objects table
--

prtInPh1MlDlciTable  OBJECT-TYPE
     SYNTAX SEQUENCE OF PrtInPh1MlDlciEntry
     MAX-ACCESS not-accessible
     STATUS  current
     DESCRIPTION
      "The write operation into the Table Objects is valid only
       to the TmpCnfg entry."
     ::= {prtPh1MlCnfg 4}

prtInPh1MlDlciEntry OBJECT-TYPE
      SYNTAX PrtInPh1MlDlciEntry
      MAX-ACCESS not-accessible
      STATUS current
	DESCRIPTION  "An entry in table."
	INDEX {prtInPh1MlDlciCnfgIdx, prtInPh1MlDlciSltIdx, prtInPh1MlDlciPrtIdx, prtInPh1MlDlciIdx }
      ::= { prtInPh1MlDlciTable 1}

PrtInPh1MlDlciEntry ::=
      SEQUENCE {
      prtInPh1MlDlciCnfgIdx        Integer32,
      prtInPh1MlDlciSltIdx         INTEGER,
      prtInPh1MlDlciPrtIdx         INTEGER,
      prtInPh1MlDlciIdx            Integer32,

      prtInPh1MlDlciValid          INTEGER,
      prtInPh1MlDlciIConSlt        INTEGER,
      prtInPh1MlDlciIConPrt        INTEGER,
      prtInPh1MlDlciIConDlci       Integer32,

      prtInPh1MlDlciTxBc           INTEGER,
      prtInPh1MlDlciTxBe           INTEGER,
      prtInPh1MlDlciRxBc           INTEGER,
      prtInPh1MlDlciRxBe           INTEGER,

      prtInPh1MlDlciPriority       Integer32,

      prtInPh1MlDlciStatus         INTEGER
      }


prtInPh1MlDlciCnfgIdx OBJECT-TYPE
      SYNTAX  Integer32 (1..255)
      MAX-ACCESS  read-only
      STATUS  current
      DESCRIPTION
      "This attribute indicates the Idx of the Cnfg (1..100) being
       accessed.
       Idx 255 relates to the TmpCnfg. "
      ::= { prtInPh1MlDlciEntry 1}
-- In phase I only the values 1 (Cnfg1) and 255 (temp) are valid.

prtInPh1MlDlciSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      MAX-ACCESS  read-only
      STATUS  current
      DESCRIPTION
      "This attribute indicates a unique  slot  position where
       the card is inserted.
       In the ?004 Unit the entries io6(10)..io16) are not valid"
      ::= { prtInPh1MlDlciEntry 2}

prtInPh1MlDlciPrtIdx OBJECT-TYPE
      SYNTAX  INTEGER
 {
       inPrt1  (101) ,
       inPrt2  (102) ,
       inPrt3  (103)
       }
      MAX-ACCESS  read-only
      STATUS  current
      DESCRIPTION
      "This attribute indicates a unique internal port number.
       MPH.1/E1 and MPH.1/T1 cards have three internal ports."
      ::= { prtInPh1MlDlciEntry 3}

prtInPh1MlDlciIdx OBJECT-TYPE
      SYNTAX  Integer32 (1..991)
      MAX-ACCESS  read-only
      STATUS  current
      DESCRIPTION
      "This attribute indicates a unique index for each possible
       used dlci(16..991). When the protocol is not Multiplexing
       protocol, then its type is 'user' and the only valid index
       is 1."
      ::= { prtInPh1MlDlciEntry 4}

prtInPh1MlDlciValid OBJECT-TYPE
      SYNTAX  INTEGER
     {
     no  (2),
     yes (3)
     }
      MAX-ACCESS  read-write
      STATUS  current
      DESCRIPTION
      "This attribute indicates whether the attributes in this entry
       are valid or not. The user can add/delete pvc (dlci to dlci
       connection) by modifing this object"
      ::= { prtInPh1MlDlciEntry 5}

prtInPh1MlDlciIConSlt OBJECT-TYPE
      SYNTAX  INTEGER
 {
          noConnect(2),
    cl    (3),
       io1   (5),
       io2   (6),
       io3   (7),
       io4   (8),
       io5   (9),
       io6  (10),
       io7  (11),
       io8  (12),
       io9  (13),
       io10 (14),
       io11 (15),
       io12 (16)
       }
      MAX-ACCESS  read-write
      STATUS  current
      DESCRIPTION
      "This attribute indicates a unique slot position In the Mux
       (Agent) where the dlci is routed to.
       In the ?004 Unit the entries io6(10)..io16) are not valid"
      ::= { prtInPh1MlDlciEntry 6}

prtInPh1MlDlciIConPrt OBJECT-TYPE
      SYNTAX  INTEGER
      {
       exPrt1    (1) ,
       exPrt2    (2) ,
       exPrt3    (3) ,
       exPrt4    (4) ,
       exPrt5    (5) ,
       exPrt6    (6) ,
       exPrt7    (7) ,
       exPrt8    (8) ,
       exPrt9    (9) ,
       exPrt10  (10) ,
    clNMS    (99) ,
          noConnect (100),
       inPrt1  (101) ,
       inPrt2  (102) ,
       inPrt3  (103) ,
       inPrt4  (104) ,
       inPrt5  (105) ,
       inPrt6  (106) ,
       inPrt7  (107) ,
       inPrt8  (108) ,
       inPrt9  (109) ,
       inPrt10 (110) ,
    inPrt11 (111) ,
    inPrt12 (112)
       }
      MAX-ACCESS  read-write
      STATUS  current
      DESCRIPTION
      "This attribute indicates a unique port id which the dlci is
       routed to."
      ::= { prtInPh1MlDlciEntry 7}


prtInPh1MlDlciIConDlci OBJECT-TYPE
      SYNTAX  Integer32    (1..991)
      MAX-ACCESS  read-write
      STATUS  current
      DESCRIPTION
      "This attribute indicates a unique internal connection dlci
       number which the src dlci is routed to."
      ::= { prtInPh1MlDlciEntry 8}

prtInPh1MlDlciTxBc OBJECT-TYPE
      SYNTAX  INTEGER
        {
         full       (1),
         zero       (2),
         txBc9600bps    (3),
        txBc14200bps    (4),
        txBc19200bps    (5),
        txBc28800bps    (6),
        txBc32000bps    (7),
        txBc38400bps    (8),
        txBc48000bps    (9),
        txBc56000bps   (10),
        txBc57600bps   (11),
          txBc64Kbps   (12),
         txBc128Kbps   (13),
         txBc192Kbps   (14),
         txBc256Kbps   (15),
         txBc320Kbps   (16),
         txBc384Kbps   (17),
         txBc448Kbps   (18),
         txBc512Kbps   (19),
         txBc768Kbps   (20),
        txBc1024Kbps   (21)
        }
      MAX-ACCESS  read-write
      STATUS  current
      DESCRIPTION
      "This attribute indicates a unique Tx committed bandwidth on
       the user transmit line or at the port receive line."
      ::= { prtInPh1MlDlciEntry 9}


prtInPh1MlDlciTxBe OBJECT-TYPE
      SYNTAX  INTEGER
        {
         full       (1),
         zero       (2),
         txBe9600bps    (3),
        txBe14200bps    (4),
        txBe19200bps    (5),
        txBe28800bps    (6),
        txBe32000bps    (7),
        txBe38400bps    (8),
        txBe48000bps    (9),
        txBe56000bps   (10),
        txBe57600bps   (11),
          txBe64Kbps   (12),
         txBe128Kbps   (13),
         txBe192Kbps   (14),
         txBe256Kbps   (15),
         txBe320Kbps   (16),
         txBe384Kbps   (17),
         txBe448Kbps   (18),
         txBe512Kbps   (19),
         txBe768Kbps   (20),
        txBe1024Kbps   (21)
        }
      MAX-ACCESS  read-write
      STATUS  current
      DESCRIPTION
      "This attribute indicates a unique Tx excess bandwidth on the
      user transmit line or at the port receive line."
      ::= { prtInPh1MlDlciEntry 10}


prtInPh1MlDlciRxBc OBJECT-TYPE
      SYNTAX  INTEGER
        {
         full       (1),
         zero       (2),
         rxBc9600bps    (3),
        rxBc14200bps    (4),
        rxBc19200bps    (5),
        rxBc28800bps    (6),
        rxBc32000bps    (7),
        rxBc38400bps    (8),
        rxBc48000bps    (9),
        rxBc56000bps   (10),
        rxBc57600bps   (11),
          rxBc64Kbps   (12),
         rxBc128Kbps   (13),
         rxBc192Kbps   (14),
         rxBc256Kbps   (15),
         rxBc320Kbps   (16),
         rxBc384Kbps   (17),
         rxBc448Kbps   (18),
         rxBc512Kbps   (19),
         rxBc768Kbps   (20),
        rxBc1024Kbps   (21)
        }
      MAX-ACCESS  read-write
      STATUS  current
      DESCRIPTION
      "This attribute indicates a unique Rx committed bandwidth on
       the user receive line or at the port transmit line."
      ::= { prtInPh1MlDlciEntry 11}


prtInPh1MlDlciRxBe OBJECT-TYPE
      SYNTAX  INTEGER
        {
         full       (1),
         zero       (2),
         rxBe9600bps    (3),
        rxBe14200bps    (4),
        rxBe19200bps    (5),
        rxBe28800bps    (6),
        rxBe32000bps    (7),
        rxBe38400bps    (8),
        rxBe48000bps    (9),
        rxBe56000bps   (10),
        rxBe57600bps   (11),
          rxBe64Kbps   (12),
         rxBe128Kbps   (13),
         rxBe192Kbps   (14),
         rxBe256Kbps   (15),
         rxBe320Kbps   (16),
         rxBe384Kbps   (17),
         rxBe448Kbps   (18),
         rxBe512Kbps   (19),
         rxBe768Kbps   (20),
        rxBe1024Kbps   (21)
        }
      MAX-ACCESS  read-write
      STATUS  current
      DESCRIPTION
      "This attribute indicates a unique Rx excess bandwidth on the
      user receive line or at the port transmit line."
      ::= { prtInPh1MlDlciEntry 12}


prtInPh1MlDlciPriority OBJECT-TYPE
      SYNTAX  Integer32  (1..8)
      MAX-ACCESS  read-write
      STATUS  current
      DESCRIPTION
      "This attribute indicates a unique priority of the pcv.
       1 is the lowest priority and 8 is the highest priority."
      ::= { prtInPh1MlDlciEntry 13}



prtInPh1MlDlciStatus OBJECT-TYPE
      SYNTAX  INTEGER
 {
          disconnected (1),
          connected    (2)
       }
      MAX-ACCESS  read-only
      STATUS  current
      DESCRIPTION
      "This attribute indicates the status of the pvc. The status is
       disconnected(1) when one of the sides is programmed as
       not connected"
      ::= { prtInPh1MlDlciEntry 14}


--
-- ML-20 - High Speed Main Link card
-- External Port Objects
--
prtPhMlCnfgTable  OBJECT-TYPE
     SYNTAX SEQUENCE OF PrtPhMlCnfgEntry
     MAX-ACCESS not-accessible
     STATUS  current
     DESCRIPTION
      "The write operation into the Table Objects is valid only
       to the TmpCnfg entry."
     ::= {prtPh1MlCnfg 5}

prtPhMlCnfgEntry OBJECT-TYPE
      SYNTAX PrtPhMlCnfgEntry
      MAX-ACCESS not-accessible
      STATUS current
	DESCRIPTION  "An entry in table."
	INDEX {prtPhMlCnfgIdx, prtPhMlSltIdx, prtPhMlPrtIdx }
      ::= { prtPhMlCnfgTable 1}

PrtPhMlCnfgEntry ::=
      SEQUENCE {
      prtPhMlCnfgIdx        Integer32,
      prtPhMlSltIdx         INTEGER,
      prtPhMlPrtIdx         INTEGER,
      prtPhMlConnect        INTEGER,
      prtPhMlRate           INTEGER,
      prtPhMlCAS            INTEGER,
      prtPhMlClockMode      INTEGER,
      prtPhMlSatBuffer      INTEGER,
      prtPhMlDialProcess    INTEGER,
      prtPhMlSyncRestore    Integer32,
      prtPhMlBus            INTEGER,
      prtPhMlMfSyncSlot     INTEGER
      }


prtPhMlCnfgIdx OBJECT-TYPE
      SYNTAX  Integer32 (1..255)
      MAX-ACCESS  read-only
      STATUS  current
      DESCRIPTION
      "This attribute indicates the Idx of the Cnfg (1..100) being
       accessed.
       Idx 255 relates to the TmpCnfg. "
      ::= { prtPhMlCnfgEntry 1}
-- In phase I only the values 1 (Cnfg1) and 255 (temp) are valid.

prtPhMlSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      MAX-ACCESS  read-only
      STATUS  current
      DESCRIPTION
      "This attribute indicates a unique  slot  position where
       the module is inserted.
       In the ?004 Unit the entries io6(10)..io12(16) are not valid."
      ::= { prtPhMlCnfgEntry 2}

prtPhMlPrtIdx OBJECT-TYPE
      SYNTAX  INTEGER
       {
       exPrt1    (1)
       }
      MAX-ACCESS  read-only
      STATUS  current
      DESCRIPTION
      "This attribute indicates a unique  port number.
       ML-20 cards have just one external interface."
      ::= { prtPhMlCnfgEntry 3}

prtPhMlConnect OBJECT-TYPE
      SYNTAX  INTEGER
       {
  no  (2),
  yes (3)
       }
      MAX-ACCESS  read-write
      STATUS  current
      DESCRIPTION
      "This attribute indicates whether the port should be considered
       in any of the mux  algorithms."
      ::= {prtPhMlCnfgEntry 4}

prtPhMlRate     OBJECT-TYPE
      SYNTAX  INTEGER
       {
        r2x64eq128Kbps   (4),
        r3x64eq192Kbps   (6),
        r4x64eq256Kbps   (8),
        r5x64eq320Kbps  (10),
        r6x64eq384Kbps  (12),
        r7x64eq448Kbps  (14),
        r8x64eq512Kbps  (16),
        r9x64eq576Kbps  (18),
        r10x64eq640Kbps (20),
        r11x64eq704Kbps (22),
        r12x64eq768Kbps (24),
        r13x64eq832Kbps (26),
        r14x64eq896Kbps (28),
        r15x64eq960Kbps (30),
        r16x64eq1024Kbps(32),
        r17x64eq1088Kbps(34),
        r18x64eq1152Kbps(36),
        r19x64eq1216Kbps(38),
        r20x64eq1280Kbps(40),
        r21x64eq1344Kbps(42),
        r22x64eq1408Kbps(44),
        r23x64eq1472Kbps(46),
        r24x64eq1536Kbps(48),
        r25x64eq1600Kbps(50),
        r26x64eq1664Kbps(52),
        r27x64eq1728Kbps(54),
        r28x64eq1792Kbps(56),
        r29x64eq1856Kbps(58),
        r30x64eq1920Kbps(60),
        r31x64eq1984Kbps(62)
       }
      MAX-ACCESS  read-write
      STATUS  current
      DESCRIPTION
      "This attribute indicates the port speed."
      ::= {prtPhMlCnfgEntry 5}

prtPhMlCAS OBJECT-TYPE
      SYNTAX  INTEGER
       {
  no  (2),
  yes (3)
       }
      MAX-ACCESS  read-write
      STATUS  current
      DESCRIPTION
      "This attribute indicates whether Channel Associated
       Signaling (CAS) is used."
      ::= {prtPhMlCnfgEntry 6}

prtPhMlClockMode OBJECT-TYPE
      SYNTAX  INTEGER
       {
          dce     (2),
          ext-dce (3),
          dte     (4)
          }
      MAX-ACCESS  read-write
      STATUS  current
      DESCRIPTION
      "Clock mode."
      ::= { prtPhMlCnfgEntry 7}

prtPhMlSatBuffer OBJECT-TYPE
      SYNTAX  INTEGER
       {
  notApplicable (1),
  no  (2),
  yes (3)
       }
      MAX-ACCESS  read-write
      STATUS  current
      DESCRIPTION
      "Satellite Buffer (+/- 256)."
      ::= {prtPhMlCnfgEntry 8}

prtPhMlDialProcess OBJECT-TYPE
      SYNTAX  INTEGER
       {
  notApplicable (1),
  no            (2),
  callIn        (3),
  callOut       (4)
       }
      MAX-ACCESS  read-write
      STATUS  current
      DESCRIPTION
      "Dial Process."
      ::= {prtPhMlCnfgEntry 9}

prtPhMlSyncRestore OBJECT-TYPE
      SYNTAX  Integer32 (0..10)
      MAX-ACCESS  read-write
      STATUS  current
      DESCRIPTION
      "Sync Restoration time, in seconds.
       notApplicable=0. "
      ::= {prtPhMlCnfgEntry 10}

prtPhMlBus OBJECT-TYPE
      SYNTAX  INTEGER
       {
  none (1),
  busA (2),
  busB (3)
       }
      MAX-ACCESS  read-write
      STATUS  current
      DESCRIPTION
      "The TDM BUS this port is linked to."
      ::= {prtPhMlCnfgEntry 11}

prtPhMlMfSyncSlot  OBJECT-TYPE
      SYNTAX  INTEGER
       {
          none  (2),
          io1   (5),
          io2   (6),
          io3   (7),
          io4   (8),
          io5   (9),
          io6  (10),
          io7  (11),
          io8  (12),
          io9  (13),
          io10 (14),
          io11 (15),
          io12 (16)
       }
      MAX-ACCESS  read-write
      STATUS  current
      DESCRIPTION
      "This attribute indicates whether the sync is synchronized
       according to a certain card and the slot of this card.
       This operation is required in order to bypass signaling of
       PCM voice channels.
       In the ?004 Unit the entries io6(10)..io12(16) are not valid"
      ::= {prtPhMlCnfgEntry 12}


-- This table is an extension for new version of MAXcess
-- modules.
prtLogicalCnfgTable  OBJECT-TYPE
     SYNTAX SEQUENCE OF PrtLogicalCnfgEntry
     MAX-ACCESS not-accessible
     STATUS  current
     DESCRIPTION
      "The write operation into the Table Objects is valid only
       to the TmpCnfg entry."
     ::= {prtLogicalCnfg 1}

prtLogicalCnfgEntry OBJECT-TYPE
      SYNTAX PrtLogicalCnfgEntry
      MAX-ACCESS not-accessible
      STATUS current
	DESCRIPTION  "An entry in table."
	INDEX {prtLogicalCnfgIdx, prtLogicalSltIdx, prtLogicalPrtIdx }
      ::= { prtLogicalCnfgTable 1}

PrtLogicalCnfgEntry ::=
      SEQUENCE {
      prtLogicalCnfgIdx   Integer32,
      prtLogicalSltIdx    INTEGER,
      prtLogicalPrtIdx   Integer32,
      prtLogicalConnect    INTEGER,
      prtLogicalFunction        INTEGER,
      prtLogicalRowStatus      RowStatus
}

prtLogicalCnfgIdx OBJECT-TYPE
      SYNTAX  Integer32 (1..255)
      MAX-ACCESS  read-only
      STATUS  current
      DESCRIPTION
      "This attribute indicates the Idx of the Cnfg (1..100) being
       accessed.
       Idx 255 relates to the TmpCnfg. "
      ::= { prtLogicalCnfgEntry 1}
-- In phase I only the values 1 (Cnfg1) and 255 (temp) are valid.

prtLogicalSltIdx OBJECT-TYPE
      SYNTAX  INTEGER
            {
              io1   (5),
              io2   (6),
              io3   (7),
              io4   (8),
              io5   (9),
              io6  (10),
              io7  (11),
              io8  (12),
              io9  (13),
              io10 (14),
              io11 (15),
              io12 (16),
       notApplicable(255)
            }
      MAX-ACCESS  read-only
      STATUS  current
      DESCRIPTION
        "Slot Index.
         For ISDN BRI Ports of MX300/30,
    io1(5) = isdn1(5) and io2(6) = isdn2(6)."
      ::= { prtLogicalCnfgEntry 2}

prtLogicalPrtIdx OBJECT-TYPE
      SYNTAX  Integer32
      MAX-ACCESS  read-only
      STATUS  current
      DESCRIPTION
      "This attribute indicates a unique  port number.
       This port number should be an internal port number:
        inPrt1(101)->inPrt50(150), linkSel1(200)->linkSel50(250),
        encaps1(300)-> encaps50(350), huntGr1(101) -> huntGr10(110)."
      ::= { prtLogicalCnfgEntry 3}

prtLogicalConnect OBJECT-TYPE
      SYNTAX  INTEGER
              {
                no  (2),
             yes (3)
              }
      MAX-ACCESS  read-create
      STATUS  current
      DESCRIPTION
      "This attribute indicates whether the port should be considered
       in any of the mux  algorithms."
      ::= { prtLogicalCnfgEntry 4}

prtLogicalFunction  OBJECT-TYPE
      SYNTAX  INTEGER
              {
                notApplicable(1),
                linkSelector(2),
         encapsulator(3),
   huntGroup(4)
              }
     MAX-ACCESS   read-create
     STATUS   current
     DESCRIPTION
     "This parameter defines the function of the relevant channel."
     ::= { prtLogicalCnfgEntry 5 }

prtLogicalRowStatus  OBJECT-TYPE
     SYNTAX  RowStatus
     MAX-ACCESS   read-create
     STATUS   current
     DESCRIPTION
     "This parameter allows the NMS to create/delete logical ports.
      The only possible supported RowStatus vaules are
      active (1) and destroy (6)."
     ::= { prtLogicalCnfgEntry 6 }


-- This group contains management information for the
-- link selector function.

linkSelectorCnfgTable  OBJECT-TYPE
     SYNTAX SEQUENCE OF LinkSelectorCnfgEntry
     MAX-ACCESS not-accessible
     STATUS  current
     DESCRIPTION
      "The write operation into the Table Objects is valid only
       to the TmpCnfg entry."
     ::= { prtLogicalCnfg 2}

linkSelectorCnfgEntry OBJECT-TYPE
      SYNTAX LinkSelectorCnfgEntry
      MAX-ACCESS not-accessible
      STATUS current
	DESCRIPTION  "An entry in table."
	INDEX {linkSelectorCnfgIdx, linkSelectorSltIdx, linkSelectorPrtIdx }
      ::= { linkSelectorCnfgTable 1}

LinkSelectorCnfgEntry ::=
      SEQUENCE {
      linkSelectorCnfgIdx      Integer32,
      linkSelectorSltIdx         INTEGER,
      linkSelectorPrtIdx         Integer32,
      linkSelectorMaxIdleTime      Integer32,
      linkSelectorMode INTEGER,
      linkSelectorRevert INTEGER,
      linkSelectorMinBUSession      Integer32 
	}

linkSelectorCnfgIdx OBJECT-TYPE
      SYNTAX  Integer32 (1..255)
      MAX-ACCESS  read-only
      STATUS  current
      DESCRIPTION
      "This attribute indicates the Idx of
      the Cnfg (1..100) being accessed.
       Idx 255 relates to the TmpCnfg. "
      ::= { linkSelectorCnfgEntry 1}
-- In phase I only the values 1 (Cnfg1) and 255 (temp) are valid.

linkSelectorSltIdx OBJECT-TYPE
      SYNTAX  INTEGER
            {
              io1   (5),
              io2   (6),
              io3   (7),
              io4   (8),
              io5   (9),
              io6  (10),
              io7  (11),
              io8  (12),
              io9  (13),
              io10 (14),
              io11 (15),
              io12 (16),
       notApplicable(255)
            }
      MAX-ACCESS  read-only
      STATUS  current
      DESCRIPTION
        "Slot Index"
      ::= { linkSelectorCnfgEntry 2}

linkSelectorPrtIdx OBJECT-TYPE
      SYNTAX  Integer32
      MAX-ACCESS  read-only
      STATUS  current
      DESCRIPTION
      "This attribute indicates a unique  port number.
       This port number should be internal port number:
       higher or equal to linkSeL1(201)."
      ::= { linkSelectorCnfgEntry 3}

linkSelectorMaxIdleTime OBJECT-TYPE
     SYNTAX  Integer32 (0..255)
     MAX-ACCESS   read-write
     STATUS   current
     DESCRIPTION
     "Move to higher prioritized connected link
     after this period of seconds of silence on the current link.
     0=move immediately to higher prioritized connected link.
     UNIT is seconds."
     DEFVAL { 0 }
::= {linkSelectorCnfgEntry 4}

linkSelectorMode OBJECT-TYPE
      SYNTAX  INTEGER { notApplicable(1),
    backup(2), bod(3)       }
      MAX-ACCESS   read-write
     STATUS   current
     DESCRIPTION
     " If the link selector is in mode:
      backup(2)=then the link with the lower priority will be
                used in case of failure of the higher priority link,
      bod(3)=bandwidth on demand or dynamic bandwidth allocation
             means that links with lower priority will be used
             whenever additional bandwidth is required. "
     DEFVAL { backup }
::= {linkSelectorCnfgEntry 5}

linkSelectorRevert OBJECT-TYPE
      SYNTAX  INTEGER { notApplicable(1),
   auto(2), manual(3)       }
      MAX-ACCESS   read-write
     STATUS   current
     DESCRIPTION
     " If the link selector is in mode backup:
      auto(2)=return automatically to Main link when it is OK.
      manual(3)=stays connected to backup link."
     DEFVAL { auto }
::= {linkSelectorCnfgEntry 6}

linkSelectorMinBUSession     OBJECT-TYPE
     SYNTAX  Integer32 (1..255)
     MAX-ACCESS   read-write
     STATUS   current
     DESCRIPTION
     "Minimum duration of a backup session before
     returning to Main Link. Relevant in Backup Mode and
     when Revert is auto(2).  Value 255 is for NEVER which
     means never return to Main Link.
     UNIT is minutes."
     DEFVAL { 10 }
::= {linkSelectorCnfgEntry 7}

-- Prioritized Links
linkSelectorPLinkTable  OBJECT-TYPE
     SYNTAX SEQUENCE OF LinkSelectorPLinkEntry
     MAX-ACCESS not-accessible
     STATUS  current
     DESCRIPTION
      "The write operation into the Table Objects is valid only
       to the TmpCnfg entry."
     ::= { prtLogicalCnfg 3}

linkSelectorPLinkEntry OBJECT-TYPE
      SYNTAX LinkSelectorPLinkEntry
      MAX-ACCESS not-accessible
      STATUS current
	DESCRIPTION  "An entry in table."
	INDEX {pLinkCnfgIdx, pLinkSltIdx, pLinkPrtIdx, pLinkIdx }
      ::= { linkSelectorPLinkTable 1}

LinkSelectorPLinkEntry ::=
      SEQUENCE {
      pLinkCnfgIdx      Integer32,
      pLinkSltIdx   INTEGER,
      pLinkPrtIdx       Integer32,
      pLinkIdx         Integer32,
      pLinkSlotNu       INTEGER,
      pLinkPortNu       Integer32,
      pLinkPrioNu       Integer32,
      pLinkVRate        INTEGER
}

pLinkCnfgIdx OBJECT-TYPE
      SYNTAX  Integer32 (1..255)
      MAX-ACCESS  read-only
      STATUS  current
      DESCRIPTION
     "This attribute indicates the Idx of the Cnfg (1..100) being
       accessed.
       Idx 255 relates to the TmpCnfg. "
      ::= { linkSelectorPLinkEntry 1}
-- In phase I only the values 1 (Cnfg1) and 255 (temp) are valid.

pLinkSltIdx OBJECT-TYPE
      SYNTAX  INTEGER
            {
              io1   (5),
              io2   (6),
              io3   (7),
              io4   (8),
              io5   (9),
              io6  (10),
              io7  (11),
              io8  (12),
              io9  (13),
              io10 (14),
              io11 (15),
              io12 (16),
       notApplicable(255)
            }
      MAX-ACCESS  read-only
      STATUS  current
      DESCRIPTION
        "Slot Index"
      ::= { linkSelectorPLinkEntry 2}

pLinkPrtIdx OBJECT-TYPE
      SYNTAX  Integer32(200..250)
      MAX-ACCESS  read-only
      STATUS  current
      DESCRIPTION
      "This attribute indicates a unique  port number.
       This port number should be the link selector number."
::= { linkSelectorPLinkEntry 3}


pLinkIdx OBJECT-TYPE
      SYNTAX  Integer32 (1..8)
      MAX-ACCESS   read-only
     STATUS   current
     DESCRIPTION
     "This index is the row number."
::= { linkSelectorPLinkEntry 4}

pLinkSlotNu OBJECT-TYPE
      SYNTAX  INTEGER {
      noConnect (2), cl(3),
        io1(5),
        io2(6),
        io3(7),
        io4(8),
        io5(9),
        io6(10),
        io7(11),
        io8(12),
        io9(13),
        io10(14),
        io11(15),
        io12(16),
        notApplicable(255)
       }
     MAX-ACCESS   read-write
     STATUS   current
     DESCRIPTION
     "The slot of the prioritized link.
     For ISDN BRI ports of MX300/30,
 io1(5) = isdn1(5) and io2(6) = isdn2(6)."
     DEFVAL { noConnect }
::= { linkSelectorPLinkEntry 5 }

pLinkPortNu OBJECT-TYPE
      SYNTAX  Integer32
      MAX-ACCESS   read-write
      STATUS   current
      DESCRIPTION
      "The port of the prioritized link.
      Value 100 is for noConnect."
      DEFVAL { 100 }
::= { linkSelectorPLinkEntry 6 }

pLinkPrioNu OBJECT-TYPE
      SYNTAX  Integer32(1..8)
      MAX-ACCESS   read-write
      STATUS   current
      DESCRIPTION
      "The priority of the prioritized link.
       MIN=1...., MAX=8."
::= { linkSelectorPLinkEntry 7 }

pLinkVRate OBJECT-TYPE
       SYNTAX INTEGER {
        r1x56eq56Kbps    (1),
        r1x64eq64Kbps    (2),
        r2x56eq112Kbps   (3),
        r2x64eq128Kbps   (4),
        r3x56eq168Kbps   (5),
        r3x64eq192Kbps   (6),
        r4x56eq224Kbps   (7),
        r4x64eq256Kbps   (8),
        r5x56eq280Kbps   (9),
        r5x64eq320Kbps  (10),
        r6x56eq336Kbps  (11),
        r6x64eq384Kbps  (12),
        r7x56eq392Kbps  (13),
        r7x64eq448Kbps  (14),
        r8x56eq448Kbps  (15),
        r8x64eq512Kbps  (16),
        r9x56eq504Kbps  (17),
        r9x64eq576Kbps  (18),
        r10x56eq560Kbps (19),
        r10x64eq640Kbps (20),
        r11x56eq616Kbps (21),
        r11x64eq704Kbps (22),
        r12x56eq672Kbps (23),
        r12x64eq768Kbps (24),
        r13x56eq728Kbps (25),
        r13x64eq832Kbps (26),
        r14x56eq784Kbps (27),
        r14x64eq896Kbps (28),
        r15x56eq840Kbps (29),
        r15x64eq960Kbps (30),
        r16x56eq896Kbps (31),
        r16x64eq1024Kbps(32),
        r17x56eq952Kbps (33),
        r17x64eq1088Kbps(34),
        r18x56eq1008Kbps(35),
        r18x64eq1152Kbps(36),
        r19x56eq1064Kbps(37),
        r19x64eq1216Kbps(38),
        r20x56eq1120Kbps(39),
        r20x64eq1280Kbps(40),
        r21x56eq1176Kbps(41),
        r21x64eq1344Kbps(42),
        r22x56eq1232Kbps(43),
        r22x64eq1408Kbps(44),
        r23x56eq1288Kbps(45),
        r23x64eq1472Kbps(46),
        r24x56eq1344Kbps(47),
        r24x64eq1536Kbps(48),
        r25x56eq1400Kbps(49),
        r25x64eq1600Kbps(50),
        r26x56eq1456Kbps(51),
        r26x64eq1664Kbps(52),
        r27x56eq1512Kbps(53),
        r27x64eq1728Kbps(54),
        r28x56eq1568Kbps(55),
        r28x64eq1792Kbps(56),
        r29x56eq1624Kbps(57),
        r29x64eq1856Kbps(58),
        r30x56eq1680Kbps(59),
        r30x64eq1920Kbps(60),
        r31x56eq1736Kbps(61),
        r31x64eq1984Kbps(62),
        noRate(100)
       }
       MAX-ACCESS   read-write
       STATUS   current
       DESCRIPTION
     "The rate to use with this link."
       DEFVAL { noRate }
::= { linkSelectorPLinkEntry 8 }


--
-- Megaplex or Kilomux ?000/?004 MPH.1/3 High speed packet data cards.
-- Megaplex or Kilomux ?000/?004 MPL.6 Low speed packet data cards.
--      (Mph1, Mph3, Mpl6)
-- Maxcess 3000/3004 MLS-3/6, MHS-1/3
--
-- prtExPhPlCnfgTable  OBJECT IDENTIFIER ::= {prtPhPlCnfg 1}
-- prtExPhPlDlciTable  OBJECT IDENTIFIER ::= {prtPhPlCnfg 2}
-- prtExPhPlModemTable OBJECT IDENTIFIER ::= {prtPhPlCnfg 3}

-- Mph.1 Mph.3 Mpl.6/ Kphs.1 Kphs.3 Mls.3 Mls.6 Mhs.1 Mhs.3
-- External port objects table

prtExPhPlCnfgTable  OBJECT-TYPE
      SYNTAX SEQUENCE OF PrtExPhPlCnfgEntry
      MAX-ACCESS not-accessible
      STATUS  current
      DESCRIPTION "The write operation into the Table Objects is
      valid only to the TmpCnfg entry."
      ::= {prtPhPlCnfg 1}

prtExPhPlCnfgEntry OBJECT-TYPE
      SYNTAX PrtExPhPlCnfgEntry
      MAX-ACCESS not-accessible
      STATUS current
	DESCRIPTION  "An entry in table."
	INDEX {prtExPhPlCnfgIdx, prtExPhPlSltIdx, prtExPhPlPrtIdx}
      ::= { prtExPhPlCnfgTable 1}

PrtExPhPlCnfgEntry ::=
      SEQUENCE {
      prtExPhPlCnfgIdx            Integer32,
      prtExPhPlSltIdx             INTEGER,
      prtExPhPlPrtIdx             INTEGER,
      prtExPhPlConnect            INTEGER,
      prtExPhPlHRate              INTEGER,
      prtExPhPlLRate              INTEGER,
      prtExPhPlProtocol           INTEGER,
      prtExPhPlConnectionTyp      INTEGER,
      prtExPhPlClkMode            INTEGER,
      prtExPhPlDceClkSrc          INTEGER,
      prtExPhPlCongResponse       INTEGER,
      prtExPhPlCongLevel          Integer32,
      prtExPhPlTc                 INTEGER,
      prtExPhPlFlowControl        INTEGER,
      prtExPhPlDcdRts             INTEGER,
      prtExPhPlDcdRtsControlPath  INTEGER,
      prtExPhPlDataBits           INTEGER,
      prtExPhPlParity             INTEGER,
      prtExPhPlStopBits           INTEGER,
      prtExPhPlLXon               Integer32,
      prtExPhPlLXoff              Integer32,
	  prtExPhPlFrMngProt          INTEGER,
	  prtExPhPlEnqPeriod          Integer32,
	  prtExPhPlFullRptPeriod      Integer32,
	  prtExPhPlFrWindowSize       Integer32,
	  prtExPhPlErrorsThreshold    Integer32,
	  prtExPhPlPvcCreateMsg       INTEGER,
	  prtExPhPlCllmMsg            INTEGER,
	  prtExPhPlProtDelayLevel     INTEGER,
	  prtExPhPlClockEncoding      INTEGER,
	  prtExPhPlMinSeparators      Integer32,
	  prtExPhPlCcittCrc           INTEGER,
	  prtExPhPlFrameSeparator     INTEGER,
	  prtExPhPlIdleCode           Integer32,
	  prtExPhPlJitter             Integer32 
	}

prtExPhPlCnfgIdx OBJECT-TYPE
      SYNTAX  Integer32 (1..255)
      MAX-ACCESS  read-only
      STATUS  current
      DESCRIPTION
      "This attribute indicates the Idx of the Cnfg (1..100) being
       accessed.
       Idx 255 relates to the TmpCnfg. "
      ::= { prtExPhPlCnfgEntry 1}
-- In phase I only the values 1 (Cnfg1) and 255 (temp) are valid.

prtExPhPlSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16),
    notApplicable (255)
     }
      MAX-ACCESS  read-only
      STATUS  current
      DESCRIPTION
      "This attribute indicates a unique  slot  position where
       the card is inserted.
       In the ?004 Unit the entries io6(10)..io12(16) are not valid"
      ::= { prtExPhPlCnfgEntry 2}

prtExPhPlPrtIdx OBJECT-TYPE
      SYNTAX  INTEGER
 {
          exPrt1  (1) ,
          exPrt2  (2) ,
          exPrt3  (3) ,
          exPrt4  (4) ,
          exPrt5  (5) ,
          exPrt6  (6)
       }
      MAX-ACCESS read-only
      STATUS  current
      DESCRIPTION
      "This attribute indicates a unique port number.
       In case of PH.1 card, only exPrt(1) is valid."
      ::= { prtExPhPlCnfgEntry 3}

prtExPhPlConnect OBJECT-TYPE
      SYNTAX  INTEGER
       {
  no  (2),
  yes (3)
       }
      MAX-ACCESS  read-write
      STATUS  current
      DESCRIPTION
      "This attribute indicates whether the port should be considered
       in any of the mux  algorithms."
      ::= { prtExPhPlCnfgEntry 4}

prtExPhPlHRate OBJECT-TYPE
      SYNTAX  INTEGER
       {
        notApplicable (1),
        r32KbpsNLE    (2),
        r48KbpsNLE    (3),
        r56KbpsNLE    (4),
        r64KbpsNLE    (5),
        r112KbpsNLE   (6),
        r128KbpsNLE   (7),
        r168KbpsNLE   (8),
        r192KbpsNLE   (9),
        r224KbpsNLE  (10),
        r256KbpsNLE  (11),
        r280KbpsE    (12),
        r320KbpsE    (13),
        r336KbpsNLE  (14),
        r384KbpsNLE  (15),
        r392KbpsE    (16),
        r448KbpsNLE  (17),
        r504KbpsLE   (18), -- r504KbpsE 
        r512KbpsE    (19), -- r512KbpsNLE			  
        r560KbpsE    (20),
        r576KbpsLE   (21), -- r576KbpsE
        r616KbpsE    (22),
        r640KbpsE    (23),
        r672KbpsNLE  (24),
        r704KbpsE    (25),
        r728KbpsE    (26),
        r768KbpsNLE  (27),
        r784KbpsE    (28),
        r832KbpsE    (29),
        r840KbpsE    (30),
        r896KbpsNLE  (31),
        r952KbpsE    (32),
        r960KbpsE    (33),
       r1008KbpsLE   (34), -- r1008KbpsE
       r1024KbpsE    (35), -- r1024KbpsNLE
       r1064KbpsE    (36),
       r1088KbpsE    (37),
       r1120KbpsE    (38),
       r1152KbpsLE   (39), -- r1152KbpsE
       r1176KbpsE    (40),
       r1216KbpsE    (41),
       r1232KbpsE    (42),
       r1280KbpsE    (43),
       r1288KbpsE    (44),
       r1344KbpsNLE  (45),
       r1400KbpsE    (46),
       r1408KbpsE    (47),
       r1456KbpsE    (48),
       r1472KbpsE    (49),
       r1512KbpsE    (50),
       r1536KbpsE    (51), -- r1536KbpsNLE
       r1568KbpsE    (52),
       r1600KbpsE    (53),
       r1624KbpsE    (54),
       r1664KbpsE    (55),
       r1680KbpsE    (56),
       r1728KbpsE    (57),
       r1736KbpsE    (58),
       r1792KbpsNLE  (59),
       r1856KbpsE    (60),
       r1920KbpsE    (61),
       r1984KbpsE    (62),
       r2048KbpsE    (63), -- r2048KbpsNLE
--
--  Additional rates for: MAXcess, MP2100h 
--
       r9d6KbpsNLE   (65),
       r14d4KbpsNLE  (66),
       r16KbpsNLE    (67),
       r19d2KbpsNLE  (68),
       r28d8KbpsNLE  (69),
       r38d4KbpsNLE  (70),
       r57d6KbpsNLE  (71), -- For Mx 30/300 Only
       r115d2KbpsNLE (72),  -- For Mx 30/300 Only
       r24000bps     (73)
       }
      MAX-ACCESS  read-write
      STATUS  current
      DESCRIPTION
      "This attribute indicates the port speed for HIGH speed cards.
       The card has limitations about the maximum sigma channel
       speeds and about the possible rates for each clock mode .
       N - The rate is valid for DCE and EXT-DCE Nodal clock mode.
       L - The rate is valid for DCE and EXT-DCE Local clock mode.
       E - The rate is valid for DTE External clock mode.
       'r9d6KbpsNLE' means rate of 9.6 Kbps ('d'=dot).
       
       Note: Some rate attributes have been changed. As the MIB was already
             released with the old attributes, the names of the options were
             not changed. The new names + attributes are in a comment.
             Example:   r2048KbpsE (63), -- r2048KbpsNLE"
      ::= { prtExPhPlCnfgEntry 5}

prtExPhPlLRate  OBJECT-TYPE
      SYNTAX  INTEGER
       {
          notApplicable  (1),
          r300bpsNLE     (2),
          r600bpsNLE     (3),
          r800bpsNLE     (4),
          r1200bpsNLE    (5),
          r2400bpsNLE    (6),
          r4800bpsNLE    (7),
          r9600bpsNLE    (8),
          r14400bpsLE    (9),  -- r14400bpsNLE
          r19200bpsNLE   (10),
          r28800bpsLE    (11), -- r28800bpsNLE
          r32000bpsNLE   (12),
          r38400bpsNLE   (13),
          r48000bpsNLE   (14),
          r56000bpsNLE   (15),
          r57600bpsLE    (16), -- r57600bpsNLE
          r64000bpsNLE   (17),
          r112000bps     (18), -- For Mx 30/300 Only: r112000bpsNLE 
          r115200bps     (19), -- For Mx 30/300 Only: r115200bpsNLE
--
-- additional rates
--
         r16000bpsNLE    (20),
         r100bpsNLE      (21), -- For Mx 30/300 Only
         r128000bps      (22), -- For Mx 30/300 Only
         r24000bps       (23)
       }
      MAX-ACCESS  read-write
      STATUS  current
      DESCRIPTION
      "This attribute indicates the port speed for LOW speed cards.
       The card has limitations about the possible rates for each
       clock mode.
       N - The rate is valid for DCE and EXT-DCE Nodal clock mode.
       L - The rate is valid for DCE and EXT-DCE Local clock mode.
       E - The rate is valid for DTE External clock mode.

       Note: Some rate attributes have been changed. As the MIB was already
             released with the old attributes, the names of the options were
             not changed. The new names + attributes are in a comment.
             Example:  r57600bpsLE (16), -- r57600bpsNLE  "

      ::= { prtExPhPlCnfgEntry 6}

prtExPhPlProtocol OBJECT-TYPE
      SYNTAX  INTEGER
     {
        fr                 (1),
        frPlus             (2),
        pCellRelay         (3),
        hdlcSdlc           (4),
        transparentHdlc    (5),
        async              (6),
        asyncReliable      (7),
        activePPP          (8),
        slip               (9),
        pppAgent           (10),
        slipAgent          (11),
        transparent        (12),
        sna                (13)
     }
      MAX-ACCESS  read-write
      STATUS  current
      DESCRIPTION
      "This object indicates the applied protocol."
      ::= { prtExPhPlCnfgEntry 7}

prtExPhPlConnectionTyp OBJECT-TYPE
      SYNTAX  INTEGER
     {
     sameNetManaged  (1),
     sameNetNotMana  (2),
     user            (3),
     otherNet        (4),
     pubNet          (5),
        notApplicable (255)
     }
      MAX-ACCESS  read-write
      STATUS  current
      DESCRIPTION
      "This attribute indicates the link connection type.
       It is required for three reasons:
     FR/CR Inband management opration (LMI,CLMM...).
     CIR check.
     NMS network management.

       SameNetManaged - indicates network internal line.
       SameNetMotMana - indicates network internal line, but the
                        remote mux is not managed by the NMS.

       User           - User to Network Interface.
       OtherNet       - Network To Network Interface.
       PubNet         - Access Mux To PubNet Interface."
      ::= { prtExPhPlCnfgEntry 8}

prtExPhPlClkMode OBJECT-TYPE
      SYNTAX  INTEGER
              {
                  dce     (1),
                  extDce  (2),
                  dte     (3),
      int     (4),
      lbt     (5)
              }
      MAX-ACCESS  read-write
      STATUS  current
      DESCRIPTION
      "Clock mode."
      ::= { prtExPhPlCnfgEntry 9}

prtExPhPlDceClkSrc OBJECT-TYPE
      SYNTAX  INTEGER
              {
                  notApplicable (1),
                  local         (2),
                  nodalTiming   (3)
              }
      MAX-ACCESS  read-write
      STATUS  current
      DESCRIPTION
      "This attribute indicates the source of the clock when working
       in dce or ext-dce clock mode.
       notApplicable(1) - is applied for dte(3) and lbt(5) clock modes.
	                      When clock mode is dte, the clock source is
						  always external, therefore this object's value is
						  notApplicable.
       local(2) and nodalTiming(3) - are valid in dce(1), extDce(2)
                                     or int(4) clock modes.
       The recommended clock source is local(2)."
      ::= { prtExPhPlCnfgEntry 10}

prtExPhPlCongResponse OBJECT-TYPE
      SYNTAX  INTEGER
     {
        no                  (2),
        flowControl         (3), -- duplex, to/from flow control
        toFlowControl       (4)  -- simplex , only to flow control
     }
      MAX-ACCESS  read-write
      STATUS  current
      DESCRIPTION
"This attribute indicates how to handle the congestion indication
 to/from the mux internal connection side (for example
 transmit/received becn to/from the network).
   no           - do nothing
   flowControl  - translates the congestion indication between the
                  port and the internal connection port according
                  to the definition of the prtInPh1MlFlowControl
                  parameters. The operation is done on both
                  directions.
   toFlowControl- translates the backward congestion indication
                  received from the internal connection port
                  (normally the network side) to flow control and
                  do nothing in the other direction."
      ::= { prtExPhPlCnfgEntry 11}

prtExPhPlCongLevel OBJECT-TYPE
      SYNTAX  Integer32 (0..70)
      MAX-ACCESS  read-write
      STATUS  current
      DESCRIPTION
      "This attribute indicates the level of delayed data in
       precents of total available dynamic memory,
       for which the port will start to operate as congested.
       The resolution of the parameter is 5 percent."
      ::= { prtExPhPlCnfgEntry 12}

prtExPhPlTc OBJECT-TYPE
      SYNTAX  INTEGER
          {
          tc1sec  (1),
          tc2sec  (2),
          tc3sec  (3),
          tc4sec  (4),
    notApplicable (255)
          }
      MAX-ACCESS  read-write
      STATUS  current
      DESCRIPTION
      "This attribute indicates the Tc parameter which is the time
       period of the sliding window in which the Bc/Be are tested.
       The value of this parameter is identical for all the ports
       of a  specific card ."
      ::= { prtExPhPlCnfgEntry 13}

prtExPhPlFlowControl OBJECT-TYPE
      SYNTAX  INTEGER
     {
        none                (2),
        fecnBecn            (3),
        xonXoff             (4),
        dtrCts              (5),
        speedReduction      (6)   -- simplex response only congestion to flow control
     }
      MAX-ACCESS  read-write
      STATUS  current
      DESCRIPTION
      "This attribute indicates the required flow control betweeen
       the port and the remote equipment.
       fecnBecn - is valid only for FR, FR+ and CR protocols.
       xonXoff,dtrCts - are valid only for Async protocols.
       speedReduction - is valid only for DLC protocol when the
                        Clock Mode is DCE and the Clock Source is
                        Local."
      ::= { prtExPhPlCnfgEntry 14}

prtExPhPlDcdRts OBJECT-TYPE
      SYNTAX  INTEGER
     {
        notApplicable     (1),
        on                (2),
        endToEnd          (3)
     }
      MAX-ACCESS  read-write
      STATUS  current
      DESCRIPTION
      "Protocol may require end to end connect indication over the
       network. End to end link connection establishment over the
       FR network will be indicated to the user by using DCD or
       RTS control signals, depending on the clock mode: DCE or
       DTE respectively.
       The options are :
       - On :
              DCD(DCE)/RTS(DTE) will be constantly ON no matter
              if the End to End connection is established or not.
       - End to End:
              The DCD(DCE)/RTS(DTE) will be according to the status
              of the End to End connection."
      ::= { prtExPhPlCnfgEntry 15}

prtExPhPlDcdRtsControlPath OBJECT-TYPE
      SYNTAX  INTEGER
     {
        notApplicable     (1),
        off               (2),
        on                (3)
     }
      MAX-ACCESS  read-write
      STATUS  current
      DESCRIPTION
      "Protocol may require end to end connect indication over the
       network. This parameter defines whether to take the user
       connection status (RTS(DCE)/DCD(DTE)) and forward it to the
       network side.
      - on : Transmit active connection to the network regardless
              the RTS/DCD control lines status.
      - off: Transmit active connection to the network according
              to the status of the RTS/DCD pin. "
      ::= { prtExPhPlCnfgEntry 16}

prtExPhPlDataBits OBJECT-TYPE
      SYNTAX  INTEGER
         {
         notApplicable  (1),
         dataBits7Bits (2),
         dataBits8Bits (3)
         }
      MAX-ACCESS  read-write
      STATUS  current
      DESCRIPTION
      "This attribute indicates the number of data bits in async
       frame.
       It is relevant only for Async protocols."
      ::= { prtExPhPlCnfgEntry 17}

prtExPhPlParity OBJECT-TYPE
      SYNTAX  INTEGER
         {
         notApplicable  (1),
         odd            (2),
         even           (3),
         none           (4)
         }
      MAX-ACCESS  read-write
      STATUS  current
      DESCRIPTION
      "This attribute indicates the parity operation mode in
       async frame.
       It is relevant only for Async protocols."
      ::= { prtExPhPlCnfgEntry 18}

prtExPhPlStopBits OBJECT-TYPE
      SYNTAX  INTEGER
         {
         notApplicable  (1),
         sb1Bit           (2),
         sb1dot5Bits      (3),
         sb2Bits          (4)
         }
      MAX-ACCESS  read-write
      STATUS  current
      DESCRIPTION
      "This attribute indicates the minimum number of stop bits
       in the tx async frame.
       It is relevant only for Async protocols."
      ::= { prtExPhPlCnfgEntry 19}

prtExPhPlLXon OBJECT-TYPE
      SYNTAX  Integer32
      MAX-ACCESS  read-write
      STATUS  current
      DESCRIPTION
      "This attribute indicates the character used as X-On to
       notify receive enable.
       This parameter is valid only for async protocols.
    Valid values: 0..255.
       The value 256 indicates that it's not applicable "
      ::= { prtExPhPlCnfgEntry 20}

prtExPhPlLXoff OBJECT-TYPE
      SYNTAX  Integer32
      MAX-ACCESS  read-write
      STATUS  current
      DESCRIPTION
      "This attribute indicates the character used as X-Off to
       notify receive disable.
       This parameter is valid only for async protocols.
    Valid values: 0..255.
       The value 256 indicates that it's not applicable "
      ::= { prtExPhPlCnfgEntry 21}

prtExPhPlFrMngProt OBJECT-TYPE
      SYNTAX  INTEGER
   {
   notApplicable (1),
   none          (2),
   lmi           (3),
   ansiT1        (4),  --Annex D
   annexA        (5)
   }
      MAX-ACCESS  read-write
      STATUS  current
      DESCRIPTION
      "This object indicates the Frame-Relay management protocol.
       ansiT1 = ANSI T1.617 Annex D (this is the default value).
       This parameter is applicable only for FR and FR+ protocols.
       When prtExPhPlConnectionTyp = sameNetManaged, this object
       will be RO (internally determined). "
      ::= { prtExPhPlCnfgEntry 22}

prtExPhPlEnqPeriod OBJECT-TYPE
      SYNTAX  Integer32 (1..30)
      MAX-ACCESS  read-write
      STATUS  current
      DESCRIPTION
      "This object is the Status Enquiry Period, in seconds.
       It determines the frequency of the Status Enquiry message
       as sent by the FR user side.
       At the FR network side, it determines the timeout for this
       message reception.
    Default = 4 seconds.
       This parameter is applicable only for FR and FR+ protocols
    AND
       only when prtExPhPlFrMngProt is NOT (notApplicable or none)."
    ::= { prtExPhPlCnfgEntry 23}

prtExPhPlFullRptPeriod OBJECT-TYPE
      SYNTAX  Integer32 (1..255)
      MAX-ACCESS  read-write
      STATUS  current
      DESCRIPTION
      "This object is the Full Report Frequency.
       It determines the number of the Status Enquiry messages
       sent by the FR user side, before a Full Report Request is
       sent.
       The units are : Status Enquiry messages (periods).
    Valid values: 1 .. 255.
       255 = infinite.
       This parameter is applicable only for FR and FR+ protocols
    AND
       only when prtExPhPlFrMngProt is NOT (notApplicable or none)."
    ::= { prtExPhPlCnfgEntry 24}

prtExPhPlFrWindowSize OBJECT-TYPE
      SYNTAX  Integer32 (1..10)
      MAX-ACCESS  read-write
      STATUS  current
      DESCRIPTION
      "This object is the FR Window Size.
       It determines the number of samplings in the sliding window
       that counts the errors.
       This parameter is applicable only for FR and FR+ protocols
    AND
       only when prtExPhPlFrMngProt is NOT (notApplicable or none)."
    ::= { prtExPhPlCnfgEntry 25}

prtExPhPlErrorsThreshold OBJECT-TYPE
      SYNTAX  Integer32 (1..10)
      MAX-ACCESS  read-write
      STATUS  current
      DESCRIPTION
      "This object is the Max Errors.
       It determines the number of Status Enquiry Errors that
       occured within the FR sliding window, before this port is
       considered DOWN (threshold).
       This parameter is applicable only for FR and FR+ protocols
    AND
       only when prtExPhPlFrMngProt is NOT (notApplicable or none)."
    ::= { prtExPhPlCnfgEntry 26}

prtExPhPlPvcCreateMsg OBJECT-TYPE
      SYNTAX  INTEGER
   {
   notApplicable (1),
   no            (2),
   yes           (3)
   }
      MAX-ACCESS  read-write
      STATUS  current
      DESCRIPTION
      "This object is Update Message (if required or not).
       It determines whether a message of a New PVC Creation is
       requested or not (yes/no).
       Default = no.
       This parameter is applicable only for FR and FR+ protocols
    AND
       only when prtExPhPlFrMngProt is NOT (notApplicable or none)."
    ::= { prtExPhPlCnfgEntry 27}

prtExPhPlCllmMsg OBJECT-TYPE
      SYNTAX  INTEGER
   {
   notApplicable (1),
   no            (2),
   yes           (3)
   }
      MAX-ACCESS  read-write
      STATUS  current
      DESCRIPTION
      "This object is CLLM Message (if required or not).
       It determines whether to send (or not) a congestion message
       when the port is Rx congested.
       Default = no.
       This parameter is applicable only for FR and FR+ protocols
    AND
       only when prtExPhPlFrMngProt is NOT (notApplicable or none)."
    ::= { prtExPhPlCnfgEntry 28}

prtExPhPlProtDelayLevel OBJECT-TYPE
      SYNTAX  INTEGER
	  {
	  notApplicable (1),
	  s36Byte       (2),  --level 1
	  s150Byte      (3),  --level 2
	  s264Byte      (4),  --level 3
	  s378Byte      (5),  --level 4
	  s492Byte      (6)	  --level 5
	  }
      MAX-ACCESS  read-write
      STATUS  current

      DESCRIPTION
      "This object is the Segmentation in Bytes.
       	In some cases, the enumerated values will mean
	    other segmentation values than specified:

	   Product:    MX-3000 	    MX-3000 	   MX-300/MX-30
	   Protocol:     FR+     	Transparent		FR+
	   -----------------------------------------------------
	   level 1     50 Bytes		44 Bytes		50 Bytes
	   level 2    158 Bytes	   155 Bytes	   158 Bytes
	   level 3    266 Bytes	   266 Bytes	   266 Bytes
	   level 4    376 Bytes	   377 Bytes	   376 Bytes
	   level 5    484 Bytes	   488 Bytes	   484 Bytes

	   Defval=level 1 value

       This parameter is applicable only for FR+ and
       transparent protocols."
	   ::= { prtExPhPlCnfgEntry 29}

prtExPhPlClockEncoding OBJECT-TYPE
      SYNTAX  INTEGER
	  {
	  notApplicable (1),
	  nrz           (2),
	  nrzI          (3),
	  fm0           (4),
	  manchester    (5),
	  diffManchester(6),
	  nrzISpace     (7),
	  nrzIMark      (8)
	  }
      MAX-ACCESS  read-write
      STATUS  current
      DESCRIPTION
      "This object is the Encoding type of the Line.
       This parameter is applicable only for FR and FR+ protocols.
       For MAXCESS 3000 & MP2100H: when setting to nrzI (3) the nrzI works
       as nrzI Mark.
       For MAXCESS 30/300 when setting to nrzI (3) the nrzI works as nrzI Space."
	   ::= { prtExPhPlCnfgEntry 30}

prtExPhPlMinSeparators OBJECT-TYPE
      SYNTAX  Integer32 (0..16)
      MAX-ACCESS  read-write
      STATUS  current
      DESCRIPTION
      "Minimum number of bytes separating between two adjacent frames (HDLC item).
       0 = notApplicable"
	   ::= { prtExPhPlCnfgEntry 31}

prtExPhPlCcittCrc OBJECT-TYPE
      SYNTAX  INTEGER
	  {
	  notApplicable (1),
	  crc16         (2),
	  crc32         (3)
	  }
      MAX-ACCESS  read-write
      STATUS  current
      DESCRIPTION
      "This object indicates how many Bits are used for CRC (HDLC item)."
	   ::= { prtExPhPlCnfgEntry 32}

prtExPhPlFrameSeparator OBJECT-TYPE
      SYNTAX  INTEGER
	  {
	  notApplicable (1),
	  idles         (2),
	  flags         (3)
	  }
      MAX-ACCESS  read-write
      STATUS  current
      DESCRIPTION
      "This object indicates what should be transferred on the line when there
       are no frames to pass (HDLC item).
       idles: mean that FF will pass on the line
       flags: mean that 7E will pass on the line."
	   ::= { prtExPhPlCnfgEntry 33}

prtExPhPlIdleCode       OBJECT-TYPE
      SYNTAX  Integer32
      MAX-ACCESS  read-write
      STATUS  current
      DESCRIPTION
      "Determines the code for transmission when there are no frames to transmit 
       on the line. The value should be 0 to FFH."
	   ::= { prtExPhPlCnfgEntry 34}

prtExPhPlJitter OBJECT-TYPE
      SYNTAX  Integer32  (0..1000)
      MAX-ACCESS  read-write
      STATUS  current
      DESCRIPTION
      "Maximum variant delay of the FR network, in msec."
 	   ::= { prtExPhPlCnfgEntry 35}

--
-- PH.1 & PH.3
-- External port Dlci table
--
prtExPhPlDlciTable  OBJECT-TYPE
     SYNTAX SEQUENCE OF PrtExPhPlDlciEntry
     MAX-ACCESS not-accessible
     STATUS  current
     DESCRIPTION
      "The write operation into the Table Objects is valid only
       at the TmpCnfg entry."
     ::= {prtPhPlCnfg 2}

prtExPhPlDlciEntry OBJECT-TYPE
      SYNTAX PrtExPhPlDlciEntry
      MAX-ACCESS not-accessible
      STATUS current
	DESCRIPTION  "An entry in table."
	INDEX {prtExPhPlDlciCnfgIdx, prtExPhPlDlciSltIdx, prtExPhPlDlciPrtIdx, prtExPhPlDlciIdx }
      ::= { prtExPhPlDlciTable 1}

PrtExPhPlDlciEntry ::=
      SEQUENCE {
      prtExPhPlDlciCnfgIdx        Integer32,
      prtExPhPlDlciSltIdx         INTEGER,
      prtExPhPlDlciPrtIdx         INTEGER,
      prtExPhPlDlciIdx            Integer32,

      prtExPhPlDlciValid          INTEGER,
      prtExPhPlDlciIConSlt        INTEGER,
      prtExPhPlDlciIConPrt        INTEGER,
      prtExPhPlDlciIConDlci       Integer32,

      prtExPhPlDlciTxBc           INTEGER,
      prtExPhPlDlciTxBe           INTEGER,
      prtExPhPlDlciRxBc           INTEGER,
      prtExPhPlDlciRxBe           INTEGER,

      prtExPhPlDlciPriority       Integer32,

      prtExPhPlDlciStatus         INTEGER
      }


prtExPhPlDlciCnfgIdx OBJECT-TYPE
      SYNTAX  Integer32 (1..255)
      MAX-ACCESS  read-only
      STATUS  current
      DESCRIPTION
      "This attribute indicates the Idx of the Cnfg (1..100) being
       accessed.
       Idx 255 relates to the TmpCnfg. "
      ::= { prtExPhPlDlciEntry 1}
-- In phase I only the values 1 (Cnfg1) and 255 (temp) are valid.

prtExPhPlDlciSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16),
    notApplicable (255)
     }
      MAX-ACCESS  read-only
      STATUS  current
      DESCRIPTION
      "This attribute indicates a unique  slot  position where
       the card is inserted.
       In the ?004 Unit the entries io6(10)..io16) are not valid"
      ::= { prtExPhPlDlciEntry 2}

prtExPhPlDlciPrtIdx OBJECT-TYPE
      SYNTAX  INTEGER
 {
          exPrt1  (1) ,
          exPrt2  (2) ,
          exPrt3  (3) ,
    exPrt4  (4) ,
    exPrt5  (5) ,
    exPrt6  (6)
       }
      MAX-ACCESS  read-only
      STATUS  current
      DESCRIPTION
      "This attribute indicates a unique internal port number.
       PH.1/E1 and PH.1/T1 cards have three internal ports.
       Stand-alone units may have six such ports."
      ::= { prtExPhPlDlciEntry 3}

prtExPhPlDlciIdx OBJECT-TYPE
      SYNTAX  Integer32 (1..991)
      MAX-ACCESS  read-only
      STATUS  current
      DESCRIPTION
      "This attribute indicates a unique index for each possible
       used dlci(16..991). When the protocol is not Multiplexing
       protocol, its type is 'user' and the only valid index is 1."
      ::= { prtExPhPlDlciEntry 4}

prtExPhPlDlciValid OBJECT-TYPE
      SYNTAX  INTEGER
     {
     no  (2),
     yes (3)
     }
      MAX-ACCESS  read-write
      STATUS  current
      DESCRIPTION
      "This attribute indicates whether the attributes in this
       entry are valid or not. The user can add/delete pvc (dlci
       to dlci connection) by modifing this object"
      ::= { prtExPhPlDlciEntry 5}

prtExPhPlDlciIConSlt OBJECT-TYPE
      SYNTAX  INTEGER
 {
          noConnect (2),
    cl    (3),
       io1   (5),
       io2   (6),
       io3   (7),
       io4   (8),
       io5   (9),
       io6  (10),
       io7  (11),
       io8  (12),
       io9  (13),
       io10 (14),
       io11 (15),
       io12 (16),
    notApplicable (255)
       }
      MAX-ACCESS  read-write
      STATUS  current
      DESCRIPTION
      "This attribute indicates a unique slot position In the Mux
       (Agent) where the dlci is routed to.
    cl - will represent any of the CL slots. This value can be
         selected for multiple DLCIs of the product.
       In the ?004 Unit the entries io6(10)..io16) are not valid"
      ::= { prtExPhPlDlciEntry 6}

prtExPhPlDlciIConPrt OBJECT-TYPE
      SYNTAX  INTEGER
      {
       exPrt1    (1) ,
       exPrt2    (2) ,
       exPrt3    (3) ,
       exPrt4    (4) ,
       exPrt5    (5) ,
       exPrt6    (6) ,
       exPrt7    (7) ,
       exPrt8    (8) ,
       exPrt9    (9) ,
       exPrt10  (10) ,
    clNMS      (99),
          noConnect (100),
       inPrt1  (101) ,
       inPrt2  (102) ,
       inPrt3  (103) ,
       inPrt4  (104) ,
       inPrt5  (105) ,
       inPrt6  (106) ,
       inPrt7  (107) ,
       inPrt8  (108) ,
       inPrt9  (109) ,
       inPrt10 (110)
       }
      MAX-ACCESS  read-write
      STATUS  current
      DESCRIPTION
      "This attribute indicates a unique port id which the dlci is
       routed to.
       clNMS - will be used for NMS SNMP messages. It can be any
               port of the CL card.
               This value will be selectable only if
               prtExPhPlDlciIConSlt='cl' or 'notApplicable'."
      ::= { prtExPhPlDlciEntry 7}


prtExPhPlDlciIConDlci OBJECT-TYPE
      SYNTAX  Integer32    (1..991)
      MAX-ACCESS  read-write
      STATUS  current
      DESCRIPTION
      "This attribute indicates a unique internal connection dlci
       number,  the dlci is routed to."
      ::= { prtExPhPlDlciEntry 8}

prtExPhPlDlciTxBc OBJECT-TYPE
      SYNTAX  INTEGER
        {
         full       (1),
         zero       (2),
         txBc9600bps    (3),
        txBc14400bps    (4),
        txBc19200bps    (5),
        txBc28800bps    (6),
        txBc32000bps    (7),
        txBc38400bps    (8),
        txBc48000bps    (9),
        txBc56000bps   (10),
        txBc57600bps   (11),
          txBc64Kbps   (12),
         txBc128Kbps   (13),
         txBc192Kbps   (14),
         txBc256Kbps   (15),
         txBc320Kbps   (16),
         txBc384Kbps   (17),
         txBc448Kbps   (18),
         txBc512Kbps   (19),
         txBc768Kbps   (20),
        txBc1024Kbps   (21),
--
--KM30 ; KM300 additional rates
--
        txBc16000bps   (25),
   txBc112Kbps   (26)
        }
      MAX-ACCESS  read-write
      STATUS  current
      DESCRIPTION
      "This attribute indicates a unique Tx committed bandwidth on
       the user transmit line (or at the port receive line)."
      ::= { prtExPhPlDlciEntry 9}


prtExPhPlDlciTxBe OBJECT-TYPE
      SYNTAX  INTEGER
        {
         full       (1),
         zero       (2),
         txBe9600bps    (3),
        txBe14400bps    (4),
        txBe19200bps    (5),
        txBe28800bps    (6),
        txBe32000bps    (7),
        txBe38400bps    (8),
        txBe48000bps    (9),
        txBe56000bps   (10),
        txBe57600bps   (11),
          txBe64Kbps   (12),
         txBe128Kbps   (13),
         txBe192Kbps   (14),
         txBe256Kbps   (15),
         txBe320Kbps   (16),
         txBe384Kbps   (17),
         txBe448Kbps   (18),
         txBe512Kbps   (19),
         txBe768Kbps   (20),
        txBe1024Kbps   (21),
--
--KM30 ; KM300 additional rates
--
        txBc16000bps   (25),
   txBc112Kbps   (26)
        }
      MAX-ACCESS  read-write
      STATUS  current
      DESCRIPTION
      "This attribute indicates a unique Tx excess bandwidth on the
      user transmit line (or at the port receive line)."
      ::= { prtExPhPlDlciEntry 10}


prtExPhPlDlciRxBc OBJECT-TYPE
      SYNTAX  INTEGER
        {
         full       (1),
         zero       (2),
         rxBc9600bps    (3),
        rxBc14400bps    (4),
        rxBc19200bps    (5),
        rxBc28800bps    (6),
        rxBc32000bps    (7),
        rxBc38400bps    (8),
        rxBc48000bps    (9),
        rxBc56000bps   (10),
        rxBc57600bps   (11),
        rxBc64Kbps   (12),
         rxBc128Kbps   (13),
         rxBc192Kbps   (14),
         rxBc256Kbps   (15),
         rxBc320Kbps   (16),
         rxBc384Kbps   (17),
         rxBc448Kbps   (18),
         rxBc512Kbps   (19),
         rxBc768Kbps   (20),
        rxBc1024Kbps   (21),
--
--KM30 ; KM300 additional rates
--
        rxBc16000bps   (25),
   rxBc112Kbps   (26)
        }
      MAX-ACCESS  read-write
      STATUS  current
      DESCRIPTION
      "This attribute indicates a unique Rx committed bandwidth on the
      user receive line (or at the port transmit line)."
      ::= { prtExPhPlDlciEntry 11}


prtExPhPlDlciRxBe OBJECT-TYPE
      SYNTAX  INTEGER
        {
         full       (1),
         zero       (2),
         rxBe9600bps    (3),
        rxBe14400bps    (4),
        rxBe19200bps    (5),
        rxBe28800bps    (6),
        rxBe32000bps    (7),
        rxBe38400bps    (8),
        rxBe48000bps    (9),
        rxBe56000bps   (10),
        rxBe57600bps   (11),
          rxBe64Kbps   (12),
         rxBe128Kbps   (13),
         rxBe192Kbps   (14),
         rxBe256Kbps   (15),
         rxBe320Kbps   (16),
         rxBe384Kbps   (17),
         rxBe448Kbps   (18),
         rxBe512Kbps   (19),
         rxBe768Kbps   (20),
        rxBe1024Kbps   (21),
--
--KM30 ; KM300 additional rates
--
        rxBc16000bps   (25),
   rxBc112Kbps   (26)
        }
      MAX-ACCESS  read-write
      STATUS  current
      DESCRIPTION
      "This attribute indicates a unique Rx excess bandwidth on the
      user receive line (or at the port transmit line)."
      ::= { prtExPhPlDlciEntry 12}


prtExPhPlDlciPriority OBJECT-TYPE
      SYNTAX  Integer32  (1..8)
      MAX-ACCESS  read-write
      STATUS  current
      DESCRIPTION
      "This attribute indicates a unique priority of the pcv.
       1 is the lowest priority and 8 is the highest priority."
      ::= { prtExPhPlDlciEntry 13}


prtExPhPlDlciStatus OBJECT-TYPE
      SYNTAX  INTEGER
 {
          disconnected (1),
          connected    (2)
       }
      MAX-ACCESS  read-only
      STATUS  current
      DESCRIPTION
      "This attribute indicates the status of the pvc. The status is
       disconnected(1) when one of the sides is programmed as not
       connected"
      ::= { prtExPhPlDlciEntry 14}


-- Parameters of an external Modem which is connected to a High/Low Speed
-- Port.

prtExPhPlModemTable  OBJECT-TYPE
      SYNTAX SEQUENCE OF PrtExPhPlModemEntry
      MAX-ACCESS not-accessible
      STATUS  current
      DESCRIPTION "External Modem Parameters.
      The write operation into the
      Table Objects is valid only for the TmpCnfg entry."
      ::= {prtPhPlCnfg 3}

prtExPhPlModemEntry OBJECT-TYPE
      SYNTAX PrtExPhPlModemEntry
      MAX-ACCESS not-accessible
      STATUS current
	DESCRIPTION  "An entry in table."
	INDEX {prtExPhPlModemCnfgIdx,prtExPhPlModemSltIdx,prtExPhPlModemPrtIdx}
      ::= { prtExPhPlModemTable 1}

PrtExPhPlModemEntry ::=
      SEQUENCE {
      prtExPhPlModemCnfgIdx           Integer32,
      prtExPhPlModemSltIdx            INTEGER,
      prtExPhPlModemPrtIdx            INTEGER,
      prtExPhPlModemStatus            INTEGER,
      prtExPhPlModemActivate          INTEGER,
      prtExPhPlModemMaxIdleTime       Integer32,
      prtExPhPlModemTimeBtwnCalls     Integer32,
	  prtExPhPlModemCallDelay         Integer32 
	}

prtExPhPlModemCnfgIdx OBJECT-TYPE
      SYNTAX  Integer32 (1..255)
      MAX-ACCESS  read-only
      STATUS  current
      DESCRIPTION
      "This attribute indicates the Idx of the Cnfg (1..100) being
       accessed.
       Idx 255 relates to the TmpCnfg. "
      ::= { prtExPhPlModemEntry 1}

prtExPhPlModemSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16),
       notApplicable (255)
     }
      MAX-ACCESS  read-only
      STATUS  current
      DESCRIPTION
      "This attribute indicates a unique  slot  position where
       the card is inserted.
       In the ?004 Unit the entries io6(10)..io12(16) are not valid"
      ::= { prtExPhPlModemEntry 2}

prtExPhPlModemPrtIdx OBJECT-TYPE
      SYNTAX  INTEGER
 {
          exPrt1  (1) ,
          exPrt2  (2) ,
          exPrt3  (3) ,
          exPrt4  (4) ,
          exPrt5  (5) ,
          exPrt6  (6)
       }
      MAX-ACCESS read-only
      STATUS  current
      DESCRIPTION
      "This attribute indicates a unique port number.
       In case of PH.1 card, only exPrt(1) is valid."
      ::= { prtExPhPlModemEntry 3}

prtExPhPlModemStatus OBJECT-TYPE
      SYNTAX INTEGER
      {
       disable (2),
       enable  (3)
      }
      MAX-ACCESS  read-write
      STATUS  current
      DESCRIPTION
      "This object indicates whether a Dial Up Modem is enabled
       on this port.
       Default: disable"
      ::= { prtExPhPlModemEntry 4}

prtExPhPlModemActivate OBJECT-TYPE
      SYNTAX INTEGER
     {
      onFirstFrame(2),
      always    (3),
      notApplicable (255)
     }
      MAX-ACCESS  read-write
      STATUS  current
      DESCRIPTION
      "This object indicates whether the Dial Up Modem is activated when
       the first frame is received or it is always activated.
       Default: onFirstFrame"
      ::= { prtExPhPlModemEntry 5}

prtExPhPlModemMaxIdleTime OBJECT-TYPE
      SYNTAX Integer32
      MAX-ACCESS  read-write
      STATUS  current
      DESCRIPTION
      "Max Time allowed in Seconds without any traffic before the line
       is disconnected.

       Legal Values are: 1 sec, 2 sec .. 5 sec, 10 sec, 20 sec..
       1 min, 2 min .. 10 min, 15 min, 20 min, 25 min, 30 min.
       65535 sec. means that this parameter is not applicable. 

       Default: 1 sec."
       ::= { prtExPhPlModemEntry 6}

prtExPhPlModemTimeBtwnCalls OBJECT-TYPE
      SYNTAX Integer32
      MAX-ACCESS  read-write
      STATUS  current
      DESCRIPTION
      "Minimum Time in Seconds which is required after a call was
       disconnected. In this time no other call will be initiated
       from this Modem port even if there were frames transmitted
       to this port. This time is required for some Modems which
       have initializations that take a few seconds.
       
       Legal Values are:
	   0 sec. - 30 sec., 1-5 min.
       65535 sec. means that this parameter is not applicable. 

       Default: 0 sec"
       ::= { prtExPhPlModemEntry 7}

prtExPhPlModemCallDelay OBJECT-TYPE
      SYNTAX Integer32
      MAX-ACCESS  read-write
      STATUS  current
      DESCRIPTION
      "Time in Seconds that the device will wait before dialing to the remote
	   device.
	   
	   This feature is mostly used when there is a backup modem to the 
	   main link and the main link is down. In this case it is important to prevent
	   the 2 devices from dialing through the backup modems to each other at the same time.
	   It is advised to configure one side with a small call delay and the other side
	   with a large call delay.
       
       Legal Values are:
	   0 - 30, 60, 120, 180, 240, 300, 600, 900, 1200, 1500, 1800 . 
       65535 sec. means that this parameter is not applicable. 

       Default: 0 sec"
       ::= { prtExPhPlModemEntry 8}

--
-- Megaplex ?000/?004 LS-2 TDM I/O family card include:
-- Ls2-CCITT-X.50, Ls2-CCITT-X.58, Ls2-AT&T-SDM
--
--prtExLs2CnfgTable OBJECT IDENTIFIER ::= {prtLs2Cnfg 1}
--prtInLs2CnfgTable OBJECT IDENTIFIER ::= {prtLs2Cnfg 2}

prtExLs2CnfgTable OBJECT-TYPE
      SYNTAX SEQUENCE OF PrtExLs2CnfgEntry
      MAX-ACCESS not-accessible
      STATUS  current
      DESCRIPTION
       "The write operation into the Table Objects is valid only
        to the TmpCnfg entry."
      ::= {prtLs2Cnfg 1}

prtExLs2CnfgEntry OBJECT-TYPE
      SYNTAX PrtExLs2CnfgEntry
      MAX-ACCESS not-accessible
      STATUS current
	DESCRIPTION  "An entry in table."
	INDEX {prtExLs2CnfgIdx, prtExLs2SltIdx, prtExLs2PrtIdx }
      ::= {prtExLs2CnfgTable  1}

PrtExLs2CnfgEntry ::=
      SEQUENCE {
        prtExLs2CnfgIdx   Integer32,
        prtExLs2SltIdx    INTEGER,
        prtExLs2PrtIdx    INTEGER,
        prtExLs2Connect   INTEGER,
        prtExLs2Rate      INTEGER,
        prtExLs2ClkMode   INTEGER,
        prtExLs2Cts       INTEGER,
        prtExLs2Dcd       INTEGER,
        prtExLs2EnvIdx    Integer32 
	}

prtExLs2CnfgIdx OBJECT-TYPE
      SYNTAX  Integer32 (1..255)
      MAX-ACCESS  read-only
      STATUS  current
      DESCRIPTION
      "This attribute indicates the Idx of the Cnfg (1..100) being
       accessed.
       Idx  255 relates to the TmpCnfg"
      ::= {prtExLs2CnfgEntry 1}
-- In phase I only the values 1 (Cnfg1) and 255 (temp) are valid.

prtExLs2SltIdx OBJECT-TYPE
      SYNTAX  INTEGER
          {
       io1   (5),
       io2   (6),
       io3   (7),
       io4   (8),
       io5   (9),
       io6  (10),
       io7  (11),
       io8  (12),
       io9  (13),
       io10 (14),
       io11 (15),
       io12 (16)
       }
      MAX-ACCESS  read-only
      STATUS  current
      DESCRIPTION
      "This attribute indicates a unique  slot  position where
       the card is inserted.
       In the ?004 Unit the entries io6(10)..io16) are not valid."
      ::= {prtExLs2CnfgEntry 2}

prtExLs2PrtIdx OBJECT-TYPE
      SYNTAX  INTEGER
          {
          exPrt1    (1) ,
          exPrt2    (2) ,
          exPrt3    (3) ,
          exPrt4    (4) ,
          exPrt5    (5) ,
          exPrt6    (6) ,
          exPrt7    (7) ,
          exPrt8    (8) ,
          exPrt9    (9) ,
          exPrt10  (10)
          }
      MAX-ACCESS  read-only
      STATUS  current
      DESCRIPTION
      "This attribute indicates a unique  port index.
      For the Ls2/X.58 exPrt(7)..exPrt(10) are not valid."
      ::= {prtExLs2CnfgEntry 3}


prtExLs2Connect OBJECT-TYPE
      SYNTAX  INTEGER
              {
                no  (2),
                yes (3)
              }
      MAX-ACCESS  read-write
      STATUS  current
      DESCRIPTION
      "This attribute indicates whether the  port  should be
       considered in any of the mux algorithms."
      ::= {prtExLs2CnfgEntry 4}

prtExLs2Rate OBJECT-TYPE
      SYNTAX  INTEGER
       {
          r2400bps  (2),
          r4800bps  (3),
          r9600bps  (4),
          r19200bps (5)
       }
      MAX-ACCESS  read-write
      STATUS  current
      DESCRIPTION
      "Port rates."
      ::= {prtExLs2CnfgEntry 5}

prtExLs2ClkMode OBJECT-TYPE
      SYNTAX  INTEGER
       {
          dce     (1),
          ext-dce (2),
          dte     (3)
       }
      MAX-ACCESS  read-write
      STATUS  current
      DESCRIPTION
      "This attribute indicates a unique port operation clock mode."
      ::= {prtExLs2CnfgEntry 6}

prtExLs2Cts OBJECT-TYPE
      SYNTAX  INTEGER
       {
    on       (2),
    rts-min  (3),
    rts-max  (4)
       }
      MAX-ACCESS  read-write
      STATUS  current
      DESCRIPTION
      "CTS."
      ::= {prtExLs2CnfgEntry 7}

prtExLs2Dcd OBJECT-TYPE
      SYNTAX  INTEGER
       {
    on        (2),
    card-sync (3)
       }
      MAX-ACCESS  read-write
      STATUS  current
      DESCRIPTION
      "DCD."
      ::= {prtExLs2CnfgEntry 8}

prtExLs2EnvIdx OBJECT-TYPE
      SYNTAX  Integer32 (0..24)
      MAX-ACCESS  read-write
      STATUS  current
      DESCRIPTION
      "Envelope Index.
       When prtInLs2EnvAssign=auto, the value is 0 (not applicable)."
      ::= {prtExLs2CnfgEntry 9}

-- Ls2 Internal composit channel parameters
--
prtInLs2CnfgTable OBJECT-TYPE
      SYNTAX SEQUENCE OF PrtInLs2CnfgEntry
      MAX-ACCESS not-accessible
      STATUS  current
      DESCRIPTION
       "The write operation into the Table Objects is valid only
        to the TmpCnfg entry."
      ::= {prtLs2Cnfg 2}

prtInLs2CnfgEntry OBJECT-TYPE
      SYNTAX PrtInLs2CnfgEntry
      MAX-ACCESS not-accessible
      STATUS current
	DESCRIPTION  "An entry in table."
	INDEX {prtInLs2CnfgIdx, prtInLs2SltIdx, prtInLs2PrtIdx }
      ::= {prtInLs2CnfgTable 1}

PrtInLs2CnfgEntry ::=
      SEQUENCE {
        prtInLs2CnfgIdx   Integer32,
        prtInLs2SltIdx    INTEGER,
        prtInLs2PrtIdx    INTEGER,
        prtInLs2Connect   INTEGER,
        prtInLs2Group     Integer32,
        prtInLs2Member    Integer32,
        prtInLs2LinkTo    INTEGER,
        prtInLs2EnvAssign INTEGER
      }

prtInLs2CnfgIdx OBJECT-TYPE
      SYNTAX  Integer32 (1..255)
      MAX-ACCESS  read-only
      STATUS  current
      DESCRIPTION
      "This attribute indicates the Idx of the Cnfg (1..100) being
       accessed.
       Idx  255 relates to the TmpCnfg"
      ::= {prtInLs2CnfgEntry 1}
-- In phase I only the values 1 (Cnfg1) and 255 (temp) are valid.

prtInLs2SltIdx OBJECT-TYPE
      SYNTAX  INTEGER
          {
       io1   (5),
       io2   (6),
       io3   (7),
       io4   (8),
       io5   (9),
       io6  (10),
       io7  (11),
       io8  (12),
       io9  (13),
       io10 (14),
       io11 (15),
       io12 (16)
       }
      MAX-ACCESS  read-only
      STATUS  current
      DESCRIPTION
      "This attribute indicates a unique  slot  position where
       the card is inserted.
       In the ?004 Unit the entries io6(10)..io16) are not valid."
      ::= {prtInLs2CnfgEntry 2}

prtInLs2PrtIdx OBJECT-TYPE
      SYNTAX  INTEGER
          {
          inPrt1    (101),
    inPrt2    (102)
          }
      MAX-ACCESS  read-only
      STATUS  current
      DESCRIPTION
      "This attribute indicates a unique internal port index."
      ::= {prtInLs2CnfgEntry 3}

prtInLs2Connect OBJECT-TYPE
      SYNTAX  INTEGER
              {
                no  (2),
                yes (3)
              }
      MAX-ACCESS  read-write
      STATUS  current
      DESCRIPTION
      "This attribute indicates whether the port should be considered in
       any of the mux  algorithms. It also affects all the module
       considerations because the module has only one Internal
       interface which is the composite channel."
      ::= {prtInLs2CnfgEntry 4}

prtInLs2Group OBJECT-TYPE
      SYNTAX  Integer32 (1..12)
      MAX-ACCESS  read-write
      STATUS  current
      DESCRIPTION
      "This attribute indicates the group number of the port.
       LS-2 internal ports with the same group number share the same Time slot of the main
       link"
      ::= {prtInLs2CnfgEntry 5}

prtInLs2Member OBJECT-TYPE
      SYNTAX  Integer32 (1..4)
      MAX-ACCESS  read-write
      STATUS  current
      DESCRIPTION
      "This attribute indicates the group member id of the port.
       This parameter is for the automatic envelope assignment
       algorithm."
      ::= {prtInLs2CnfgEntry 6}

prtInLs2LinkTo OBJECT-TYPE
      SYNTAX  INTEGER
       {
       io1   (5),
       io2   (6),
       io3   (7),
       io4   (8),
       io5   (9),
       io6  (10),
       io7  (11),
       io8  (12),
       io9  (13),
       io10 (14),
       io11 (15),
       io12 (16)
       }
      MAX-ACCESS  read-write
      STATUS  deprecated
      DESCRIPTION
      "It indicates the slot of the main link card to which the
       LS2 card is mapped.
       STATUS  deprecated - this object is replaced by prtGenCnfgLinkToSlot
       and prtGenCnfgLinkToPort."
      ::= {prtInLs2CnfgEntry 7}

prtInLs2EnvAssign OBJECT-TYPE
      SYNTAX  INTEGER
       {
        auto    (2),
        manual  (3)
       }
      MAX-ACCESS  read-write
      STATUS  current
      DESCRIPTION
      "Envelope assignment type."
      ::= {prtInLs2CnfgEntry 8}


--
-- Megaplex?000/?004 VC-2, VC-6, VC-2/R2, VC-Q TDM I/O family port.
-- (Vc2E&m,Vc2Fxs1Plar,Vc2Fxo1,Vc2Fxs2,Vc2Fxo2,Vc2Fxs3,Vc2Fxo3)
-- Vc6E&M, Vc6Fxo, Vc6Fxs, Vc6aE&M, Vc6aFxo, Vc6aFxs
-- Vc2/R2(Fxs)
-- VC-Q
-- VC-12, VC-12/6
-- VC-8,  VC-16

prtVc2CnfgTable OBJECT-TYPE
      SYNTAX SEQUENCE OF PrtVc2CnfgEntry
      MAX-ACCESS not-accessible
      STATUS  current
      DESCRIPTION
       "The write operation into the Table Objects is valid only
        to the TmpCnfg entry."
      ::= { cnfgPrtMux 5}

prtVc2CnfgEntry OBJECT-TYPE
      SYNTAX PrtVc2CnfgEntry
      MAX-ACCESS not-accessible
      STATUS current
	DESCRIPTION  "An entry in table."
	INDEX {prtVc2CnfgIdx, prtVc2SltIdx, prtVc2PrtIdx }
      ::= { prtVc2CnfgTable 1}

PrtVc2CnfgEntry ::=
      SEQUENCE {
        prtVc2CnfgIdx       Integer32,
        prtVc2SltIdx        INTEGER,
        prtVc2PrtIdx        Integer32,

        prtExVc2Connect     INTEGER,
        
        prtExVc2TransGain   Integer32,
        prtExVc2ReceiveGain Integer32,

        prtExVc2Wire        INTEGER,
        prtExVc2CodingLaw   INTEGER,
        prtExVc2Sig         INTEGER,
        prtExVc2Oos         INTEGER,
        prtExVc2LinkTo      INTEGER,
        prtExVc2OperMode    INTEGER,
        prtExVc2SigProfile  INTEGER,
        prtExVc2CallEnable  INTEGER,
        prtExVc2R2Delay     INTEGER,
        prtExVc2CasStd      INTEGER,
        prtExVc2EchoCanceler INTEGER,
        prtExVc2IfType      INTEGER,
        prtExVc2Encoding    INTEGER,
        prtExVc2TxBitCode   OCTET STRING,
        prtExVc2RxBitOutput OCTET STRING,
		prtExVc2MeterRate   INTEGER,
		prtExVc2IfSignaling INTEGER,
        prtExVc2SeizeAck    INTEGER,
        prtExVc2EandMType   INTEGER,
		prtExVc2RemType     INTEGER,
		prtExVc2ConvTime    INTEGER,
		prtExVc2SigFeedback INTEGER,
		prtExVc2EchoCancelerModule  INTEGER
      }

prtVc2CnfgIdx OBJECT-TYPE
      SYNTAX  Integer32  (1..255)
      MAX-ACCESS  read-only
      STATUS  current
      DESCRIPTION
      "This attribute indicates the Idx of the Cnfg (1..100) being
       accessed.
       Idx  255 relates to the TmpCnfg"
      ::= {prtVc2CnfgEntry 1}
-- In phase I only the values 1 (Cnfg1) and 255 (temp) are valid.

prtVc2SltIdx OBJECT-TYPE
      SYNTAX  INTEGER
 {
       io1   (5),
       io2   (6),
       io3   (7),
       io4   (8),
       io5   (9),
       io6  (10),
       io7  (11),
       io8  (12),
       io9  (13),
       io10 (14),
       io11 (15),
       io12 (16),
       notApplicable (255)
 }
      MAX-ACCESS  read-only
      STATUS  current
      DESCRIPTION
      "This attribute indicates a unique  slot  position where
       the card is inserted.
       For Stand Alone products like WR: notApplicable (255)"
      ::= {prtVc2CnfgEntry 2}

prtVc2PrtIdx OBJECT-TYPE
      SYNTAX  Integer32
      MAX-ACCESS  read-only
      STATUS  current
      DESCRIPTION
      "A unique identifier of the port, within the card.
       For Megaplex card ports, Web Ranger and FCD-IP Voice ports 
 	   the values will be:
       exPrt1    (1) 
       exPrt2    (2) 
       exPrt3    (3) 
       exPrt4    (4) 
       exPrt5    (5) 
       exPrt6    (6) 
       exPrt7    (7) 
       exPrt8    (8) 
       exPrt9    (9) 
       exPrt10  (10) 
       exPrt11  (11) 
       exPrt12  (12)
       exPrt13  (13) 
       exPrt14  (14) 
       exPrt15  (15) 
       exPrt16  (16) 
 	   
	   For LA-240:
	     The index for fixed voice ports will be - 
	       exPrt6    (6) 
           exPrt7    (7) 
           exPrt8    (8) 
           exPrt9    (9) 
		 The index for voice card ports will be - 
		   Slot number * 100 + ch (for IO-1: 101..104, for IO-2: 201..204)."
      ::= {prtVc2CnfgEntry 3}

prtExVc2Connect OBJECT-TYPE
      SYNTAX  INTEGER
              {
                no  (2),
                yes (3),
				v51 (4) 
              }
      MAX-ACCESS  read-write
      STATUS  current
      DESCRIPTION
      "This attribute indicates whether the  port  should be
       considered in any of the mux algorithms."
      ::= {prtVc2CnfgEntry 4}

prtExVc2TransGain OBJECT-TYPE
      SYNTAX  Integer32
      MAX-ACCESS  read-write
      STATUS  current
      DESCRIPTION
      "Transmit gain in dBm.
       For ports of VC-6A, VC-6AG, VC-8 and VC-16 cards, the units will be 0.1dBm
       because valid values can be in 0.5dBm steps."
      ::= {prtVc2CnfgEntry 5}

prtExVc2ReceiveGain OBJECT-TYPE
      SYNTAX  Integer32
      MAX-ACCESS  read-write
      STATUS  current
      DESCRIPTION
      "Receive gain in dBm.
       For ports of VC-6A, VC-6AG, VC-8 and VC-16 cards, the units will be 0.1dBm
       because valid values can be in 0.5dBm steps."
      ::= {prtVc2CnfgEntry 6}

prtExVc2Wire OBJECT-TYPE
      SYNTAX  INTEGER
       {
          w2wire   (1),
          w4wire   (2),
		  notApplicable  (255)
       }
      MAX-ACCESS  read-write
      STATUS  current
      DESCRIPTION
      "For some cards, this object is equal for all the ports in the specific
       card because of HW limitations.
       For FXO & FXS this parameter is not applicable."
      ::= {prtVc2CnfgEntry 7}

prtExVc2CodingLaw OBJECT-TYPE
      SYNTAX  INTEGER
       {
          aLAW    (1),
          uLAW    (2)
       }
      MAX-ACCESS  read-write
      STATUS  current
      DESCRIPTION
      "This attribute indicates the Method/Law for decoding/encoding the voice
       information.
       aLaw(1) is the standard Law for E1 links.
       uLaw(2) is the standard Law for T1 links.

       This object is equal for all the ports in the specific module because
       of HW limitations"
      ::= {prtVc2CnfgEntry 8}

prtExVc2Sig OBJECT-TYPE
      SYNTAX  INTEGER
       {
          noSignaling           (1),
          robbedBitMultiFrame   (2),
          chAssociatedE1        (3),
          robbedBitFrame        (4)
       }
      MAX-ACCESS  read-write
      STATUS  current
      DESCRIPTION
      "This attribute indicates the method for decoding/encoding the signaling
       information(on/off hook).
       noSignaling        (1) - not using signaling (only voice).
       robbedBitMultiFrame(2) - is the standard method for T1 links and
                                proprietary method for E1 links.
       chAssociatedE1     (3) - is valid only for E1 G.732S links.
       robbedBitFrame     (4) - is proprietary method implimenting 7 bit for
                                the voice and 1 bit dedicated for signaling.

       For some cards, this object is equal for all the ports in the specific module 
       because of HW limitations."
      ::= {prtVc2CnfgEntry 9}

prtExVc2Oos OBJECT-TYPE
      SYNTAX  INTEGER
       {
          forcedIdle     (1),
          forcedBusy     (2),
          busyIdle       (3),
          idleBusy       (4),
          notApplicable  (5)
       }
      MAX-ACCESS  read-write
      STATUS  current
      DESCRIPTION
      "This object is equal for all the ports in the specific card
       because of HW limitations"
      ::= {prtVc2CnfgEntry 10}

prtExVc2LinkTo OBJECT-TYPE
      SYNTAX  INTEGER
       {
       io1   (5),
       io2   (6),
       io3   (7),
       io4   (8),
       io5   (9),
       io6  (10),
       io7  (11),
       io8  (12),
       io9  (13),
       io10 (14),
       io11 (15),
       io12 (16),
	   notApplicable  (255)
       }
      MAX-ACCESS  read-write
      STATUS  deprecated
      DESCRIPTION
      "This attribute indicates the slot of the ML card to which
       the VC card is mapped.
       STATUS  deprecated - this object is replaced by prtGenCnfgLinkToSlot
       and prtGenCnfgLinkToPort."
      ::= {prtVc2CnfgEntry 11}

prtExVc2OperMode OBJECT-TYPE
      SYNTAX  INTEGER
       {
       normal          (2),
       unidirectRx     (3),
       broadcast       (4)
       }
      MAX-ACCESS  read-write
      STATUS  current
      DESCRIPTION
      "This object indicates the operation mode of the port.
       normal = bi-directional (Tx/Rx)
       unidirectRx = unidirectional Rx.
       broadcast = Tx upon request."
      ::= {prtVc2CnfgEntry 12}


prtExVc2SigProfile OBJECT-TYPE
      SYNTAX  INTEGER
       {
       notApplicable   (1),
       manual          (2),
       p1              (3),
       p2              (4),
       p3Fxo3S3        (5),
       reversePolarity (6),	 --3RP
       meteringPulse   (7),	 --3MP
	   p4              (8)
       }
      MAX-ACCESS  read-write
      STATUS  current
      DESCRIPTION
      "This object indicates the Signaling Profile of the port.
       notApplicable - for VC-2 family and when
                       prtExVc2Sig=noSignaling(1)
       p1 = profile 1
       p2 = profile 2
       p3 = profile 3 
       p4 = profile 4 "
      ::= {prtVc2CnfgEntry 13}

prtExVc2CallEnable OBJECT-TYPE
      SYNTAX  INTEGER
       {
       notApplicable (1),
       incoming      (2),
       outgoing      (3),
       both          (4)
       }
      MAX-ACCESS  read-write
      STATUS  current
      DESCRIPTION
      "This object indicates the Enabled Call direction.
       notApplicable - for all cards except VC-2/R2.
       both     - incoming + outgoing."
      ::= {prtVc2CnfgEntry 14}

prtExVc2R2Delay OBJECT-TYPE
      SYNTAX  INTEGER
       {
       notApplicable (1),
       terrestrial   (2),
       satellite     (3)
       }
      MAX-ACCESS  read-write
      STATUS  current
      DESCRIPTION
      "This object indicates the R2 Delay.
       notApplicable - for all cards except VC-2/R2."
      ::= {prtVc2CnfgEntry 15}

prtExVc2CasStd OBJECT-TYPE
      SYNTAX  INTEGER
       {
       notApplicable (1),
       r2Q422        (2),
       specialA      (3),
       specialB      (4),
	   specialC      (5),
	   specialD      (6),
	   specialE      (7),
   	   specialF      (8),
       specialG      (9)
       }
      MAX-ACCESS  read-write
      STATUS  current
      DESCRIPTION
      "This object indicates the CAS (Channel Associated Signaling)
       Standard.
       notApplicable - for all cards except VC-2/R2."
      ::= {prtVc2CnfgEntry 16}

prtExVc2EchoCanceler OBJECT-TYPE
      SYNTAX  INTEGER
       {
       notApplicable (1),
          off    (2),
          on     (3)
       }
      MAX-ACCESS  read-write
      STATUS  current
      DESCRIPTION
      "Echo canceler activation.
       notApplicable - for VC-2 and VC-6 cards."
      ::= {prtVc2CnfgEntry 17}

prtExVc2IfType OBJECT-TYPE
      SYNTAX  INTEGER
       {
       notApplicable (1),
       w2Em     (2),
       w4Em     (3),
       fxo      (4),
       fxs      (5)
       }
      MAX-ACCESS  read-write
      STATUS  current
      DESCRIPTION
      "Interface Type."
      ::= {prtVc2CnfgEntry 18}

prtExVc2Encoding OBJECT-TYPE
      SYNTAX  INTEGER
       {
          notApplicable (1),
          pcm           (2),
          adpcm         (3)
       }
      MAX-ACCESS  read-write
      STATUS  current
      DESCRIPTION
      "Voice Encoding Mode."
      ::= {prtVc2CnfgEntry 19}

prtExVc2TxBitCode OBJECT-TYPE
      SYNTAX  OCTET STRING
      MAX-ACCESS  read-write
      STATUS  current
      DESCRIPTION
      "
       - - - For MP & FCD - - -

       This object represents 4 parameters, by 2 Octets :
       Tx D Bit Code-MSB nibble,
       Tx C Bit Code-    nibble,
       Tx B Bit Code-    nibble,
       Tx A Bit Code-LSB nibble.

       Each nibble:
    0 hex = 0000 = Not Applicable
    1 hex = 0001 = M lead
    2 hex = 0010 = M lead inverse
    3 hex = 0011 = Reverse Polarity
    4 hex = 0100 = Metering Pulse
    5 hex = 0101 = Forced 1
    6 hex = 0110 = Forced 0
    7-F hex - not used (invalid values)
       This object will be RO if prtExVc2SigProfile is NOT manual.
      
       
      - - - For WR II - - -

   This object represents the following 4 parameters by 2 Octets:
   1. On/Off hook signaling transmission mode from the FXS towards the T1/E1 (MSB nibble 1).
   2. Default signaling bits that are not in use (nibble 2).
   3. Ring Detection signaling transmission mode from the FXO towards the T1/E1(nibble 3).
   4. M (Mouth) Signaling transmission mode from the E&M towards the T1/E1(LSB nibble 4). 

      Each nibble:
	---------------------------------------------------------------------------------------
	Value          On/Off Hook       Default sig.      Ring Detect.        M (Mouth)
	---------------------------------------------------------------------------------------
    0 hex = 0000   Not Applicable    Not Applicable.  Not Applicable	   Not Applicable
    1 hex = 0001   Tx A bit			 Values 1-3 are	  Tx A bit			   Tx A bit
    2 hex = 0010   Tx A bit inverse	 for On/Off Hook  Tx A bit inv.	  	   Tx A bit inv.
    3 hex = 0011   Tx B bit			 A,B,A Inv,B Inv. Tx B bit			   Tx B bit
    4 hex = 0100   Tx B bit inverse	 Values 4-7 are	  Tx B bit inv.		   Tx B bit inv.
    5 hex = 0101   not Used-invalid	 for On/Off Hook  not Used-invalid	   not Used-invalid
    6 hex = 0110   not Used-invalid	 A, A Inverse.	  not Used-invalid 	   not Used-invalid
    7 hex = 0111   not Used-invalid			 		  not Used-invalid	   not Used-invalid	 
    8 hex = 1000   not Used-invalid	 Values 8-11 are  not Used-invalid	   not Used-invalid
    9 hex = 1001   not Used-invalid	 for On/Off Hook  not Used-invalid	   not Used-invalid
	A hex = 1010   not used-invalid	 B, B Inverse.	  not Used-invalid	   not Used-invalid
	B hex = 1011   not used-invalid	 The Bits order:  not Used-invalid	   not Used-invalid
    C-F hex 	   not used-invalid	 ABCD			  not Used-invalid	   not Used-invalid
   

    Default value: 11 11 "
      ::= {prtVc2CnfgEntry 20}

prtExVc2RxBitOutput OBJECT-TYPE
      SYNTAX  OCTET STRING
      MAX-ACCESS  read-write
      STATUS  current
      DESCRIPTION
      "
       - - - For MP (VC-Q card only) & FCD - - -
       This object represents 3  parameters by 2 Octets:
       Spare       -MSB nibble, always=0 hex
       E Lead Output          -    nibble,
       Reverse Polarity Output-    nibble,
       Metering Pulse Output  -LSB nibble.

       Each nibble:
    0 hex = 0000 = Not Applicable
    1 hex = 0001 = Rx A bit
    2 hex = 0010 = Rx A bit inverse
    3 hex = 0011 = Rx B bit
    4 hex = 0100 = Rx B bit inverse
    5 hex = 0101 = Rx C bit
    6 hex = 0110 = Rx C bit inverse
    7 hex = 0111 = Rx D bit
    8 hex = 1000 = Rx D bit inverse
    9 hex = 1001 = none
    A-F hex - not used (invalid values)
       This object will be RO if prtExVc2SigProfile is NOT manual.

      - - - For MP (VC-8, VC-16, VC-16A cards) - - - 

    This object represents 4 parameters, by 2 Octets :
    Tx D Bit Code-MSB nibble,
    Tx C Bit Code-    nibble,
    Tx B Bit Code-    nibble,
    Tx A Bit Code-LSB nibble.

    Each nibble:
    0 hex = 0000 = Not Applicable
    1 hex = 0001 = not used (invalid value)
    2 hex = 0010 = not used (invalid value)
    3 hex = 0011 = not used (invalid value)
    4 hex = 0100 = not used (invalid value)
    5 hex = 0101 = Forced 1
    6 hex = 0110 = Forced 0
    7-F hex - not used (invalid values)
    This object will be RO.
       
             
      - - - For WR II - - -

   This object represents the following 2 parameters in 1 Octet:
   1. On/Off hook signaling receive mode from the T1/E1 into the FXS/FXO (MSB nibble 1).
   2. E (Ear) Signaling receive mode from the T1/E1 into the E&M (LSB nibble 2). 

      Each nibble:
	---------------------------------------------------------------------------------------
	Value          On/Off Hook       E (Ear)
	---------------------------------------------------------------------------------------
    0 hex = 0000   Not Applicable    Not Applicable
    1 hex = 0001   Rx A bit			 Rx A bit
    2 hex = 0010   Rx A bit inverse	 Rx A bit inverse
    3 hex = 0011   Rx B bit			 Rx B bit
    4 hex = 0100   Rx B bit inverse	 Rx B bit inverse
    5-F hex 	   not used-invalid	 not Used-invalid
   

    Default value: 11 "

      ::= {prtVc2CnfgEntry 21}

prtExVc2MeterRate OBJECT-TYPE
      SYNTAX  INTEGER
      {
        notApplicable(1),
        r16Khz (2),
        r12Khz (3)
      }
      MAX-ACCESS  read-write
      STATUS  current
      DESCRIPTION
      "This entry is applicable only for VC-6A/FXO, VC-6A/FXS, VC-8/FXO,
       VC-8/FXS, VC-16/FXO and VC-16/FXS.
       Meter Rate means rate of Call Meter in Public Phones, in KHz units.
       For some cards, the value must be the same for all card's ports."
      ::= {prtVc2CnfgEntry 22}

prtExVc2IfSignaling OBJECT-TYPE
      SYNTAX  INTEGER
      {
        notApplicable(1),
        loopStart    (2),
		groundStart  (3),
		winkStart    (4)
      }
      MAX-ACCESS  read-write
      STATUS  current
      DESCRIPTION
      "This entry is applicable only for VC-6A, VC-6AG, VC-8/FXO, VC-8/FXS,
       VC-16/FXO and VC-16/FXS cards.
       Interface Analog Signaling.
       Must be the same for all card's ports.
       loopStart - for the usual trunk/phone types.
       groundStart - for trunks that need Ground signaling .
       winkStart - for trunks that need Reverse Polarity. "
      ::= {prtVc2CnfgEntry 23}

prtExVc2SeizeAck OBJECT-TYPE
      SYNTAX INTEGER
      {
      notApplicable (1),
	  no  (2),
      yes (3)
      }
      MAX-ACCESS  read-write
      STATUS  current
      DESCRIPTION
      "This parameter shows whether the device will acknowledge
       a seize signal (On/Off Hook).
       When the value is set to yes(3) & the device receives an on/off hook signal
       it will transmit back an on/off hook signal.
	   When the value is set to no(2) & the device receives an on/off hook signal
       it will NOT transmit back an on/off hook signal.
       
       Default value for WR FXO: no(2)."
       ::= {prtVc2CnfgEntry 24}

prtExVc2EandMType OBJECT-TYPE
       SYNTAX INTEGER
	   {
       notApplicable (1),
	   type1 (2),
       type2 (3),
       type3 (4),
       type5 (5)  -- SSDC5  
       }
      MAX-ACCESS  read-write
      STATUS  current
      DESCRIPTION
      "This is the signaling type on the E&M analog side.
       The analog signaling includes voltage, no. of pins and other parameters."
       ::= {prtVc2CnfgEntry 25}

prtExVc2RemType OBJECT-TYPE
       SYNTAX INTEGER
	   {
       notApplicable (1),
	   lb  (2),
       pbx (3),
	   e1  (4),
	   t1  (5),	 --T1ESF
	   t1D4  (6)
       }
      MAX-ACCESS  read-write
      STATUS  current
      DESCRIPTION
      "Remote Type.
       Applicable for VC-6A/4LB card &
       for IPMUX-1E Far End Type - E1,T1(T1-ESF) or T1-D4 ."
       ::= {prtVc2CnfgEntry 26}

prtExVc2ConvTime OBJECT-TYPE
       SYNTAX INTEGER
	   {
       notApplicable (1),
	   m2 (2),
       m3 (3),
	   m5 (4),
	   unlimited (5)
       }
      MAX-ACCESS  read-write
      STATUS  current
      DESCRIPTION
      "Conversation Time in minutes.
       Applicable for VC-6A/4LB card."
       ::= {prtVc2CnfgEntry 27}

prtExVc2SigFeedback OBJECT-TYPE
       SYNTAX INTEGER
	   {
       notApplicable (1),
	   no  (2),
       yes (3)
       }
      MAX-ACCESS  read-write
      STATUS  current
      DESCRIPTION
      "Signaling Feedback.
       Applicable for VC-8/FXO and VC-16/FXO cards."
       ::= {prtVc2CnfgEntry 28}


prtExVc2EchoCancelerModule OBJECT-TYPE
      SYNTAX  INTEGER
       {
       notApplicable (1),
       notExist   (2),
       exist      (3)
       }
      MAX-ACCESS  read-only
      STATUS  current
      DESCRIPTION
      "This parameter indicates whether Echo canceler module exists for this port."
      ::= {prtVc2CnfgEntry 29}



--
-- Megaplex?000/?004 port specific config for HS(TDM) modules
-- HS-2,HS-3,HS-Q, HS-Q/SC, HS-6, HS-12
--
prtHsfCnfgTable OBJECT-TYPE
      SYNTAX SEQUENCE OF PrtHsfCnfgEntry
      MAX-ACCESS not-accessible
      STATUS  current
      DESCRIPTION
       "The write operation into the Table Objects is valid only
        to the TmpCnfg entry."
      ::= { cnfgPrtMux 6}

prtHsfCnfgEntry OBJECT-TYPE
      SYNTAX PrtHsfCnfgEntry
      MAX-ACCESS not-accessible
      STATUS current
	DESCRIPTION  "An entry in table."
	INDEX {prtHsfCnfgIdx, prtHsfSltIdx, prtHsfPrtIdx }
      ::= { prtHsfCnfgTable 1}

PrtHsfCnfgEntry ::=
      SEQUENCE {
        prtHsfCnfgIdx       	Integer32,
        prtHsfSltIdx        	INTEGER,
        prtHsfPrtIdx        	INTEGER,
        prtExHsfConnect     	INTEGER,
        prtExHsfRate        	INTEGER,
        prtExHsfClkMode     	INTEGER,
        prtExHsfCts        	 	INTEGER,
        prtExHsfFifoSize    	INTEGER,
        prtExHsfLinkTo      	INTEGER,
  		prtExHsfOperMode    	INTEGER,
  		prtExHsfInbandLoopback 	INTEGER,
		prtExHsfClkPolarity     INTEGER,
		prtExHsfControlSignal   INTEGER
      }

prtHsfCnfgIdx OBJECT-TYPE
      SYNTAX  Integer32 (1..255)
      MAX-ACCESS  read-only
      STATUS  current
      DESCRIPTION
      "This attribute indicates the Idx of the Cnfg (1..100) being
       accessed.
       Idx  255 relate to the TmpCnfg. "
      ::= {prtHsfCnfgEntry 1}
-- In phase I only the values 1 (Cnfg1) and 255 (temp) are valid.

prtHsfSltIdx OBJECT-TYPE
      SYNTAX  INTEGER
          {
       io1   (5),
       io2   (6),
       io3   (7),
       io4   (8),
       io5   (9),
       io6  (10),
       io7  (11),
       io8  (12),
       io9  (13),
       io10 (14),
       io11 (15),
       io12 (16)
       }
      MAX-ACCESS  read-only
      STATUS  current
      DESCRIPTION
      "This attribute indicates a unique  slot  position where
       the card is inserted.
       In the ?004 Unit the entries io6(10)..io16) are not valid."
      ::= {prtHsfCnfgEntry 2}

prtHsfPrtIdx OBJECT-TYPE
      SYNTAX  INTEGER
          {
          exPrt1    (1) ,
          exPrt2    (2) ,
          exPrt3    (3) ,
         exPrt4    (4) ,
         exPrt5    (5) ,
         exPrt6    (6) ,
         exPrt7    (7) ,
         exPrt8    (8) ,
         exPrt9    (9) ,
         exPrt10  (10) ,
         exPrt11  (11) ,
         exPrt12  (12)
          }
      MAX-ACCESS  read-only
      STATUS  current
      DESCRIPTION
      "This attribute indicates a unique  external port index.
        Hs2 has only two ports (exPrt1,exPrt2).
        Hs3 has three ports (exPrt1,exPrt2,exPrt3).
        Hsq and hsqN has four ports.
        Hs6 has six external ports.
        Hs12 has twelve external ports."
      ::= {prtHsfCnfgEntry 3}

prtExHsfConnect OBJECT-TYPE
      SYNTAX  INTEGER
              {
                no  (2),
                yes (3)
              }
      MAX-ACCESS  read-write
      STATUS  current
      DESCRIPTION
      "This attribute indicates whether the port should be
       considered in any of the mux algorithms."
      ::= {prtHsfCnfgEntry 4}


prtExHsfRate     OBJECT-TYPE
      SYNTAX  INTEGER
       {
        r1x56eq56Kbps    (1),
        r1x64eq64Kbps    (2),
        r2x56eq112Kbps   (3),
        r2x64eq128Kbps   (4),
        r3x56eq168Kbps   (5),
        r3x64eq192Kbps   (6),
        r4x56eq224Kbps   (7),
        r4x64eq256Kbps   (8),
        r5x56eq280Kbps   (9),
        r5x64eq320Kbps  (10),
        r6x56eq336Kbps  (11),
        r6x64eq384Kbps  (12),
        r7x56eq392Kbps  (13),
        r7x64eq448Kbps  (14),
        r8x56eq448Kbps  (15),
        r8x64eq512Kbps  (16),
        r9x56eq504Kbps  (17),
        r9x64eq576Kbps  (18),
        r10x56eq560Kbps (19),
        r10x64eq640Kbps (20),
        r11x56eq616Kbps (21),
        r11x64eq704Kbps (22),
        r12x56eq672Kbps (23),
        r12x64eq768Kbps (24),
        r13x56eq728Kbps (25),
        r13x64eq832Kbps (26),
        r14x56eq784Kbps (27),
        r14x64eq896Kbps (28),
        r15x56eq840Kbps (29),
        r15x64eq960Kbps (30),
        r16x56eq896Kbps (31),
        r16x64eq1024Kbps(32),
        r17x56eq952Kbps (33),
        r17x64eq1088Kbps(34),
        r18x56eq1008Kbps(35),
        r18x64eq1152Kbps(36),
        r19x56eq1064Kbps(37),
        r19x64eq1216Kbps(38),
        r20x56eq1120Kbps(39),
        r20x64eq1280Kbps(40),
        r21x56eq1176Kbps(41),
        r21x64eq1344Kbps(42),
        r22x56eq1232Kbps(43),
        r22x64eq1408Kbps(44),
        r23x56eq1288Kbps(45),
        r23x64eq1472Kbps(46),
        r24x56eq1344Kbps(47),
        r24x64eq1536Kbps(48),
        r25x56eq1400Kbps(49),
        r25x64eq1600Kbps(50),
        r26x56eq1456Kbps(51),
        r26x64eq1664Kbps(52),
        r27x56eq1512Kbps(53),
        r27x64eq1728Kbps(54),
        r28x56eq1568Kbps(55),
        r28x64eq1792Kbps(56),
        r29x56eq1624Kbps(57),
        r29x64eq1856Kbps(58),
        r30x56eq1680Kbps(59),
        r30x64eq1920Kbps(60),
        r31x56eq1736Kbps(61),
        r31x64eq1984Kbps(62),
  r32Kbps         (63)
       }
      MAX-ACCESS  read-write
      STATUS  current
      DESCRIPTION
      "This attribute indicates the port speed. "
      ::= {prtHsfCnfgEntry 5}

prtExHsfClkMode OBJECT-TYPE
      SYNTAX  INTEGER
       {
          dce     (1),
          ext-dce (2),
          dte     (3),
    none    (4)
       }
      MAX-ACCESS  read-write
      STATUS  current
      DESCRIPTION
      "This attribute indicates a unique port operation clock mode."
      ::= { prtHsfCnfgEntry 6}

prtExHsfCts OBJECT-TYPE
      SYNTAX  INTEGER
       {
     notApplicable (1),
     on            (2),
     rts           (3)
       }
      MAX-ACCESS  read-write
      STATUS  current
      DESCRIPTION
      "This attribute indicates a unique CTS control line
       operation mode."
      ::= {prtHsfCnfgEntry 7}

prtExHsfFifoSize OBJECT-TYPE
      SYNTAX  INTEGER
       {
     auto     (2),
           s16bits  (3),
           s30bits  (4),
           s52bits  (5),
           s72bits  (6)
       }
      MAX-ACCESS  read-write
      STATUS  current
      DESCRIPTION
      "Size in bits."
      ::= {prtHsfCnfgEntry 8}

prtExHsfLinkTo  OBJECT-TYPE
      SYNTAX  INTEGER
       {
       io1   (5),
       io2   (6),
       io3   (7),
       io4   (8),
       io5   (9),
       io6  (10),
       io7  (11),
       io8  (12),
       io9  (13),
       io10 (14),
       io11 (15),
       io12 (16)
       }
      MAX-ACCESS  read-write
      STATUS  deprecated
      DESCRIPTION
      "This attribute indicates a slot of Main Link module, that the
       port is linked to. This object is the same for all the
       ports in the specific card because of HW limitations.
       STATUS  deprecated - this object is replaced by prtGenCnfgLinkToSlot
       and prtGenCnfgLinkToPort."
      ::= {prtHsfCnfgEntry 9}

prtExHsfOperMode OBJECT-TYPE
      SYNTAX  INTEGER
       {
       normal          (2),
       unidirectRx     (3),
    broadcast       (4)
       }
      MAX-ACCESS  read-write
      STATUS  current
      DESCRIPTION
      "This object indicates the operation mode of the port.
       normal = bi-directional (Tx/Rx)
       unidirectRx = unidirectional Rx.
       broadcast = Tx upon request."
      ::= {prtHsfCnfgEntry 10}


prtExHsfInbandLoopback OBJECT-TYPE
      SYNTAX  INTEGER
       {
       notApplicable   (1),
       disabled        (2),
       ft1Enabled      (3)
       }
      MAX-ACCESS  read-write
      STATUS  current
      DESCRIPTION
      "This object indicates if Inband Loopback from the Network
       should be enabled or disabled."
      ::= {prtHsfCnfgEntry 11}


prtExHsfClkPolarity OBJECT-TYPE
      SYNTAX  INTEGER
       {
       notApplicable   (1),
       normal          (2),
       invert          (3)
       }
      MAX-ACCESS  read-write
      STATUS  current
      DESCRIPTION
      "This object indicates the clock polarity.
       For FCD-M this object will be applicable only for the fixed HS port
       (the fixed port on the device)."
      ::= {prtHsfCnfgEntry 12}

prtExHsfControlSignal OBJECT-TYPE
      SYNTAX  INTEGER
       {
       notApplicable   (1),
       local           (2),
       endToEnd        (3)
       }
      MAX-ACCESS  read-write
      STATUS  current
      DESCRIPTION
      "This object indicates the Control Signal according to G.797 ITU-T standard.
       For FCD-M this object will be applicable for the fixed HS port
       (the fixed port on the device) and HS-Q/N channels.
       Local and End to End are applicable only when channel Interface type is RS-530, 
       else it will be Not Applicable."
      ::= {prtHsfCnfgEntry 13}





--
-- Megaplex?000/?004 Hs-4/1(HS4T1) HS-4/2(HS4E1) port configuration
--
--prtExHs4CnfgTable   OBJECT IDENTIFIER ::= {prtHs4Cnfg 1}
--prtExHs4TsCnfgTable OBJECT IDENTIFIER ::= {prtHs4Cnfg 2}

prtExHs4CnfgTable OBJECT-TYPE
      SYNTAX SEQUENCE OF PrtExHs4CnfgEntry
      MAX-ACCESS not-accessible
      STATUS  current
      DESCRIPTION
       "The write operation into the Table Objects is valid only
        to the TmpCnfg entry."
      ::= {prtHs4Cnfg 1}

prtExHs4CnfgEntry OBJECT-TYPE
      SYNTAX PrtExHs4CnfgEntry
      MAX-ACCESS not-accessible
      STATUS current
	DESCRIPTION  "An entry in table."
	INDEX {prtExHs4CnfgIdx, prtExHs4SltIdx,  prtExHs4PrtIdx }
      ::= { prtExHs4CnfgTable 1}

PrtExHs4CnfgEntry ::=
      SEQUENCE {
        prtExHs4CnfgIdx     Integer32,
        prtExHs4SltIdx      INTEGER,
        prtExHs4PrtIdx      INTEGER,

     prtExHs4Connect     INTEGER,
     prtExHs4LineType    INTEGER,
     prtExHs4LineCode    INTEGER,
     prtExHs4LineLen     INTEGER,
     prtExHs4RestoreT    INTEGER,
     prtExHs4OosSig      INTEGER,
     prtExHs4OosCode     INTEGER,
     prtExHs4IdleCode    Integer32,
     prtExHs4MfClkSrcSlt INTEGER,
     prtExHs4MfClkSrcPrt INTEGER
      }

prtExHs4CnfgIdx OBJECT-TYPE
      SYNTAX  Integer32  (1..255)
      MAX-ACCESS  read-only
      STATUS  current
      DESCRIPTION
      "This attribute indicates the Idx of the Cnfg (1..100) being
       accessed.
       Idx  255 relates to the TmpCnfg"
      ::= {prtExHs4CnfgEntry 1}
-- In phase I only the values 1 (Cnfg1) and 255 (temp) are valid.

prtExHs4SltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      MAX-ACCESS  read-only
      STATUS  current
      DESCRIPTION
      "This attribute indicates a unique  slot  position where
       the card is inserted."
      ::= {prtExHs4CnfgEntry 2}

prtExHs4PrtIdx OBJECT-TYPE
      SYNTAX  INTEGER
     {
       exPrt1    (1)
     }
      MAX-ACCESS  read-only
      STATUS  current
      DESCRIPTION
      "A unique identifier of the port, within the card."
      ::= {prtExHs4CnfgEntry 3}

prtExHs4Connect OBJECT-TYPE
      SYNTAX  INTEGER
       {
  no  (2),
  yes (3)
       }
      MAX-ACCESS  read-write
      STATUS  current
      DESCRIPTION
      "This attribute indicates whether the port should be
       considered in any of the mux  algorithm. It also affects
       all the module considerations because the card has only
       one external (physical) interface."
      ::= {prtExHs4CnfgEntry 4}

prtExHs4LineType    OBJECT-TYPE
      SYNTAX  INTEGER
       {
  esfT1          (2), --> dsx1ESF
  sfT1           (3), --> dsx1D4
  g732nE1        (4), --> dsx1E1
  g732nE1CRC    (5), --> dsx1E1-CRC
  g732sE1        (6), --> dsx1E1-MF
  g732sE1CRC    (7)  --> dsx1E1-MF-CRC
       }
      MAX-ACCESS  read-write
      STATUS  current
      DESCRIPTION
      "This attribute is the line type parameter for T1/E1
       interface.
       The user should select only the parameters relevant to the
       specific card:
       T1 line code parameters for the HS-4/1 and
       E1 line code parameters for the HS-4/2.
       This parameter has the same values as dsx1LineType in T1/E1
       MIB (RFC-1406). The parameters in dsx1LineType are:
      other          (1)
      dsx1ESF        (2)
      dsx1D4         (3)
      dsx1E1         (4)
      dsx1E1-CRC     (5)
      dsx1E1-MF      (6)
      dsx1E1-MF-CRC  (7)"
      ::= {prtExHs4CnfgEntry 5}

prtExHs4LineCode OBJECT-TYPE
      SYNTAX  INTEGER
       {
  b7T1   (1),  --> dsx1JBZS
  b8zsT1 (2),  --> dsx1B8ZS
        hdb3E1 (4)   --> dsx1HDB3
       }
      MAX-ACCESS  read-write
      STATUS  current
      DESCRIPTION
      "This attribute is the line code parameter used for T1/E1
       interface.
       The user should select only the parameters relevant to the
       specific card:
       T1 line code parameters for the MPH.1/T1 and
       E1 line code parameters for the MPH.1/E1.
       This parameter has the same values as dsx1LineCoding in T1/E1
       MIB (RFC-1406).  The parameters in dsx1LineCoding are:
     dsx1JBZS  (1)
     dsx1B8ZS  (2)
     dsx1HDB3  (3)
     dsx1ZBTSI (4)
     dsx1AMI   (5)
     other     (6)"
      ::= {prtExHs4CnfgEntry 6}

prtExHs4LineLen  OBJECT-TYPE
      SYNTAX  INTEGER
       {
  unknown   (1),
        len0p133ft   (2),
        len134p266ft (3),
        len267p399ft (4),
        len400p533ft (5),
        len534p655ft (6),
        fcc68    (7)
       }
      MAX-ACCESS  read-write
      STATUS  current
      DESCRIPTION
      "This attribute is the line length parameter used only for
       T1 interfaces.
       len399p533ft=len-399-533ft "
      ::= {prtExHs4CnfgEntry 7}

prtExHs4RestoreT OBJECT-TYPE
      SYNTAX  INTEGER
       {
        restoreT1secFast      (2),
        restoreT10sec62411    (3),
  ccittE1       (4)
       }
      MAX-ACCESS  read-write
      STATUS  current
      DESCRIPTION
      "Time passing from the disappearance of the loss of
       synchronization condition (red alarm), to the restoration
       of normal service."
      ::= {prtExHs4CnfgEntry 8}

prtExHs4OosSig   OBJECT-TYPE
      SYNTAX  INTEGER
       {
        notsupported  (2),
        forcedIdle    (3),
        forcedBusy    (4),
        busyIdle      (5),
        idleBusy      (6)
       }
      MAX-ACCESS  read-write
      STATUS  current
      DESCRIPTION
      "Out of Service signal type."
      ::= {prtExHs4CnfgEntry 9}

prtExHs4OosCode  OBJECT-TYPE
      SYNTAX  INTEGER
          {
          notsupported (2),
            oosCode00H        (3),
            oosCode1aH        (4),
            oosCode54H        (5),
            oosCode7eH        (6),
            oosCode7fH        (7),
            oosCode98H        (8),
            oosCode9eH        (9),
            oosCoded5H        (10),
            oosCodee4H        (11),
            oosCodeffH        (12)
          }
      MAX-ACCESS  read-write
      STATUS  current
      DESCRIPTION
      "OOS Code"
      ::= {prtExHs4CnfgEntry 10}

prtExHs4IdleCode  OBJECT-TYPE
      SYNTAX  Integer32
      MAX-ACCESS  read-write
      STATUS  current
      DESCRIPTION
      " Type value(00 - FF HEX), excluding 0H,8H,10H,12H,21H,24H,
        42H,49H,84H,92H"
      ::= {prtExHs4CnfgEntry 11}

prtExHs4MfClkSrcSlt  OBJECT-TYPE
      SYNTAX  INTEGER
       {
          local (2),
       io1   (5),
       io2   (6),
       io3   (7),
       io4   (8),
       io5   (9),
       io6  (10),
       io7  (11),
       io8  (12),
       io9  (13),
       io10 (14),
       io11 (15),
       io12 (16)
       }
      MAX-ACCESS  read-write
      STATUS  current
      DESCRIPTION
"This attribute indicates whether the port Tx is multiframe
synchronized with Rx multiframe of another port and the slot position of that port.
This opration is required in order to bypass signaling of PCM
voice channels.
When its value is Local(2) there is no meaning to 'prtExHs4MfClkSrcPrt'
parameter.
In the ?004 Unit the entries io6(10)..io16) are not valid"
      ::= {prtExHs4CnfgEntry 12}

prtExHs4MfClkSrcPrt  OBJECT-TYPE
      SYNTAX  INTEGER
      {
       exPrt1    (1),
       exPrt2    (2),
       inPrt1  (101)
      }
      MAX-ACCESS  read-write
      STATUS  current
      DESCRIPTION
      "A unique number to identify a port position in the mux if the
       MultiFrame clock source is valid (YES).
       inPrt1 - for MTML-H/E1 cards."
      ::= {prtExHs4CnfgEntry 13}

--
-- Hs4 Time Slot Config Table
--
prtExHs4TsCnfgTable OBJECT-TYPE
     SYNTAX SEQUENCE OF PrtExHs4TsEntry
     MAX-ACCESS not-accessible
     STATUS  current
     DESCRIPTION
      "The write operation into the Table Objects is valid only
       to the TmpCnfg entry."
     ::= {prtHs4Cnfg 2}

prtExHs4TsEntry OBJECT-TYPE
      SYNTAX PrtExHs4TsEntry
      MAX-ACCESS not-accessible
      STATUS current
	DESCRIPTION  "An entry in table."
	INDEX {prtExHs4TsCnfgIdx, prtExHs4TsSltIdx, prtExHs4TsPrtIdx, prtExHs4TsIdx }
      ::= { prtExHs4TsCnfgTable 1}

PrtExHs4TsEntry ::=
      SEQUENCE {
      prtExHs4TsCnfgIdx        Integer32,
      prtExHs4TsSltIdx         INTEGER,
      prtExHs4TsPrtIdx         INTEGER,
      prtExHs4TsIdx            Integer32,
      prtExHs4TsIConSlot       INTEGER,
      prtExHs4TsIConPrt        INTEGER,
      prtExHs4TsIConTs         Integer32 
	}

prtExHs4TsCnfgIdx OBJECT-TYPE
      SYNTAX  Integer32  (1..255)
      MAX-ACCESS  read-only
      STATUS  current
      DESCRIPTION
      "This attribute indicates the Idx of the Cnfg (1..100) being
       accessed.
       Idx 255 relates to the TmpCnfg. "
      ::= { prtExHs4TsEntry 1}
-- In phase I only the values 1 (Cnfg1) and 255 (temp) are valid.

prtExHs4TsSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      MAX-ACCESS  read-only
      STATUS  current
      DESCRIPTION
      "This attribute indicates a unique  slot  position where
       the card is inserted.
       In the ?004 Unit the entries io6(10)..io16) are not valid"
      ::= { prtExHs4TsEntry 2}

prtExHs4TsPrtIdx OBJECT-TYPE
      SYNTAX  INTEGER
 {
          exPrt1    (1)
       }
      MAX-ACCESS  read-only
      STATUS  current
      DESCRIPTION
      "This attribute indicates a unique  port number.
       Hs4/T1 and Hs4/T1 cards have only one external interface."
      ::= { prtExHs4TsEntry 3}

prtExHs4TsIdx OBJECT-TYPE
      SYNTAX  Integer32
      MAX-ACCESS  read-only
      STATUS  current
      DESCRIPTION
      "This attribute indicates a unique time slot  position.
       The valid time slots are:
       1..24 for T1 Card and
       1..31 for E1 interface.
       In G732S-E1 lines, time slot 16 is not valid for data,
       it is dedicated to multiframe synchronization bits
       and voice signaling."
      ::= { prtExHs4TsEntry 4}

prtExHs4TsIConSlot OBJECT-TYPE
      SYNTAX  INTEGER
       {
       noConnect (2),
          io1       (5),
          io2       (6),
          io3       (7),
          io4       (8),
          io5       (9),
          io6      (10),
          io7      (11),
          io8      (12),
          io9      (13),
          io10     (14),
          io11     (15),
          io12     (16),
    split   (100)
       }
      MAX-ACCESS  read-write
      STATUS  current
      DESCRIPTION
      "This attribute indicates whether the specified time slot is
       connected/routed internally in the Agent and to which card
       it is connected.
       In the ?004 Unit the entries io6(10)..io16) are not valid.
    split - will be used when the Src TS is connected to more
               than one slot OR more than one port (each needing
               less than a whole TS)."
      ::= {prtExHs4TsEntry 5}

prtExHs4TsIConPrt OBJECT-TYPE
      SYNTAX  INTEGER
       {
       exPrt1    (1) ,
       exPrt2    (2) ,
       exPrt3    (3) ,
       exPrt4    (4) ,
       exPrt5    (5) ,
       exPrt6    (6) ,
       exPrt7    (7) ,
       exPrt8    (8) ,
       exPrt9    (9) ,
       exPrt10  (10) ,
       exPrt11  (11) ,
       exPrt12  (12) ,
       noConnect (100)
       }
      MAX-ACCESS  read-write
      STATUS  current
      DESCRIPTION
      "This attribute indicates the internally (In Mux)
       connected/routed port."
      ::= {prtExHs4TsEntry 6}

prtExHs4TsIConTs OBJECT-TYPE
      SYNTAX  Integer32
      MAX-ACCESS  read-write
      STATUS  current
      DESCRIPTION
      "This attribute indicates a unique time slot  position.
       The valid time slots are:
       1..24 for T1 Module and
       1..31 for E1 interface.
       In G732S-E1 lines time slot 16 is not valid for data,
       it is dedicated for multiframe synchronization bits
       and voice signaling."
      ::= { prtExHs4TsEntry 7}

--
-- Megaplex?000/?004 and DXC Hs-U port configuration
--
--prtExHsiCnfgTable   OBJECT IDENTIFIER ::= {prtHsiCnfg 1}

prtExHsiCnfgTable OBJECT-TYPE
      SYNTAX SEQUENCE OF PrtExHsiCnfgEntry
      MAX-ACCESS not-accessible
      STATUS  current
      DESCRIPTION
       "The write operation into the Table Objects is valid only
        to the TmpCnfg entry."
      ::= {prtHsiCnfg 1}

prtExHsiCnfgEntry OBJECT-TYPE
      SYNTAX PrtExHsiCnfgEntry
      MAX-ACCESS not-accessible
      STATUS current
	DESCRIPTION  "An entry in table."
	INDEX {prtExHsiCnfgIdx, prtExHsiSltIdx,  prtExHsiPrtIdx }
      ::= { prtExHsiCnfgTable 1}

PrtExHsiCnfgEntry ::=
      SEQUENCE {
        prtExHsiCnfgIdx     Integer32,
        prtExHsiSltIdx      INTEGER,
        prtExHsiPrtIdx      Integer32,

        prtExHsiConnect     INTEGER,
        prtExHsiRate        INTEGER,
        prtExHsiLinkTo      INTEGER,
        prtExHsiInterface   INTEGER,
		prtExHsiActType		INTEGER
      }

prtExHsiCnfgIdx OBJECT-TYPE
      SYNTAX  Integer32  (1..255)
      MAX-ACCESS  read-only
      STATUS  current
      DESCRIPTION
      "This attribute indicates the Idx of the Cnfg (1..100) being
       accessed.
       Idx 255 relates to the TmpCnfg"
      ::= {prtExHsiCnfgEntry 1}
-- In phase I only the values 1 (Cnfg1) and 255 (temp) are valid.

prtExHsiSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16),
	   io13 (17),
	   io14 (18),
	   io15 (19),
	   notApplicable (255)
     }
      MAX-ACCESS  read-only
      STATUS  current
      DESCRIPTION
      "This attribute indicates a unique  slot  position where
       the card is inserted."
      ::= {prtExHsiCnfgEntry 2}

prtExHsiPrtIdx OBJECT-TYPE
      SYNTAX  Integer32
--     {
--          exPrt1    (1),
--          exPrt2    (2),
--          exPrt3    (3),
--          exPrt4    (4),
--          exPrt5    (5),
--          exPrt6    (6),
--          exPrt7    (7),
--          exPrt8    (8),
--          exPrt9    (9),
--          exPrt10  (10),
--          exPrt11  (11),
--          exPrt12  (12)
--        }
      MAX-ACCESS  read-only
      STATUS  current
      DESCRIPTION
      "A unique port identifier within the card.
       For MP : 1..12
       For DXC: 111 .. 2531. See DXC R6 spec for port index convention.
       For FCD-A, 'S' Interface external ports: 131, 141, 151, 161."
      ::= {prtExHsiCnfgEntry 3}

prtExHsiConnect OBJECT-TYPE
      SYNTAX  INTEGER
       {
        no  (2),
        yes (3),
		v51 (4)
       }
      MAX-ACCESS  read-write
      STATUS  current
      DESCRIPTION
      "This attribute indicates whether the port should be considered in
       any of the mux  algorithms.
       v51 - this port is connected to a V5.1 interface. All rest of the
             values will be 'notApplicable' in this case. V5.1 MIB will be
             used instead."
      ::= {prtExHsiCnfgEntry 4}

prtExHsiRate    OBJECT-TYPE
      SYNTAX  INTEGER
       {
          r600bps   (2),
          r1200bps  (3),
          r2400bps  (4),
          r4800bps  (5),
          r9600bps  (6),
          r19200bps (7),
          r38400bps (8),
          r48kbps   (9),
          r56kbps  (10),
          r64kbps  (11),
          r128kbps (12),
    notApplicable (255)
       }
      MAX-ACCESS  read-write
      STATUS  current
      DESCRIPTION
      "This attribute indicates the port speed."
      ::= {prtExHsiCnfgEntry 5}

prtExHsiLinkTo  OBJECT-TYPE
      SYNTAX  INTEGER
       {
       io1   (5),
       io2   (6),
       io3   (7),
       io4   (8),
       io5   (9),
       io6  (10),
       io7  (11),
       io8  (12),
       io9  (13),
       io10 (14),
       io11 (15),
       io12 (16)
       }
      MAX-ACCESS  read-write
      STATUS  deprecated
      DESCRIPTION
      "It indicates the slot of the main link card to which the HS-? card
       is mapped.
       STATUS  deprecated - this object is replaced by prtGenCnfgLinkToSlot
       and prtGenCnfgLinkToPort."
      ::= {prtExHsiCnfgEntry 6}

prtExHsiInterface  OBJECT-TYPE
      SYNTAX  INTEGER
       {
       lt   (1),
       nt   (2),
       te   (3),
	   lt1  (4),
    notApplicable (255)
       }
      MAX-ACCESS  read-write
      STATUS  current
      DESCRIPTION
      "It indicates the interface type:
       lt = line termination
       nt = network termination
       te = terminal equipment.
	   lt1 - for ASMi-31 connection (not ISDN)
	   For MP:
       For HS-U/I and HS-U/1 only 'lt' and 'nt' are applicable.
       For HS-S , only 'te' and 'nt' are applicable.
       For HS-U, this object is not applicable.
       For HS-U6, HS-U12, are applicable: 'lt'=lt-i,'nt'=nt-i, lt1.
       For DXC:
       For HS-U8, HS-U16, are applicable: 'lt'=LT-I,'nt'=NT-I, 'lt1'=LT-1."
      ::= {prtExHsiCnfgEntry 7}

prtExHsiActType  OBJECT-TYPE
      SYNTAX  INTEGER
       {
       notApplicable (1),
       type1 (2),
       type2 (3),
	   type3 (4)
       }
      MAX-ACCESS  read-write
      STATUS  current
      DESCRIPTION
      "It indicates the Activation Type. Activation Type is the Synchronization
	   type towards the PBX. It is applicable only when prtExHsiInterface=nt.
	   notApplicable - for cards that do not support this object, or when 
	   prtExHsiInterface is NOT nt."
      ::= {prtExHsiCnfgEntry 8}


--prtInHsiCnfgTable   OBJECT IDENTIFIER ::= {prtHsiCnfg 2}
--This table is not applicable for MP-2100 HS-U card type

prtInHsiCnfgTable OBJECT-TYPE
      SYNTAX SEQUENCE OF PrtInHsiCnfgEntry
      MAX-ACCESS not-accessible
      STATUS  current
      DESCRIPTION
       "The write operation into the Table Objects is valid only
        to the TmpCnfg entry.
        This table is not applicable for MP-2100 HS-U card type."
      ::= {prtHsiCnfg 2}

prtInHsiCnfgEntry OBJECT-TYPE
      SYNTAX PrtInHsiCnfgEntry
      MAX-ACCESS not-accessible
      STATUS current
	DESCRIPTION  "An entry in table."
	INDEX {prtInHsiCnfgIdx, prtInHsiSltIdx,  prtInHsiPrtIdx }
      ::= { prtInHsiCnfgTable 1}

PrtInHsiCnfgEntry ::=
      SEQUENCE {
        prtInHsiCnfgIdx     Integer32,
        prtInHsiSltIdx      INTEGER,
        prtInHsiPrtIdx      Integer32,

        prtInHsiConnect     INTEGER,
        prtInHsiRate        INTEGER,
		prtInHsiConcentratedTo Integer32 
	}

prtInHsiCnfgIdx OBJECT-TYPE
      SYNTAX  Integer32  (1..255)
      MAX-ACCESS  read-only
      STATUS  current
      DESCRIPTION
      "This object indicates the Idx of the Cnfg (1..100) being
       accessed.
       Idx 255 relates to the TmpCnfg"
      ::= {prtInHsiCnfgEntry 1}

prtInHsiSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16),
	   io13 (17),
	   io14 (18),
	   io15 (19),
	   notApplicable (255)
     }
      MAX-ACCESS  read-only
      STATUS  current
      DESCRIPTION
      "This object indicates a unique  slot  position where
       the card is inserted."
      ::= {prtInHsiCnfgEntry 2}

prtInHsiPrtIdx OBJECT-TYPE
      SYNTAX  Integer32
      MAX-ACCESS  read-only
      STATUS  current
      DESCRIPTION
      "A unique port identifier within the card.
       Valid values for MP: inPrt1 (101) .. inPrt48 (148).
       Valid values for DXC: 11012.. 25316. See DXC R6 spec for port index convention."
      ::= {prtInHsiCnfgEntry 3}

prtInHsiConnect OBJECT-TYPE
      SYNTAX  INTEGER
       {
       no  (2),
       yes (3)
       }
      MAX-ACCESS  read-write
      STATUS  current
      DESCRIPTION
      "This attribute indicates whether the port should be considered in
       any of the mux  algorithms."
      ::= {prtInHsiCnfgEntry 4}

prtInHsiRate    OBJECT-TYPE
      SYNTAX  INTEGER
       {
          r600bps   (2),
          r1200bps  (3),
          r2400bps  (4),
          r4800bps  (5),
          r9600bps  (6),
          r19200bps (7),
          r38400bps (8),
          r48kbps   (9),
          r56kbps  (10),
          r64kbps  (11),
          r128kbps (12),
		  concentrated  (13),
		  notConnected (100),  
          notApplicable(255)
          }
      MAX-ACCESS  read-write
      STATUS  current
      DESCRIPTION
      "This object indicates the port speed.
       For HS-U/I and HS-S ports:
       2 bit - up to 9600bps
       4 bit - 19200bps
       8 bit - 38400bps .. 64kbps.
       concentrated - this D channel goes to a Concentration channel,
                      that represents many channels that this value was
                      selected for them. The Concentrated channel is an
                      Internal D Channel of the same card. 
                      This value is applicable only for	D channels, except 
                      Concentration channel itself.
                      --for HS-S and HS-U/I cards the Concentration channel 
                        will always be: internal-13
                      --for MP-2200 HS-S12, HS-S6, HS-U12, HS-U6 and
                        DXC HS-U8 and HS-U16 cards, the Concentration channel
                        is selected via the prtInHsiConcentratedTo object.
       notConnected - same as prtInHsiConnect=no."
      ::= {prtInHsiCnfgEntry 5}

prtInHsiConcentratedTo OBJECT-TYPE
      SYNTAX  Integer32
      MAX-ACCESS  read-write
      STATUS  current
      DESCRIPTION
      "The Concentration D Channel of the prtInHsiPrtIdx port.
	   The port always belongs to the same card as prtInHsiPrtIdx port.
	   This object is applicable only when prtInHsiRate=concentrated.
       Valid values:
	   - notApplicable: 255
       - for MP-2200: HS-S12, HS-U12 cards: inPrt37 (137) .. inPrt48 (148).
                      HS-S6, HS-U6 cards: inPrt19 (119) .. inPrt24 (124).
       - for DXC:     HS-U8  cards: 112 .. 254
                      HS-U16 cards: 112 .. 258. See DXC R6 spec for port index 
                      convention."
      ::= {prtInHsiCnfgEntry 6}

--
-- Megaplex?000/?004 Hs-R and HS-U port configuration
-- DXC HS-U8, HS-U16 port configuration for Interface=LT-1
--
--prtExHsrCnfgTable   OBJECT IDENTIFIER ::= {prtHsrCnfg 1}

prtExHsrCnfgTable OBJECT-TYPE
      SYNTAX SEQUENCE OF PrtExHsrCnfgEntry
      MAX-ACCESS not-accessible
      STATUS  current
      DESCRIPTION
       "The write operation into the Table Objects is valid only
        to the TmpCnfg entry."
      ::= {prtHsrCnfg 1}

prtExHsrCnfgEntry OBJECT-TYPE
      SYNTAX PrtExHsrCnfgEntry
      MAX-ACCESS not-accessible
      STATUS current
	DESCRIPTION  "An entry in table."
	INDEX {prtExHsrCnfgIdx, prtExHsrSltIdx,  prtExHsrPrtIdx }
      ::= { prtExHsrCnfgTable 1}

PrtExHsrCnfgEntry ::=
      SEQUENCE {
        prtExHsrCnfgIdx     Integer32,
        prtExHsrSltIdx      INTEGER,
        prtExHsrPrtIdx      Integer32,

        prtExHsrConnect     INTEGER,
        prtExHsrProtocol    INTEGER,
        prtExHsrRate        INTEGER,
        prtExHsrDataBits    INTEGER,
        prtExHsrParity      INTEGER,
        prtExHsrStopBits    INTEGER,
        prtExHsrCts         INTEGER,
        prtExHsrClkMode     INTEGER,
        prtExHsrLinkTo      INTEGER,
        prtExHsrDcdDsr      INTEGER,
        prtExHsrOperMode    INTEGER,
        prtExHsrRtsDtr      INTEGER,
		prtExHsrLlbEnable   INTEGER,
		prtExHsrRlbEnable   INTEGER,
		prtExHsrRateAdapt   INTEGER,
		prtExHsrRemoteModem INTEGER 
      }

prtExHsrCnfgIdx OBJECT-TYPE
      SYNTAX  Integer32  (1..255)
      MAX-ACCESS  read-only
      STATUS  current
      DESCRIPTION
      "This object indicates the Idx of the Cnfg (1..100) being
       accessed.
       Idx 255 relates to the TmpCnfg"
      ::= {prtExHsrCnfgEntry 1}

prtExHsrSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16),
	   io13 (17),
	   io14 (18),
	   io15 (19)
     }
      MAX-ACCESS  read-only
      STATUS  current
      DESCRIPTION
      "This object indicates a unique  slot  position where
       the card is inserted."
      ::= {prtExHsrCnfgEntry 2}

prtExHsrPrtIdx OBJECT-TYPE
      SYNTAX  Integer32
      MAX-ACCESS  read-only
      STATUS  current
      DESCRIPTION
      "A unique prt identifier within the card.
       Valid values:
	   For MP:
        - For HS-R cards: exPrt1 (1)   .. exPrt4 (4)
        - For HS-U/1 cards: inPrt1 (101) .. inPrt4 (104)
        - For HS-S12, HS-S6, HS-U12, HS-U6 cards:
          exPrt1 (1) .. exPrt12 (12). 
          This MIB table is used only for LT-1 interface.
       For DXC:
        - For HS-U8, HS-U16 cards:
          111 .. 2531 (See DXC R6 spec for port index convention). 
          This MIB table is used only for LT-1 interface."
      ::= {prtExHsrCnfgEntry 3}

prtExHsrConnect OBJECT-TYPE
      SYNTAX  INTEGER
       {
       no  (2),
       yes (3)
       }
      MAX-ACCESS  read-write
      STATUS  current
      DESCRIPTION
      "This object indicates whether the port should be considered in
       any of the mux  algorithms."
      ::= {prtExHsrCnfgEntry 4}

prtExHsrProtocol OBJECT-TYPE
      SYNTAX  INTEGER
              {
                sync  (2),
                async (3)
              }
      MAX-ACCESS  read-write
      STATUS  current
      DESCRIPTION
      "This object indicates the protocol."
      ::= {prtExHsrCnfgEntry 5}

prtExHsrRate    OBJECT-TYPE
      SYNTAX  INTEGER
       {
       r600bps    (2),
       r1200bps   (3),
       r2400bps   (4),
       r4800bps   (5),
       r9600bps   (6),
       r19200bps  (7),
       r38400bps  (8),
       r48kbps    (9),
       r56kbps   (10),
       r64kbps   (11),
       r16000bps (12),
       r32000bps (13),
       r57600bps (14),
       r115200bps(15),
       r128000bps(16),
	   notConnected (100)
       }
      MAX-ACCESS  read-write
      STATUS  current
      DESCRIPTION
      "This object indicates the port speed.
       The 16,32,48,56,64 and 128 kbps rates are applicable only for Sync
       protocol.
       The 57.6 and 115.2 kbps rates are applicable only for Async
       protocol.
       notConnected= 0 rate."
      ::= {prtExHsrCnfgEntry 6}

prtExHsrDataBits OBJECT-TYPE
      SYNTAX  INTEGER
       {
        d5bits    (1),
        d6bits    (2),
        d7bits    (3),
        d8bits    (4),
        notApplicable (255)
       }
      MAX-ACCESS  read-write
      STATUS  current
      DESCRIPTION
      "Data Bits.
       This object is applicable for Async protocol only."
      ::= {prtExHsrCnfgEntry 7}

prtExHsrParity OBJECT-TYPE
      SYNTAX  INTEGER
       {
        no  (2),
        yes (3),
		odd (4),
		even(5),
        notApplicable (255)
       }
      MAX-ACCESS  read-write
      STATUS  current
      DESCRIPTION
      "- For HS-R card, this object indicates if the parity bit is needed or not.
	     Therefore, the 'no' and 'yes; values are applicable. 
       - For HS-S12, HS-U12, the parity type is selected: no, odd, even.
       This object is applicable for Async protocol only."
      ::= { prtExHsrCnfgEntry 8}

prtExHsrStopBits OBJECT-TYPE
      SYNTAX  INTEGER
       {
        stopBits1Bit      (1),
        stopBits2Bits     (2),
        notApplicable   (255)
       }
      MAX-ACCESS  read-write
      STATUS  current
      DESCRIPTION
      "This object indicates the minimum number of stop bits in
       the tx async frame.
       This object is applicable for Async protocol only."
      ::= { prtExHsrCnfgEntry 9}

prtExHsrCts OBJECT-TYPE
      SYNTAX  INTEGER
       {
       on       (2),
       rts      (3),
       notApplicable   (255)
       }
      MAX-ACCESS  read-write
      STATUS  current
      DESCRIPTION
      "CTS.
       This object is applicable for Async protocol only."
      ::= {prtExHsrCnfgEntry 10}

prtExHsrClkMode OBJECT-TYPE
      SYNTAX  INTEGER
      {
      dce     (1),
      extDce  (2),
      notApplicable  (255)
      }
      MAX-ACCESS  read-write
      STATUS  current
      DESCRIPTION
      "Clock mode.
       This object is applicable for Sync protocol only."
      ::= { prtExHsrCnfgEntry 11}

prtExHsrLinkTo  OBJECT-TYPE
      SYNTAX  INTEGER
       {
	   notApplicable (1),
       io1   (5),
       io2   (6),
       io3   (7),
       io4   (8),
       io5   (9),
       io6  (10),
       io7  (11),
       io8  (12),
       io9  (13),
       io10 (14),
       io11 (15),
       io12 (16)
       }
      MAX-ACCESS  read-write
      STATUS  deprecated
      DESCRIPTION
      "It indicates the slot of the main link card to which the HS-R card
       is mapped.
       notApplicable - for HS-U/1 internal ports.
       STATUS  deprecated - this object is replaced by prtGenCnfgLinkToSlot
       and prtGenCnfgLinkToPort."
      ::= {prtExHsrCnfgEntry 12}

prtExHsrDcdDsr OBJECT-TYPE
      SYNTAX  INTEGER
       {
        notApplicable (1),
        local         (2),
        endToEnd      (3)
       }
      MAX-ACCESS  read-write
      STATUS  current
      DESCRIPTION
      "DCD & DSR."
      ::= {prtExHsrCnfgEntry 13}


prtExHsrOperMode OBJECT-TYPE
      SYNTAX  INTEGER
       {
       normal          (2),
       unidirectRx     (3),
       broadcast       (4)
       }
      MAX-ACCESS  read-write
      STATUS  current
      DESCRIPTION
      "This object indicates the operation mode of the port.
       normal = bi-directional (Tx/Rx)
       unidirectRx = unidirectional Rx.
       broadcast = Tx upon request."
      ::= {prtExHsrCnfgEntry 14}

prtExHsrRtsDtr OBJECT-TYPE
      SYNTAX  INTEGER
       {
        notApplicable (1),
        local         (2),
        endToEnd      (3)
       }
      MAX-ACCESS  read-write
      STATUS  current
      DESCRIPTION
      "RTS & DTR."
      ::= {prtExHsrCnfgEntry 15}

prtExHsrLlbEnable OBJECT-TYPE
      SYNTAX  INTEGER
       {
       notApplicable (1),
       disabled      (2),
       enabled       (3)
       }
      MAX-ACCESS  read-write
      STATUS  current
      DESCRIPTION
      "Enable/Disable LLB."
      ::= {prtExHsrCnfgEntry 16}

prtExHsrRlbEnable OBJECT-TYPE
      SYNTAX  INTEGER
       {
       notApplicable (1),
       disabled      (2),
       enabled       (3)
       }
      MAX-ACCESS  read-write
      STATUS  current
      DESCRIPTION
      "Enable/Disable RLB."
      ::= {prtExHsrCnfgEntry 17}

prtExHsrRateAdapt OBJECT-TYPE
      SYNTAX  INTEGER
       {
       notApplicable (1),
       proprietary   (2),
       v110          (3)
       }
      MAX-ACCESS  read-write
      STATUS  current
      DESCRIPTION
      "Rate Adaptation - takes a low rate and adapts it to 64Kbps.
       This object specifies the means this adaptation is done by."
      ::= {prtExHsrCnfgEntry 18}

prtExHsrRemoteModem OBJECT-TYPE
      SYNTAX  INTEGER
       {
    notApplicable (1),
    asmi31        (2),
    asmi31s2      (3)
       }
      MAX-ACCESS  read-write
      STATUS  current
      DESCRIPTION
      "Remote modem.
       asmi31s2 = ASMi-31/2 "
      ::= {prtExHsrCnfgEntry 19}

--
-- Megaplex?000/?004 MBE port configuration
--

prtExMbeCnfgTable OBJECT-TYPE
      SYNTAX SEQUENCE OF PrtExMbeCnfgEntry
      MAX-ACCESS not-accessible
      STATUS  current
      DESCRIPTION
       "The write operation into the Table Objects is valid only
        to the TmpCnfg entry."
      ::= {prtMbeCnfg 1}

prtExMbeCnfgEntry OBJECT-TYPE
      SYNTAX PrtExMbeCnfgEntry
      MAX-ACCESS not-accessible
      STATUS current
	DESCRIPTION  "An entry in table."
	INDEX {prtExMbeCnfgIdx, prtExMbeSltIdx,  prtExMbePrtIdx }
      ::= { prtExMbeCnfgTable 1}

PrtExMbeCnfgEntry ::=
      SEQUENCE {
        prtExMbeCnfgIdx     Integer32,
        prtExMbeSltIdx      INTEGER,
        prtExMbePrtIdx      INTEGER,

        prtExMbeLan         INTEGER
      }

prtExMbeCnfgIdx OBJECT-TYPE
      SYNTAX  Integer32  (1..255)
      MAX-ACCESS  read-only
      STATUS  current
      DESCRIPTION
      "This attribute indicates the Idx of the Cnfg (1..100) being
       accessed.
       Idx 255 relates to the TmpCnfg"
      ::= {prtExMbeCnfgEntry 1}
-- In phase I only the values 1 (Cnfg1) and 255 (temp) are valid.

prtExMbeSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      MAX-ACCESS  read-only
      STATUS  current
      DESCRIPTION
      "This attribute indicates a unique  slot  position where
       the card is inserted.
       In the ?004 Unit the entries io6(10)..io16) are not valid."
      ::= {prtExMbeCnfgEntry 2}

prtExMbePrtIdx OBJECT-TYPE
      SYNTAX  INTEGER
     {
          exPrt1    (1)
     }
      MAX-ACCESS  read-only
      STATUS  current
      DESCRIPTION
      "A unique port identifier within the card."
      ::= {prtExMbeCnfgEntry 3}

prtExMbeLan OBJECT-TYPE
      SYNTAX  INTEGER
       {
        remote  (1),
        main    (2)
       }
      MAX-ACCESS  read-write
      STATUS  current
      DESCRIPTION
      "This attribute indicates whether the MBE port is operated
       as main or remote bridge."
      ::= {prtExMbeCnfgEntry 4}

prtInMbeCnfgTable OBJECT-TYPE
      SYNTAX SEQUENCE OF PrtInMbeCnfgEntry
      MAX-ACCESS not-accessible
      STATUS  current
      DESCRIPTION
       "The write operation into the Table Objects is valid only
        to the TmpCnfg entry."
      ::= {prtMbeCnfg 2}

prtInMbeCnfgEntry OBJECT-TYPE
      SYNTAX PrtInMbeCnfgEntry
      MAX-ACCESS not-accessible
      STATUS current
	DESCRIPTION  "An entry in table."
	INDEX {prtInMbeCnfgIdx, prtInMbeSltIdx,  prtInMbePrtIdx }
      ::= { prtInMbeCnfgTable 1}

PrtInMbeCnfgEntry ::=
      SEQUENCE {
        prtInMbeCnfgIdx     Integer32,
        prtInMbeSltIdx      INTEGER,
        prtInMbePrtIdx      INTEGER,

        prtInMbeConnect     INTEGER,
        prtInMbeRate        INTEGER,
        prtInMbeLinkTo      INTEGER
      }

prtInMbeCnfgIdx OBJECT-TYPE
      SYNTAX  Integer32  (1..255)
      MAX-ACCESS  read-only
      STATUS  current
      DESCRIPTION
      "This attribute indicates the Idx of the Cnfg (1..100) being
       accessed.
       Idx 255 relates to the TmpCnfg"
      ::= {prtInMbeCnfgEntry 1}
-- In phase I only the values 1 (Cnfg1) and 255 (temp) are valid.

prtInMbeSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      MAX-ACCESS  read-only
      STATUS  current
      DESCRIPTION
      "This attribute indicates a unique  slot  position where
       the card is inserted.
       In the ?004 Unit the entries io6(10)..io16) are not valid."
      ::= {prtInMbeCnfgEntry 2}

prtInMbePrtIdx OBJECT-TYPE
      SYNTAX  INTEGER
     {
          inPrt1    (101)
     }
      MAX-ACCESS  read-only
      STATUS  current
      DESCRIPTION
      "A unique port identifier within the card."
      ::= {prtInMbeCnfgEntry 3}

prtInMbeConnect OBJECT-TYPE
      SYNTAX  INTEGER
       {
  no  (2),
  yes (3)
       }
      MAX-ACCESS  read-write
      STATUS  current
      DESCRIPTION
      "This attribute indicates whether the port should be considered in
       any of the mux  algorithms."
      ::= {prtInMbeCnfgEntry 4}

prtInMbeRate    OBJECT-TYPE
      SYNTAX  INTEGER
	      {
        r1x64eq64Kbps    (1),
        r2x64eq128Kbps   (2),
        r3x64eq192Kbps   (3),
        r4x64eq256Kbps   (4),
        r5x64eq320Kbps   (5),
        r6x64eq384Kbps   (6),
        r7x64eq448Kbps   (7),
        r8x64eq512Kbps   (8),
        r9x64eq576Kbps   (9),
        r10x64eq640Kbps (10),
        r11x64eq704Kbps (11),
        r12x64eq768Kbps (12),
        r13x64eq832Kbps (13),
        r14x64eq896Kbps (14),
        r15x64eq960Kbps (15),
        r16x64eq1024Kbps(16),
        r17x64eq1088Kbps(17),
        r18x64eq1152Kbps(18),
        r19x64eq1216Kbps(19),
        r20x64eq1280Kbps(20),
        r21x64eq1344Kbps(21),
        r22x64eq1408Kbps(22),
        r23x64eq1472Kbps(23),
        r24x64eq1536Kbps(24)
	      }
      MAX-ACCESS  read-write
      STATUS  current
      DESCRIPTION
      "This attribute indicates the port speed."
      ::= {prtInMbeCnfgEntry 5}

prtInMbeLinkTo  OBJECT-TYPE
      SYNTAX  INTEGER
       {
       io1   (5),
       io2   (6),
       io3   (7),
       io4   (8),
       io5   (9),
       io6  (10),
       io7  (11),
       io8  (12),
       io9  (13),
       io10 (14),
       io11 (15),
       io12 (16)
       }
      MAX-ACCESS  read-write
      STATUS  deprecated
      DESCRIPTION
      "It indicates the slot of the main link card to which the
       MBE card is mapped.
       In the ?004 Unit the entries io6(10)..io16) are not valid.
       STATUS  deprecated - this object is replaced by prtGenCnfgLinkToSlot
       and prtGenCnfgLinkToPort."
      ::= {prtInMbeCnfgEntry 6}


--
-- Megaplex?000/?004 TRE port configuration
--

prtExTreCnfgTable OBJECT-TYPE
      SYNTAX SEQUENCE OF PrtExTreCnfgEntry
      MAX-ACCESS not-accessible
      STATUS  current
      DESCRIPTION
       "The write operation into the Table Objects is valid only
        to the TmpCnfg entry."
      ::= {prtTreCnfg 1}

prtExTreCnfgEntry OBJECT-TYPE
      SYNTAX PrtExTreCnfgEntry
      MAX-ACCESS not-accessible
      STATUS current
	DESCRIPTION  "An entry in table."
	INDEX {prtExTreCnfgIdx, prtExTreSltIdx,  prtExTrePrtIdx }
      ::= { prtExTreCnfgTable 1}

PrtExTreCnfgEntry ::=
      SEQUENCE {
        prtExTreCnfgIdx     Integer32,
        prtExTreSltIdx      INTEGER,
        prtExTrePrtIdx      INTEGER,

        prtExTreLan         INTEGER,
        prtExTreLanRate     INTEGER

      }

prtExTreCnfgIdx OBJECT-TYPE
      SYNTAX  Integer32  (1..255)
      MAX-ACCESS  read-only
      STATUS  current
      DESCRIPTION
      "This attribute indicates the Idx of the Cnfg (1..100) being
       accessed.
       Idx 255 relates to the TmpCnfg"
      ::= {prtExTreCnfgEntry 1}
-- In phase I only the values 1 (Cnfg1) and 255 (temp) are valid.

prtExTreSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      MAX-ACCESS  read-only
      STATUS  current
      DESCRIPTION
      "This attribute indicates a unique  slot  position where
       the card is inserted.
       In the ?004 Unit the entries io6(10)..io16) are not valid."
      ::= {prtExTreCnfgEntry 2}

prtExTrePrtIdx OBJECT-TYPE
      SYNTAX  INTEGER
     {
          exPrt1    (1)
     }
      MAX-ACCESS  read-only
      STATUS  current
      DESCRIPTION
      "A unique port identifier within the card."
      ::= {prtExTreCnfgEntry 3}

prtExTreLan OBJECT-TYPE
      SYNTAX  INTEGER
       {
        remote  (1),
        main    (2)
       }
      MAX-ACCESS  read-write
      STATUS  current
      DESCRIPTION
      "This attribute indicates whether the TRE port is operated
       as main or remote bridge.
       Default=remote."
      ::= {prtExTreCnfgEntry 4}

prtExTreLanRate OBJECT-TYPE
      SYNTAX  INTEGER
       {
        r4M  (1),
        r16M (2)
       }
      MAX-ACCESS  read-write
      STATUS  current
      DESCRIPTION
      "This attribute indicates the Rate of the TRE port
       in Mbit/sec.
       Default-r4M."
      ::= {prtExTreCnfgEntry 5}



prtInTreCnfgTable OBJECT-TYPE
      SYNTAX SEQUENCE OF PrtInTreCnfgEntry
      MAX-ACCESS not-accessible
      STATUS  current
      DESCRIPTION
       "The write operation into the Table Objects is valid only
        to the TmpCnfg entry."
      ::= {prtTreCnfg 2}

prtInTreCnfgEntry OBJECT-TYPE
      SYNTAX PrtInTreCnfgEntry
      MAX-ACCESS not-accessible
      STATUS current
	DESCRIPTION  "An entry in table."
	INDEX {prtInTreCnfgIdx, prtInTreSltIdx,  prtInTrePrtIdx }
      ::= { prtInTreCnfgTable 1}

PrtInTreCnfgEntry ::=
      SEQUENCE {
        prtInTreCnfgIdx     Integer32,
        prtInTreSltIdx      INTEGER,
        prtInTrePrtIdx      INTEGER,

        prtInTreConnect     INTEGER,
        prtInTreRate        INTEGER,
        prtInTreLinkTo      INTEGER
      }

prtInTreCnfgIdx OBJECT-TYPE
      SYNTAX  Integer32  (1..255)
      MAX-ACCESS  read-only
      STATUS  current
      DESCRIPTION
      "This attribute indicates the Idx of the Cnfg (1..100) being
       accessed.
       Idx 255 relates to the TmpCnfg"
      ::= {prtInTreCnfgEntry 1}
-- In phase I only the values 1 (Cnfg1) and 255 (temp) are valid.

prtInTreSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      MAX-ACCESS  read-only
      STATUS  current
      DESCRIPTION
      "This attribute indicates a unique  slot  position where
       the card is inserted.
       In the ?004 Unit the entries io6(10)..io16) are not valid."
      ::= {prtInTreCnfgEntry 2}

prtInTrePrtIdx OBJECT-TYPE
      SYNTAX  INTEGER
     {
          inPrt1    (101)
     }
      MAX-ACCESS  read-only
      STATUS  current
      DESCRIPTION
      "A unique port identifier within the card."
      ::= {prtInTreCnfgEntry 3}

prtInTreConnect OBJECT-TYPE
      SYNTAX  INTEGER
       {
  no  (2),
  yes (3)
       }
      MAX-ACCESS  read-write
      STATUS  current
      DESCRIPTION
      "This attribute indicates whether the port should be considered
       in any of the mux  algorithms."
      ::= {prtInTreCnfgEntry 4}

prtInTreRate    OBJECT-TYPE
      SYNTAX  INTEGER
       {
        r1x56eq56Kbps    (1),
        r1x64eq64Kbps    (2),
        r2x56eq112Kbps   (3),
        r2x64eq128Kbps   (4),
        r3x56eq168Kbps   (5),
        r3x64eq192Kbps   (6),
        r4x56eq224Kbps   (7),
        r4x64eq256Kbps   (8),
        r5x56eq280Kbps   (9),
        r5x64eq320Kbps   (10),
        r6x56eq336Kbps   (11),
        r6x64eq384Kbps   (12),
        r7x56eq392Kbps   (13),
        r7x64eq448Kbps   (14),
        r8x56eq448Kbps   (15),
        r8x64eq512Kbps   (16),
        r9x56eq504Kbps   (17)
       }
      MAX-ACCESS  read-write
      STATUS  current
      DESCRIPTION
      "This attribute indicates the port speed."
      ::= {prtInTreCnfgEntry 5}

prtInTreLinkTo  OBJECT-TYPE
      SYNTAX  INTEGER
       {
       io1   (5),
       io2   (6),
       io3   (7),
       io4   (8),
       io5   (9),
       io6  (10),
       io7  (11),
       io8  (12),
       io9  (13),
       io10 (14),
       io11 (15),
       io12 (16)
       }
      MAX-ACCESS  read-write
      STATUS  deprecated
      DESCRIPTION
      "It indicates the slot of the main link card to which the
       MBE card is mapped.
       In the ?004 Unit the entries io6(10)..io16) are not valid.
       STATUS  deprecated - this object is replaced by prtGenCnfgLinkToSlot
       and prtGenCnfgLinkToPort."
      ::= {prtInTreCnfgEntry 6}


-- Packet VC cards. 
-- This table is used for compressed voice cards with 4/8 ports.
--

prtExPVc4CnfgTable OBJECT-TYPE
      SYNTAX SEQUENCE OF PrtExPVc4CnfgEntry
      MAX-ACCESS not-accessible
      STATUS  current
      DESCRIPTION
       "The write operation into the Table Objects is valid only
        to the TmpCnfg entry."
      ::= { prtPVc4Cnfg 1}

prtExPVc4CnfgEntry OBJECT-TYPE
      SYNTAX PrtExPVc4CnfgEntry
      MAX-ACCESS not-accessible
      STATUS current
	DESCRIPTION  "An entry in table."
	INDEX {prtExPVc4CnfgIdx, prtExPVc4SltIdx, prtExPVc4PrtIdx }
      ::= { prtExPVc4CnfgTable 1}

PrtExPVc4CnfgEntry ::=
      SEQUENCE {
        prtExPVc4CnfgIdx      Integer32,
        prtExPVc4SltIdx       INTEGER,
        prtExPVc4PrtIdx       INTEGER,

		prtExPVc4PrtType      INTEGER,
        prtExPVc4Connect      INTEGER,
		prtExPVc4IfType       INTEGER,
        prtExPVc4TxGain       Integer32,
        prtExPVc4RxGain       Integer32,
		prtExPVc4MaxRate      INTEGER,
        prtExPVc4Tc           INTEGER,
        prtExPVc4Oos          INTEGER,
		prtExPVc4EchoCanceler INTEGER,
		prtExPVc4VarDelay     Integer32,
		prtExPVc4CongLevel    Integer32,
		prtExPVc4Wire         INTEGER,
		prtExPVc4ExtensionType		INTEGER,
		prtExPVc4ExtensionNumber	DisplayString,
		prtExPVc4OutPulsing 		INTEGER,
		prtExPVc4HuntGroupMb		INTEGER,
		prtExPVc4HuntGroupIdx		Integer32,
		prtExPVc4AutoFaxMode		INTEGER,
		prtExPVc4FaxRate            INTEGER,
		prtExPVc4SeizeAck           INTEGER,
		prtExPVc4SignalingProtocol  INTEGER,
		prtExPVc4DelayStart         Integer32,
		prtExPVc4WinkMinDuration    Integer32,
		prtExPVc4WinkMaxDuration    Integer32,
        prtExPVc4GenerateTone       INTEGER,
		prtExPVc4CodingLaw          INTEGER,
        prtExPVc4GenerateRingBack   INTEGER,
		prtExPVc4ChannelId          Integer32,
		prtExPVc4PortConnection     INTEGER,
		prtExPVc4CoderAndRate       INTEGER,
		prtExPVc4DestinationNum     DisplayString,
		prtExPVc4DtmfRelay          INTEGER,
		prtExPVc4DiscOnSilence      Integer32,
		prtExPVc4DynamicJitter      INTEGER,
		prtExPVc4EandMType          INTEGER
      }

prtExPVc4CnfgIdx OBJECT-TYPE
      SYNTAX  Integer32  (1..255)
      MAX-ACCESS  read-only
      STATUS  current
      DESCRIPTION
      "This attribute indicates the Idx of the Cnfg (1..100) being
       accessed.
       Idx  255 relates to the TmpCnfg"
      ::= {prtExPVc4CnfgEntry 1}
-- In phase I only the values 1 (Cnfg1) and 255 (temp) are valid.

prtExPVc4SltIdx OBJECT-TYPE
      SYNTAX  INTEGER
 {
       io1   (5),
       io2   (6),
       io3   (7),
       io4   (8),
       io5   (9),
       io6  (10),
       io7  (11),
       io8  (12),
       io9  (13),
       io10 (14),
       io11 (15),
       io12 (16),
    notApplicable (255)
 }
      MAX-ACCESS  read-only
      STATUS  current
      DESCRIPTION
      "This attribute indicates a unique  slot  position where
       the card is inserted."
      ::= {prtExPVc4CnfgEntry 2}

prtExPVc4PrtIdx OBJECT-TYPE
      SYNTAX  INTEGER
 {
       exPrt1    (1) ,
       exPrt2    (2) ,
       exPrt3    (3) ,
       exPrt4    (4),
       inPrt1(101),
       inPrt2(102),
       inPrt3(103),
       inPrt4(104),
	   inPrt5(105),
	   inPrt6(106),
	   inPrt7(107),
	   inPrt8(108)
 }
      MAX-ACCESS  read-only
      STATUS  current
      DESCRIPTION
      "This object indicates the port number in the selected card
       (slot)."
      ::= {prtExPVc4CnfgEntry 3}

prtExPVc4PrtType OBJECT-TYPE
      SYNTAX  INTEGER
	{
	      eAndM  (1),
	      fxo    (2),
	      fxs    (3),
	      internal(4),
	      s0      (5),
		  u       (6),
		  sQsig	  (7),
		  uQsig   (8)
	}
      MAX-ACCESS  read-only
      STATUS  current
      DESCRIPTION
      "This object indicates the type of the selected port.
	   In Mx 30/300 phase 4: s0 & u are for Voice over ISDN.
	   In MX 30/300 phase 5: sQsig & uQsig are used for Voice over ISDN with Qsig option.
	   	   
	   In MX MVC4 voice cards, each pair of ports 1-2, 3-4 may have a different type:
       E&M, FXO, FXS.
	   In MVC4 compressed voice cards ports 1..4 have the same interface for all ports.
       In MVC8 compressed voice cards each group of ports 1..4, 5..8 may have
       a different type: E&M, FXO, FXS."
      ::= {prtExPVc4CnfgEntry 4}

prtExPVc4Connect OBJECT-TYPE
      SYNTAX  INTEGER
              {
                no  (2),
                yes (3)
              }
      MAX-ACCESS  read-write
      STATUS  current
      DESCRIPTION
      "This attribute indicates whether the  port  should be
       considered in any of the mux algorithms."
      ::= {prtExPVc4CnfgEntry 5}

prtExPVc4IfType OBJECT-TYPE
      SYNTAX  INTEGER
              {
                unknown     (1),
                eAndM4wires (2),
   			    eAndM2wires (3),
                fxoGnd      (4),
                fxoLoop     (5),
                fxsGnd      (6),
				fxsLoop     (7),
				e1Framer    (8),
				e1Slave     (9),
				t1Framer   (10),
				t1Slave    (11)
              }
      MAX-ACCESS  read-only
      STATUS  current
      DESCRIPTION
      "This attribute indicates the interface type of the  port.
       eAndM4wires and eAndM2wires - are valid only for E&M
                                     port type
	   eAndM4wires - means 2/4 wires
       fxoGnd and fxoLoop - are valid only for FXO port type
       fxsGnd and fxsLoop - are valid only for FXS port type
       e1Framer, e1Slave, t1Framer, t1Slave - are applicable for the mvc4Pbx
       cards only."
      ::= {prtExPVc4CnfgEntry 6}



prtExPVc4TxGain OBJECT-TYPE
      SYNTAX  Integer32
      MAX-ACCESS  read-write
      STATUS  current
      DESCRIPTION
      "Transmission gain in dBm."
      ::= {prtExPVc4CnfgEntry 7}

prtExPVc4RxGain OBJECT-TYPE
      SYNTAX  Integer32
      MAX-ACCESS  read-write
      STATUS  current
      DESCRIPTION
      "Reception gain in dBm."
      ::= {prtExPVc4CnfgEntry 8}

prtExPVc4MaxRate OBJECT-TYPE
      SYNTAX  INTEGER
       {
         notConnected  (1),
         r4800bps      (2),
         r7200bps      (3),
         r9600bps      (4),
		 notApplicatble (255)
       }
      MAX-ACCESS  read-write
      STATUS  current
      DESCRIPTION
      "Voice rate."
      ::= {prtExPVc4CnfgEntry 9}

prtExPVc4Tc OBJECT-TYPE
      SYNTAX  INTEGER
       {
          t1sec    (1),
          t2sec    (2),
    t3sec    (3),
    t4sec    (4)
       }
      MAX-ACCESS  read-write
      STATUS  current
      DESCRIPTION
      "Time interval for CIR control, in seconds. The value will
       be the same for all cards' ports."
      ::= {prtExPVc4CnfgEntry 10}

prtExPVc4Oos OBJECT-TYPE
      SYNTAX  INTEGER
       {
          notSupported   (2),
          forcedIdle     (3),
          forcedBusy     (4),
          busyIdle       (5),
          idleBusy       (6)
       }
      MAX-ACCESS  read-write
      STATUS  current
      DESCRIPTION
      "Handling type, when connection is lost."
      ::= {prtExPVc4CnfgEntry 11}

prtExPVc4EchoCanceler OBJECT-TYPE
      SYNTAX  INTEGER
       {
          off    (2),
          on     (3)
       }
      MAX-ACCESS  read-write
      STATUS  current
      DESCRIPTION
      "Echo canceler activation."
      ::= {prtExPVc4CnfgEntry 12}

prtExPVc4VarDelay OBJECT-TYPE
      SYNTAX  Integer32  (0..300)
      MAX-ACCESS  read-write
      STATUS  current
      DESCRIPTION
      "Maximum variant delay of the FR network, in msec."
      ::= {prtExPVc4CnfgEntry 13}

prtExPVc4CongLevel OBJECT-TYPE
      SYNTAX  Integer32 (0..70)
      MAX-ACCESS  read-write
      STATUS  current
      DESCRIPTION
      "This object indicates the level of delayed data in
       precents of total available dynamic memory,
       for which the port will start to operate as congested.
       The resolution of the parameter is 5%."
      ::= {prtExPVc4CnfgEntry 14}

prtExPVc4Wire OBJECT-TYPE
      SYNTAX  INTEGER
       {
          w2wire   (1),
          w4wire   (2),
    notApplicable (255)
       }
      MAX-ACCESS  read-write
      STATUS  current
      DESCRIPTION
      "This object indicates the wiring of the E&M port.
       It is applicable only for E&M card type."
      ::= {prtExPVc4CnfgEntry 15}

prtExPVc4ExtensionType OBJECT-TYPE
       SYNTAX  INTEGER
           { notApplicable(1),
             forceConnect(2),
             voiceSwitching(3),
             transparent(4),
             transparentPlus(5),
             ipForceConnect(6),
             permanentDial (7),
             autoAccept (8) }
       MAX-ACCESS  read-write
       STATUS  current
       DESCRIPTION
      "This object indicates the type of extension relevant for this port.

       ipForceConnect (6) is used for automatic connection or automatic
       dialing when the phone is off hook (hot line).
       permanentDial (7) means that the call is established upon power up. 
	   The hook may be on or off.
	   Permanent Dialing can be used when there is no signaling. 
	   autoAccept (8) means that the called party in the Permanent Dialing
	   will accept the call from the remote side automatically
	   upon on or off hook."
      ::= {prtExPVc4CnfgEntry 16}

prtExPVc4ExtensionNumber OBJECT-TYPE
       SYNTAX  DisplayString (SIZE(2))
     MAX-ACCESS  read-write
       STATUS  current
       DESCRIPTION
      "This is the extension number of this port.
      This field is relevant only when the extension
     type is voice switching and is read only if the
     port is member of a hunt group."
      ::= {prtExPVc4CnfgEntry 17}

prtExPVc4OutPulsing OBJECT-TYPE
       SYNTAX  INTEGER { notApplicable(1), no(2), yes(3) }
     MAX-ACCESS  read-write
       STATUS  current
       DESCRIPTION
      "This field indicates whether to outpulse the received
     digits. It is notApplicable(1) when the extension type
     is forceConnect(2)."
      ::= {prtExPVc4CnfgEntry 18}

prtExPVc4HuntGroupMb OBJECT-TYPE
     SYNTAX  INTEGER { notApplicable(1), no(2), yes(3) }
     MAX-ACCESS  read-write
       STATUS  current
       DESCRIPTION
      "This object indicates if this port belongs to
      an hunt group."
      ::= {prtExPVc4CnfgEntry 19}

prtExPVc4HuntGroupIdx	OBJECT-TYPE
	    SYNTAX  Integer32(0..10)
    	MAX-ACCESS  read-write
      	STATUS  current
      	DESCRIPTION
     	"If it belongs to an hunt group, this fields
	     indicates the index of the relevant hunt group.
	     0 = notApplicable "
      ::= {prtExPVc4CnfgEntry 20}

prtExPVc4AutoFaxMode	OBJECT-TYPE
    	SYNTAX  INTEGER { notApplicable(1), no(2), yes(3) }
    	MAX-ACCESS  read-write
      	STATUS  current
      	DESCRIPTION
     	"This object indicates if the system will switch automatically to
     	 FAX mode when detecting FAX activity.
     	 Default=Yes."
      ::= {prtExPVc4CnfgEntry 21}

prtExPVc4FaxRate OBJECT-TYPE
      SYNTAX  INTEGER
	      {
          notConnected  (1),
          r4800bps      (2),
		  r7200bps      (3),
		  r9600bps      (4),
		  r12000bps     (5),
		  r14400bps     (6),
          r2400bps      (7)
	      }
      MAX-ACCESS  read-write
      STATUS  current
      DESCRIPTION
      "FAX initial rate.
       Default=9600 bps."
      ::= {prtExPVc4CnfgEntry 22}

prtExPVc4SeizeAck OBJECT-TYPE
      SYNTAX INTEGER
      {
	  no   (2),
      yes  (3)
      }
      MAX-ACCESS  read-write
      STATUS  current
      DESCRIPTION
      "This parameter shows whether the device will acknowledge
       a seize signal (On/Off Hook).
       When the value is set to yes(3) & the device receives an on/off hook signal
       it will transmit back an on/off hook signal.
	   When the value is set to no(2) & the device receives an on/off hook signal
       it will NOT transmit back an on/off hook signal.
       
       Example:
       If Seize Ack Parameter = YES, when the MVC.4 receives a seize signal (Off Hook) 
       from the PBX it will send an Off Hook to the PBX.

       The Seize Parameter is relevant for all the following cards:
       MVC-4
       MVC-4/E1-Framer
       MVC-4/T1-DSU-Framer
       MVC-4/T1-CSU-Framer
       MVC-4/E1-SLAVE
       MVC-4/T1-SLAVE

       Default values:
       Analog FXS - No (value can't be changed).
       Analog FXO - Yes (value can't be changed).
       Analog E&M - No (values NO/YES).
       Digital E1/T1 Framer & Slave - No."
      ::= {prtExPVc4CnfgEntry 23}


prtExPVc4SignalingProtocol OBJECT-TYPE
      SYNTAX INTEGER
      {
	  delayStart      (2),
      immediateStart  (3),
	  winkStart       (4)
      }
      MAX-ACCESS  read-write
      STATUS  current
      DESCRIPTION
      "The signaling protocol that will be used between the PABX & the voice port.

	   Delay Start Protocol: the line is seized by sending an Off hook signal
	   and after a delay, if the called party is available (On hook)   
	   DTMF (Dual Tone Multi Frequency) digits are sent towards the called party.

       Immediate Start Protocol: the line is seized by sending an Off Hook signal
       and immediately DTMF digits are sent towards the called party.
       
       Wink start protocol: the line is seized by sending an Off Hook signal
       and then the called party sends a short Off Hook wink signal.
       Now the calling party starts sending DTMF digits."
      ::= {prtExPVc4CnfgEntry 24} 

prtExPVc4DelayStart OBJECT-TYPE
      SYNTAX Integer32
      MAX-ACCESS  read-write
      STATUS  current
      DESCRIPTION
      "This parameter is used only for Delay Protocol.
	   This is the time that the calling party will wait after sending an Off hook
	   signal and before sending DTMF digits to the called party.
       The delay values are 100..5000 msec in intervals of 100 msec."
      ::= {prtExPVc4CnfgEntry 25}

prtExPVc4WinkMinDuration OBJECT-TYPE
      SYNTAX Integer32
      MAX-ACCESS  read-write
      STATUS  current
      DESCRIPTION
      "This parameter is used only for Wink Protocol.
	   Min Duration of the Wink Signal (off hook duration from the called party).
       Legal values: 40..400 msec in intervals of 10 msec."
      ::= {prtExPVc4CnfgEntry 26}

prtExPVc4WinkMaxDuration OBJECT-TYPE
      SYNTAX Integer32
      MAX-ACCESS  read-write
      STATUS  current
      DESCRIPTION
      "This parameter is used only for Wink Protocol.
	   Max Duration of the Wink Signal (off hook duration from the called party).
       Legal values: 40..400 msec in intervals of 10 msec."
      ::= {prtExPVc4CnfgEntry 27}

prtExPVc4GenerateTone OBJECT-TYPE
      SYNTAX  INTEGER
	      {
          notApplicable  (1),
          no       (2),
		  yes      (3)
		  }
      MAX-ACCESS  read-write
      STATUS  current
      DESCRIPTION
      "This parameter indicates whether the device (MX or MPH) should generate
       dial tones for the channel.
       If the value is yes (3), it generates dial tones.
       If the value is no  (2), the connected equipment will generate dial tones.
       For example for some ISDN sets the dial tone is generated by the
       phone itself while for others sets it is generated by the MX."
      ::= {prtExPVc4CnfgEntry 28}

prtExPVc4CodingLaw OBJECT-TYPE
      SYNTAX  INTEGER
       {
          aLAW    (1),
          uLAW    (2)
       }
      MAX-ACCESS  read-write
      STATUS  current
      DESCRIPTION
      "This attribute indicates the Method/Law for decoding/encoding the voice
       information.
       aLaw(1) is the standard Law for E1 links.
       uLaw(2) is the standard Law for T1 links.

       This object is equal for all the ports in the specific module because
       of HW limitations"
      ::= {prtExPVc4CnfgEntry 29}

prtExPVc4GenerateRingBack OBJECT-TYPE
      SYNTAX  INTEGER
       {
          notApplicable  (1),
          no    (2),
          yes   (3)
       }
      MAX-ACCESS  read-write
      STATUS  current
      DESCRIPTION
      "Determines whether the Ring Back tone is generated locally or from the
       remote end.
   	   The default is - NO (Meaning coming from the remote end).
	   Yes means that the Ring Back Tone is generated locally.
       Applicable only for Force Connect."
      ::= {prtExPVc4CnfgEntry 30}

prtExPVc4ChannelId OBJECT-TYPE
      SYNTAX  Integer32 (0..256)
      MAX-ACCESS  read-write
      STATUS  current
      DESCRIPTION
      "Channel Identifier.
       According to FRF11 each voice port that works as force connect should add a
       CH Id after the DLCI in the frame header.

       Default : 1 

       Applicable only for Force Connect.
       Not Applicable value will be 0."
      ::= {prtExPVc4CnfgEntry 31}

prtExPVc4PortConnection OBJECT-TYPE
      SYNTAX  INTEGER 
       {
	      notApplicable (1),
          line    (2),
          trunk   (3)
       }
      MAX-ACCESS  read-write
      STATUS  current
      DESCRIPTION
      "Port connection determines whether the port is connected to a PABX (Trunk) or to
       Telephone set (Line) .

       It determines whether to send certain messages to the port or not.
       If the type is LINE then the port generates a
       ring back tone , if TRUNK it doesn't (The PBX does it)."
      ::= {prtExPVc4CnfgEntry 32}


prtExPVc4CoderAndRate  OBJECT-TYPE
      SYNTAX  INTEGER 
       {
       notApplicable   (1),
       g7231r6300BPS   (2),		                    
       g7231r5300BPS   (3),                
       g729A8KBPS      (4),               
       g711aLAW        (5),                    
       g711uLAW        (6),                     
       g726r16KBPS     (7),                   
       g726r24KBPS     (8),                   
       g726r32KBPS     (9),                   
       g726r40KBPS     (10),                   
       g727r16KBPS     (11),                   
       g727r24r16KBPS  (12),                
       g727r24KBPS     (13),                   
       g727r16r32KBPS  (14),                
       g727r32r24KBPS  (15),                
       g727r32KBPS     (16),                                
       g727r40r16KBPS  (17),                
       g727r40r24KBPS  (18),                
       g727r40r32KBPS  (19),                
       transparent     (20),                    
       netcoder6400BPS (21),              
       netcoder7200BPS (22),              
       netcoder8KBPS   (23),                
       netcoder8800BPS (24),              
       netcoder9600BPS (25)               
       }
      MAX-ACCESS  read-write
      STATUS  current
      DESCRIPTION
      "Coder and Rate for the Voice Compression.
       Relevant for MVC-8 card only."
      ::= {prtExPVc4CnfgEntry 33}


prtExPVc4DestinationNum  OBJECT-TYPE
      SYNTAX  DisplayString 
      MAX-ACCESS  read-write
      STATUS  current
      DESCRIPTION
      "The destination phone number: 0 to 22 digits.
       Applicable for Auto Dial - ipForceConnect(6), Permanent Dial and 
       Auto Accept Extension Types.      

       Default: Null String"
      ::= {prtExPVc4CnfgEntry 34}
		
prtExPVc4DtmfRelay  OBJECT-TYPE
      SYNTAX  INTEGER 
             {
               disable (2),
               enable  (3)
             }
      MAX-ACCESS  read-write
      STATUS  current
      DESCRIPTION
      "When DTMF RELAY is disabled, the DTMF digits (dialed by the user)
       are transmitted as compressed voice and in the remote unit are decompressed.
 
       When DTMF RELAY is enabled, the DTMF digits are detected at the near side and not
       transmitted as voice. Instead, only an indication of what digits were
       dialed are transmitted and in the far end the tone is regenerated."
      ::= {prtExPVc4CnfgEntry 35}

prtExPVc4DiscOnSilence  OBJECT-TYPE
      SYNTAX  Integer32 
      MAX-ACCESS  read-write
      STATUS  current
      DESCRIPTION
      "No. of silenced seconds after which the call will be disconected.
       A value of 0 means that there will be no disconnect when there is silence.
       Possible values: 0 - 900 sec."
      ::= {prtExPVc4CnfgEntry 36}

prtExPVc4DynamicJitter  OBJECT-TYPE
      SYNTAX  INTEGER 
             {
               disable (2),
               enable  (3)
             }
      MAX-ACCESS  read-write
      STATUS  current
      DESCRIPTION
      "The MVC8 uses two mechanisms to overcome the network delay.
       The first one is a static jitter buffer which holds a constant buffer of up
       to 300 Msec and can be controled by the JITTER parameter (prtExPVc4VarDelay).
       The second one is the dynamic jitter which calculates, in real time,
       the network delay and handles a jitter buffer dynamically.
       The dynamic mechanism that is implemented in MVC8, was intended to overcome
       network delay yet when the network bursts, the MVC8 dynamic mechanism is
       not able to overcome the delay.
       Therefore it is better not to use the dynamic jitter
       (DISABLE - should be the default) where bursts may occur often."
      ::= {prtExPVc4CnfgEntry 37}

prtExPVc4EandMType OBJECT-TYPE
       SYNTAX INTEGER
	   {
       notApplicable (1),
	   type1 (2),
       type2 (3),
       type3 (4),
       ssdc5 (5) 
       }
      MAX-ACCESS  read-write
      STATUS  current
      DESCRIPTION
      "This is the signaling type on the E&M analog side.
       The analog signaling includes voltage, no. of pins and other parameters."
       ::= {prtExPVc4CnfgEntry 38}

--
-- Packet VC4 card
-- External port Dlci table
--
prtExPVc4DlciTable  OBJECT-TYPE
     SYNTAX SEQUENCE OF PrtExPVc4DlciEntry
     MAX-ACCESS not-accessible
     STATUS  current
     DESCRIPTION
      "The write operation into the Table Objects is valid only
       at the TmpCnfg entry."
     ::= {prtPVc4Cnfg 2}

prtExPVc4DlciEntry OBJECT-TYPE
      SYNTAX PrtExPVc4DlciEntry
      MAX-ACCESS not-accessible
      STATUS current
	DESCRIPTION  "An entry in table."
	INDEX {prtExPVc4DlciCnfgIdx, prtExPVc4DlciSltIdx, prtExPVc4DlciPrtIdx}
      ::= { prtExPVc4DlciTable 1}

PrtExPVc4DlciEntry ::=
      SEQUENCE {
      prtExPVc4DlciCnfgIdx        Integer32,
      prtExPVc4DlciSltIdx         INTEGER,
      prtExPVc4DlciPrtIdx         INTEGER,

      prtExPVc4DlciValid          INTEGER,
      prtExPVc4DlciIConSlt        INTEGER,
      prtExPVc4DlciIConPrt        INTEGER,
      prtExPVc4DlciIConDlci       Integer32,

      prtExPVc4DlciTxBc           INTEGER,
      prtExPVc4DlciTxBe           INTEGER,
      prtExPVc4DlciRxBc           INTEGER,
      prtExPVc4DlciRxBe           INTEGER,

      prtExPVc4DlciPriority       Integer32,

      prtExPVc4DlciStatus         INTEGER
      }


prtExPVc4DlciCnfgIdx OBJECT-TYPE
      SYNTAX  Integer32 (1..255)
      MAX-ACCESS  read-only
      STATUS  current
      DESCRIPTION
      "This attribute indicates the Idx of the Cnfg (1..100) being
       accessed.
       Idx 255 relates to the TmpCnfg. "
      ::= { prtExPVc4DlciEntry 1}
-- In phase I only the values 1 (Cnfg1) and 255 (temp) are valid.

prtExPVc4DlciSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16),
    notApplicable (255)
     }
      MAX-ACCESS  read-only
      STATUS  current
      DESCRIPTION
      "This attribute indicates a unique  slot  position where
       the card is inserted.
       In the ?004 Unit the entries io6(10)..io16) are not valid"
      ::= { prtExPVc4DlciEntry 2}

prtExPVc4DlciPrtIdx OBJECT-TYPE
      SYNTAX  INTEGER
 {
          exPrt1  (1) ,
          exPrt2  (2) ,
          exPrt3  (3) ,
    exPrt4  (4)
       }
      MAX-ACCESS  read-only
      STATUS  current
      DESCRIPTION
      "This attribute indicates a unique internal port number.
       VC4 cards have four external ports."
      ::= { prtExPVc4DlciEntry 3}


prtExPVc4DlciValid OBJECT-TYPE
      SYNTAX  INTEGER
     {
     no  (2),
     yes (3)
     }
      MAX-ACCESS  read-write
      STATUS  current
      DESCRIPTION
      "This attribute indicates whether the attributes in this
       entry are valid or not. The user can add/delete pvc (dlci
       to dlci connection) by modifing this object"
      ::= { prtExPVc4DlciEntry 4}

prtExPVc4DlciIConSlt OBJECT-TYPE
      SYNTAX  INTEGER
 {
          noConnect (2),
       io1   (5),
       io2   (6),
       io3   (7),
       io4   (8),
       io5   (9),
       io6  (10),
       io7  (11),
       io8  (12),
       io9  (13),
       io10 (14),
       io11 (15),
       io12 (16),
    notApplicable (255)
       }
      MAX-ACCESS  read-write
      STATUS  current
      DESCRIPTION
      "This attribute indicates a unique slot position In the Mux
       (Agent) where the dlci is routed to.
       In the ?004 Unit the entries io6(10)..io16) are not valid"
      ::= { prtExPVc4DlciEntry 5}

prtExPVc4DlciIConPrt OBJECT-TYPE
      SYNTAX  INTEGER
      {
       exPrt1    (1) ,
       exPrt2    (2) ,
       exPrt3    (3) ,
       exPrt4    (4) ,
       exPrt5    (5) ,
       exPrt6    (6) ,
       exPrt7    (7) ,
       exPrt8    (8) ,
       exPrt9    (9) ,
       exPrt10  (10) ,
          noConnect (100),
       inPrt1  (101) ,
       inPrt2  (102) ,
       inPrt3  (103) ,
       inPrt4  (104) ,
       inPrt5  (105) ,
       inPrt6  (106) ,
       inPrt7  (107) ,
       inPrt8  (108) ,
       inPrt9  (109) ,
       inPrt10 (110) ,
    inPrt11 (111) ,
    inPrt12 (112)
       }
      MAX-ACCESS  read-write
      STATUS  current
      DESCRIPTION
      "This attribute indicates a unique port id which the dlci is
       routed to."
      ::= { prtExPVc4DlciEntry 6}


prtExPVc4DlciIConDlci OBJECT-TYPE
      SYNTAX  Integer32    (1..991)
      MAX-ACCESS  read-write
      STATUS  current
      DESCRIPTION
      "This attribute indicates a unique internal connection dlci
       number,  the dlci is routed to."
      ::= { prtExPVc4DlciEntry 7}

prtExPVc4DlciTxBc OBJECT-TYPE
      SYNTAX  INTEGER
        {
         full       (1),
         zero       (2),
         txBc9600bps    (3),
        txBc14400bps    (4),
        txBc19200bps    (5),
        txBc28800bps    (6),
        txBc32000bps    (7),
        txBc38400bps    (8),
        txBc48000bps    (9),
        txBc56000bps   (10),
        txBc57600bps   (11),
          txBc64Kbps   (12),
         txBc128Kbps   (13),
         txBc192Kbps   (14),
         txBc256Kbps   (15),
         txBc320Kbps   (16),
         txBc384Kbps   (17),
         txBc448Kbps   (18),
         txBc512Kbps   (19),
         txBc768Kbps   (20),
        txBc1024Kbps   (21),
--
--KM30 ; KM300 additional rates
--
        txBc16000bps   (25),
   txBc112Kbps   (26)
        }
      MAX-ACCESS  read-write
      STATUS  current
      DESCRIPTION
      "This attribute indicates a unique Tx committed bandwidth on
       the user transmit line (or at the port receive line)."
      ::= { prtExPVc4DlciEntry 8}


prtExPVc4DlciTxBe OBJECT-TYPE
      SYNTAX  INTEGER
        {
         full       (1),
         zero       (2),
         txBe9600bps    (3),
        txBe14400bps    (4),
        txBe19200bps    (5),
        txBe28800bps    (6),
        txBe32000bps    (7),
        txBe38400bps    (8),
        txBe48000bps    (9),
        txBe56000bps   (10),
        txBe57600bps   (11),
          txBe64Kbps   (12),
         txBe128Kbps   (13),
         txBe192Kbps   (14),
         txBe256Kbps   (15),
         txBe320Kbps   (16),
         txBe384Kbps   (17),
         txBe448Kbps   (18),
         txBe512Kbps   (19),
         txBe768Kbps   (20),
        txBe1024Kbps   (21),
--
--KM30 ; KM300 additional rates
--
        txBc16000bps   (25),
   txBc112Kbps   (26)
        }
      MAX-ACCESS  read-write
      STATUS  current
      DESCRIPTION
      "This attribute indicates a unique Tx excess bandwidth on the
      user transmit line (or at the port receive line)."
      ::= { prtExPVc4DlciEntry 9}


prtExPVc4DlciRxBc OBJECT-TYPE
      SYNTAX  INTEGER
        {
         full       (1),
         zero       (2),
         rxBc9600bps    (3),
        rxBc14400bps    (4),
        rxBc19200bps    (5),
        rxBc28800bps    (6),
        rxBc32000bps    (7),
        rxBc38400bps    (8),
        rxBc48000bps    (9),
        rxBc56000bps   (10),
        rxBc57600bps   (11),
        rxBc64Kbps   (12),
         rxBc128Kbps   (13),
         rxBc192Kbps   (14),
         rxBc256Kbps   (15),
         rxBc320Kbps   (16),
         rxBc384Kbps   (17),
         rxBc448Kbps   (18),
         rxBc512Kbps   (19),
         rxBc768Kbps   (20),
        rxBc1024Kbps   (21),
--
--KM30 ; KM300 additional rates
--
        rxBc16000bps   (25),
   rxBc112Kbps   (26)
        }
      MAX-ACCESS  read-write
      STATUS  current
      DESCRIPTION
      "This attribute indicates a unique Rx committed bandwidth on the
      user receive line (or at the port transmit line)."
      ::= { prtExPVc4DlciEntry 10}


prtExPVc4DlciRxBe OBJECT-TYPE
      SYNTAX  INTEGER
        {
         full       (1),
         zero       (2),
         rxBe9600bps    (3),
        rxBe14400bps    (4),
        rxBe19200bps    (5),
        rxBe28800bps    (6),
        rxBe32000bps    (7),
        rxBe38400bps    (8),
        rxBe48000bps    (9),
        rxBe56000bps   (10),
        rxBe57600bps   (11),
          rxBe64Kbps   (12),
         rxBe128Kbps   (13),
         rxBe192Kbps   (14),
         rxBe256Kbps   (15),
         rxBe320Kbps   (16),
         rxBe384Kbps   (17),
         rxBe448Kbps   (18),
         rxBe512Kbps   (19),
         rxBe768Kbps   (20),
        rxBe1024Kbps   (21),
--
--KM30 ; KM300 additional rates
--
        rxBc16000bps   (25),
   rxBc112Kbps   (26)
        }
      MAX-ACCESS  read-write
      STATUS  current
      DESCRIPTION
      "This attribute indicates a unique Rx excess bandwidth on the
      user receive line (or at the port transmit line)."
      ::= { prtExPVc4DlciEntry 11}


prtExPVc4DlciPriority OBJECT-TYPE
      SYNTAX  Integer32  (6..8)
      MAX-ACCESS  read-write
      STATUS  current
      DESCRIPTION
      "This attribute indicates a unique priority of the pvc.
       6 is the lowest priority and 8 is the highest priority."
      ::= { prtExPVc4DlciEntry 12}



prtExPVc4DlciStatus OBJECT-TYPE
      SYNTAX  INTEGER
 {
          disconnected (1),
          connected    (2)
       }
      MAX-ACCESS  read-only
      STATUS  current
      DESCRIPTION
      "This attribute indicates the status of the pvc. The status is
       disconnected(1) when one of the sides is programmed as not
       connected"
      ::= { prtExPVc4DlciEntry 13}


--
-- Megaplex ?000/?004 LS-6 TDM I/O family card include:
-- Ls6, Ls6V1/E, Ls6V1/O, Ls6V1/S, Ls6V2/E, Ls6V2/O, Ls6V2/S,
-- Ls6Vf/E, Ls6Vf/O, Ls6Vf/S
--
--prtExLs6CnfgTable OBJECT IDENTIFIER ::=  {prtLs6Cnfg 1}
--prtExLs6VCnfgTable OBJECT IDENTIFIER ::= {prtLs6Cnfg 2}
--prtInLs6CnfgTable OBJECT IDENTIFIER ::=  {prtLs6Cnfg 3}

--prtExLs6CnfgTable defines the parameters of the
-- LS-6 cards family external Data ports (1-6) ; LS-12 (1-12)

prtExLs6CnfgTable OBJECT-TYPE
      SYNTAX SEQUENCE OF PrtExLs6CnfgEntry
      MAX-ACCESS not-accessible
      STATUS  current
      DESCRIPTION
       "The write operation into the Table Objects is valid only
        to the TmpCnfg entry."
      ::= {prtLs6Cnfg 1}

prtExLs6CnfgEntry OBJECT-TYPE
      SYNTAX PrtExLs6CnfgEntry
      MAX-ACCESS not-accessible
      STATUS current
	DESCRIPTION  "An entry in table."
	INDEX {prtExLs6CnfgIdx, prtExLs6SltIdx, prtExLs6PrtIdx }
      ::= {prtExLs6CnfgTable  1}

PrtExLs6CnfgEntry ::=
      SEQUENCE {
        prtExLs6CnfgIdx    Integer32,
        prtExLs6SltIdx     INTEGER,
        prtExLs6PrtIdx     INTEGER,
        prtExLs6Connect    INTEGER,
        prtExLs6Protocol   INTEGER,
        prtExLs6Rate       INTEGER,
        prtExLs6ClkMode    INTEGER,
        prtExLs6CtrlSignal INTEGER,
        prtExLs6DataBits   INTEGER,
        prtExLs6Cts        INTEGER,
        prtExLs6LinkToInternal INTEGER
      }

prtExLs6CnfgIdx OBJECT-TYPE
      SYNTAX  Integer32 (1..255)
      MAX-ACCESS  read-only
      STATUS  current
      DESCRIPTION
      "This attribute indicates the Idx of the Cnfg (1..100) being
       accessed.
       Idx  255 relates to the TmpCnfg"
      ::= {prtExLs6CnfgEntry 1}

prtExLs6SltIdx OBJECT-TYPE
      SYNTAX  INTEGER
          {
       io1   (5),
       io2   (6),
       io3   (7),
       io4   (8),
       io5   (9),
       io6  (10),
       io7  (11),
       io8  (12),
       io9  (13),
       io10 (14),
       io11 (15),
       io12 (16),
       notApplicable (255)
       }
      MAX-ACCESS  read-only
      STATUS  current
      DESCRIPTION
      "This attribute indicates a unique  slot  position where
       the card is inserted.
       In the ?004 Unit the entries io6(10)..io12(16) are not valid."
      ::= {prtExLs6CnfgEntry 2}

prtExLs6PrtIdx OBJECT-TYPE
      SYNTAX  INTEGER
          {
          exPrt1    (1) ,
          exPrt2    (2) ,
          exPrt3    (3) ,
          exPrt4    (4) ,
          exPrt5    (5) ,
          exPrt6    (6) ,
          exPrt7    (7) ,
          exPrt8    (8) ,
          exPrt9    (9) ,
          exPrt10  (10) ,
          exPrt11  (11) ,
          exPrt12  (12)
          }
      MAX-ACCESS  read-only
      STATUS  current
      DESCRIPTION
      "This attribute indicates a unique  port index."
      ::= {prtExLs6CnfgEntry 3}

prtExLs6Connect OBJECT-TYPE
      SYNTAX  INTEGER
              {
                no  (2),
                yes (3)
              }
      MAX-ACCESS  read-write
      STATUS  current
      DESCRIPTION
      "This attribute indicates whether the  port  should be
       considered in any of the mux algorithms."
      ::= {prtExLs6CnfgEntry 4}

prtExLs6Protocol OBJECT-TYPE
      SYNTAX  INTEGER
              {
                sync  (2),
                async (3)
              }
      MAX-ACCESS  read-write
      STATUS  current
      DESCRIPTION
      "This attribute indicates the protocol.
       async - can be selected only for ports 1-2."
      ::= {prtExLs6CnfgEntry 5}

prtExLs6Rate OBJECT-TYPE
      SYNTAX  INTEGER
       {
          r300bps      (2),
          r600bps      (3),
          r1200bps     (4),
          r2400bps     (5),
          r4800bps     (6),
          r7200bps     (7),
          r8000bps     (8),
          r9600bps     (9),
          r14400bps   (10),
          r16000bps   (11),
          r19200bps   (12),
          r24000bps   (13),
          r28800bps   (14),
          r32000bps   (15),
          r38400bps   (16),
          r48000bps   (17),
          r56000bps   (18),
          r57600bps   (19),
          r64000bps   (20)
       }
      MAX-ACCESS  read-write
      STATUS  current
      DESCRIPTION
      "Port rates in bps.
       g1 - contains the values : (2)-(6),(9),(12),(16)
       g2 - contains the values : (7),(10),(14),(19)
       g3 - contains the values : (8),(11),(13),(15),(17),(18),(20);
            it is not applicable when using Async protocol.
       Rates of pair ports (1-2, 3-4, 5-6) must be from the same
       group."
      ::= {prtExLs6CnfgEntry 6}

prtExLs6ClkMode OBJECT-TYPE
      SYNTAX  INTEGER
       {
          dce     (1),
          extDce  (2),
          dte1    (3),
          notApplicable (255)
       }
      MAX-ACCESS  read-write
      STATUS  current
      DESCRIPTION
      "This attribute indicates a unique port operation clock mode.
       It is applicable for Sync protocol only ."
      ::= {prtExLs6CnfgEntry 7}

prtExLs6CtrlSignal OBJECT-TYPE
      SYNTAX  INTEGER
       {
    local     (2),
    rts       (3),
    dtrAndRts (4)
       }
      MAX-ACCESS  read-write
      STATUS  current
      DESCRIPTION
      "Control Signal."
      ::= {prtExLs6CnfgEntry 8}

prtExLs6DataBits OBJECT-TYPE
      SYNTAX  INTEGER
       {
    d6bits    (1),
    d7bits    (2),
    d8bits    (3),
    d9bits    (4),
    notApplicable (255)
       }
      MAX-ACCESS  read-write
      STATUS  current
      DESCRIPTION
      "Data Bits.
       This object is applicable for Async protocol only."
      ::= {prtExLs6CnfgEntry 9}

prtExLs6Cts OBJECT-TYPE
      SYNTAX  INTEGER
       {
     notApplicable (1),
     on            (2),
     rts           (3)
       }
      MAX-ACCESS  read-write
      STATUS  current
      DESCRIPTION
      "This object indicates the CTS control line
       operation mode."
      ::= {prtExLs6CnfgEntry 10}

prtExLs6LinkToInternal OBJECT-TYPE
      SYNTAX  INTEGER
          {
          inPrt1        (101) ,
          inPrt2        (102) ,
    notApplicable (255)
          }
      MAX-ACCESS  read-write
      STATUS  current
      DESCRIPTION
      "This object indicates which internal port of the card,
       the external port is linked to."
      ::= {prtExLs6CnfgEntry 11}


--prtExLs6VCnfgTable defines the parameters of the
-- LS-6 cards family external Voice & FAX ports (7-8)

prtExLs6VCnfgTable OBJECT-TYPE
      SYNTAX SEQUENCE OF PrtExLs6VCnfgEntry
      MAX-ACCESS not-accessible
      STATUS  current
      DESCRIPTION
       "The write operation into the Table Objects is valid only
        to the TmpCnfg entry."
      ::= {prtLs6Cnfg 2}

prtExLs6VCnfgEntry OBJECT-TYPE
      SYNTAX PrtExLs6VCnfgEntry
      MAX-ACCESS not-accessible
      STATUS current
	DESCRIPTION  "An entry in table."
	INDEX {prtExLs6VCnfgIdx, prtExLs6VSltIdx, prtExLs6VPrtIdx }
      ::= {prtExLs6VCnfgTable  1}


PrtExLs6VCnfgEntry ::=
      SEQUENCE {
        prtExLs6VCnfgIdx       Integer32,
        prtExLs6VSltIdx        INTEGER,
        prtExLs6VPrtIdx        INTEGER,

        prtExLs6VConnect       INTEGER,
        prtExLs6VRate          INTEGER,
        prtExLs6VEchoCanceler  INTEGER,
        prtExLs6VIfType        INTEGER,
        prtExLs6VTxGain        Integer32,
        prtExLs6VRxGain        Integer32,
        prtExLs6VOos           INTEGER
      }

prtExLs6VCnfgIdx OBJECT-TYPE
      SYNTAX  Integer32  (1..255)
      MAX-ACCESS  read-only
      STATUS  current
      DESCRIPTION
      "This attribute indicates the Idx of the Cnfg (1..100) being
       accessed.
       Idx  255 relates to the TmpCnfg"
      ::= {prtExLs6VCnfgEntry 1}

prtExLs6VSltIdx OBJECT-TYPE
      SYNTAX  INTEGER
 {
       io1   (5),
       io2   (6),
       io3   (7),
       io4   (8),
       io5   (9),
       io6  (10),
       io7  (11),
       io8  (12),
       io9  (13),
       io10 (14),
       io11 (15),
       io12 (16)
 }
      MAX-ACCESS  read-only
      STATUS  current
      DESCRIPTION
      "This attribute indicates a unique  slot  position where
       the card is inserted.
       In the ?004 Unit the entries io6(10)..io12(16) are not valid."
    ::= {prtExLs6VCnfgEntry 2}

prtExLs6VPrtIdx OBJECT-TYPE
      SYNTAX  INTEGER
 {
       exPrt7    (7) ,
       exPrt8    (8)
 }
      MAX-ACCESS  read-only
      STATUS  current
      DESCRIPTION
      "A unique identifier of the port, within the card."
      ::= {prtExLs6VCnfgEntry 3}

prtExLs6VConnect OBJECT-TYPE
      SYNTAX  INTEGER
              {
                no  (2),
                yes (3)
              }
      MAX-ACCESS  read-write
      STATUS  current
      DESCRIPTION
      "This attribute indicates whether the  port  should be
       considered in any of the mux algorithms."
      ::= {prtExLs6VCnfgEntry 4}


prtExLs6VRate OBJECT-TYPE
      SYNTAX  INTEGER
       {
          r6400bps      (2),
    r7200bps      (3),
    r8000bps      (4),
    r9600bps      (5),
    r16000bps     (6),
    r24000bps     (7),
    r32000bps     (8),
    r64000bps     (9)
       }
      MAX-ACCESS  read-write
      STATUS  current
      DESCRIPTION
      "Rate (bps) used for FAX transmission and Voice coding."
      ::= {prtExLs6VCnfgEntry 5}

prtExLs6VEchoCanceler OBJECT-TYPE
      SYNTAX  INTEGER
       {
          off    (2),
          on     (3)
       }
      MAX-ACCESS  read-write
      STATUS  current
      DESCRIPTION
      "Echo canceler activation."
      ::= {prtExLs6VCnfgEntry 6}

prtExLs6VIfType OBJECT-TYPE
      SYNTAX  INTEGER
              {
          w2wire   (1),
          w4wire   (2)
              }
      MAX-ACCESS  read-write
      STATUS  current
      DESCRIPTION
      "This attribute indicates the interface type of the  port.
       w4wire - is applicable only for E&M port type."
      ::= {prtExLs6VCnfgEntry 7}

prtExLs6VTxGain OBJECT-TYPE
      SYNTAX  Integer32
      MAX-ACCESS  read-write
      STATUS  current
      DESCRIPTION
      "Transmit gain in dBm.
       E&M - values range: -17 .. 8
       FXO - values range: -16 .. 4
       FXS - values range: -13 .. 8  "
      ::= {prtExLs6VCnfgEntry 8}

prtExLs6VRxGain OBJECT-TYPE
      SYNTAX  Integer32
      MAX-ACCESS  read-write
      STATUS  current
      DESCRIPTION
      "Receive gain in dBm.
       E&M - values range: -17 .. 2
       FXO - values range: -17 .. -1
       FXS - values range: -17 .. 2  "
      ::= {prtExLs6VCnfgEntry 9}

prtExLs6VOos OBJECT-TYPE
      SYNTAX  INTEGER
       {
          forcedIdle     (1),
          forcedBusy     (2),
          busyIdle       (3),
          idleBusy       (4)
       }
      MAX-ACCESS  read-write
      STATUS  current
      DESCRIPTION
      "Out of Service signaling mode."
      ::= {prtExLs6VCnfgEntry 10}



-- Ls6 and Ls12 Internal composite channel parameters
--

prtInLs6CnfgTable OBJECT-TYPE
      SYNTAX SEQUENCE OF PrtInLs6CnfgEntry
      MAX-ACCESS not-accessible
      STATUS  current
      DESCRIPTION
       "The write operation into the Table Objects is valid only
        to the TmpCnfg entry."
      ::= {prtLs6Cnfg 3}

prtInLs6CnfgEntry OBJECT-TYPE
      SYNTAX PrtInLs6CnfgEntry
      MAX-ACCESS not-accessible
      STATUS current
	DESCRIPTION  "An entry in table."
	INDEX {prtInLs6CnfgIdx, prtInLs6SltIdx, prtInLs6PrtIdx }
      ::= {prtInLs6CnfgTable 1}

PrtInLs6CnfgEntry ::=
      SEQUENCE {
        prtInLs6CnfgIdx    Integer32,
        prtInLs6SltIdx     INTEGER,
        prtInLs6PrtIdx     INTEGER,
        prtInLs6Connect    INTEGER,
        prtInLs6TandemMode INTEGER,
        prtInLs6Rate       INTEGER,
        prtInLs6RemoteType INTEGER,
        prtInLs6LinkTo     INTEGER
      }

prtInLs6CnfgIdx OBJECT-TYPE
      SYNTAX  Integer32 (1..255)
      MAX-ACCESS  read-only
      STATUS  current
      DESCRIPTION
      "This attribute indicates the Idx of the Cnfg (1..100) being
       accessed.
       Idx  255 relates to the TmpCnfg"
      ::= {prtInLs6CnfgEntry 1}

prtInLs6SltIdx OBJECT-TYPE
      SYNTAX  INTEGER
          {
       io1   (5),
       io2   (6),
       io3   (7),
       io4   (8),
       io5   (9),
       io6  (10),
       io7  (11),
       io8  (12),
       io9  (13),
       io10 (14),
       io11 (15),
       io12 (16)
       }
      MAX-ACCESS  read-only
      STATUS  current
      DESCRIPTION
      "This attribute indicates a unique  slot  position where
       the card is inserted.
       In the ?004 Unit the entries io6(10)..io12(16) are not valid."
      ::= {prtInLs6CnfgEntry 2}

prtInLs6PrtIdx OBJECT-TYPE
      SYNTAX  INTEGER
          {
          inPrt1    (101),
          inPrt2    (102)
          }
      MAX-ACCESS  read-only
      STATUS  current
      DESCRIPTION
      "This attribute indicates a unique internal port index."
      ::= {prtInLs6CnfgEntry 3}

prtInLs6Connect OBJECT-TYPE
      SYNTAX  INTEGER
              {
                no  (2),
                yes (3)
              }
      MAX-ACCESS  read-write
      STATUS  current
      DESCRIPTION
      "This attribute indicates whether the port should be considered in
       any of the mux  algorithms. It also affects all the module
       considerations because the module has only one Internal
       interface which is the composite channel."
      ::= {prtInLs6CnfgEntry 4}

prtInLs6TandemMode  OBJECT-TYPE
      SYNTAX  INTEGER
       {
     noTandem     (1),
     tandemMaster (2),
     tandemSlave  (3)
    }
      MAX-ACCESS  read-write
      STATUS  current
      DESCRIPTION
      "This object indicates the Tandem Mode.
       tandemSlave - is valid only for an LS-6 card having on
    the (current slot-1) an LS-6 card with 'tandemMaster' mode."
       ::= {prtInLs6CnfgEntry 5}

prtInLs6Rate OBJECT-TYPE
      SYNTAX  INTEGER
       {
     r32Kbps   (1),
     r56Kbps   (2),
     r64Kpbs   (3),
     r128Kbps  (4),
     r256Kbps  (5),
     r384Kbps  (6),
     r192Kbps  (7),
     r512Kbps  (8),
     r768Kbps  (9),
	 r14400bps(10) 
    }
      MAX-ACCESS  read-write
      STATUS  current
      DESCRIPTION
      "Main Rate in Kbps."
      ::= {prtInLs6CnfgEntry 6}

prtInLs6RemoteType OBJECT-TYPE
      SYNTAX  INTEGER
       {
     ls6            (1),
     km2kSlave      (2),
     km2kStandalone (3),
     notApplicable (255)
    }
      MAX-ACCESS  read-write
      STATUS  current
      DESCRIPTION
      "Remote Type.
       notApplicable - when prtInLs6TandemMode=tandemSlave "
      ::= {prtInLs6CnfgEntry 7}

prtInLs6LinkTo OBJECT-TYPE
      SYNTAX  INTEGER
       {
       io1   (5),
       io2   (6),
       io3   (7),
       io4   (8),
       io5   (9),
       io6  (10),
       io7  (11),
       io8  (12),
       io9  (13),
       io10 (14),
       io11 (15),
       io12 (16),
    notApplicable (255)
       }
      MAX-ACCESS  read-write
      STATUS  deprecated
      DESCRIPTION
      "It indicates the slot of the main link card to which the
       Ls6 card is mapped.
       In the ?004 Unit the entries io6(10)..io12(16) are not valid.
       notApplicable - when prtInLs6TandemMode=tandemSlave.
       STATUS  deprecated - this object is replaced by prtGenCnfgLinkToSlot
       and prtGenCnfgLinkToPort. "
      ::= {prtInLs6CnfgEntry 8}

--
-- Megaplex?000/?004 VC-3 TDM I/O family port.
-- (VC3/E&M,VC3/FXO,VC3/FXS)
--
--

--prtExVc3CnfgTable defines the parameters of the
-- VC-3 and VF-3 cards family external ports

prtExVc3CnfgTable OBJECT-TYPE
      SYNTAX SEQUENCE OF PrtExVc3CnfgEntry
      MAX-ACCESS not-accessible
      STATUS  current
      DESCRIPTION
       "The write operation into the Table Objects is valid only
        to the TmpCnfg entry."
      ::= { prtVc3Cnfg 1}

prtExVc3CnfgEntry OBJECT-TYPE
      SYNTAX PrtExVc3CnfgEntry
      MAX-ACCESS not-accessible
      STATUS current
	DESCRIPTION  "An entry in table."
	INDEX {prtExVc3CnfgIdx, prtExVc3SltIdx, prtExVc3PrtIdx }
      ::= { prtExVc3CnfgTable 1}

PrtExVc3CnfgEntry ::=
      SEQUENCE {
        prtExVc3CnfgIdx        Integer32,
        prtExVc3SltIdx         INTEGER,
        prtExVc3PrtIdx         INTEGER,

        prtExVc3Connect      INTEGER,
        prtExVc3TransGain    Integer32,
        prtExVc3ReceiveGain  Integer32,
        prtExVc3Wire         INTEGER,
        prtExVc3Rate         INTEGER,
        prtExVc3EchoCanceler INTEGER
      }

prtExVc3CnfgIdx OBJECT-TYPE
      SYNTAX  Integer32  (1..255)
      MAX-ACCESS  read-only
      STATUS  current
      DESCRIPTION
      "This attribute indicates the Idx of the Cnfg (1..100) being
       accessed.
       Idx  255 relates to the TmpCnfg"
      ::= {prtExVc3CnfgEntry 1}

prtExVc3SltIdx OBJECT-TYPE
      SYNTAX  INTEGER
 {
       io1   (5),
       io2   (6),
       io3   (7),
       io4   (8),
       io5   (9),
       io6  (10),
       io7  (11),
       io8  (12),
       io9  (13),
       io10 (14),
       io11 (15),
       io12 (16)
 }
      MAX-ACCESS  read-only
      STATUS  current
      DESCRIPTION
      "This attribute indicates a unique  slot  position where
       the card is inserted.
       In the ?004 Unit the entries io6(10)..io12(16) are not valid."
      ::= {prtExVc3CnfgEntry 2}

prtExVc3PrtIdx OBJECT-TYPE
      SYNTAX  INTEGER
 {
       exPrt1    (1) ,
       exPrt2    (2) ,
       exPrt3    (3)
 }
      MAX-ACCESS  read-only
      STATUS  current
      DESCRIPTION
      "A unique identifier of the port, within the card."
      ::= {prtExVc3CnfgEntry 3}

prtExVc3Connect OBJECT-TYPE
      SYNTAX  INTEGER
              {
                no  (2),
                yes (3)
              }
      MAX-ACCESS  read-write
      STATUS  current
      DESCRIPTION
      "This attribute indicates whether the  port  should be
       considered in any of the mux algorithms."
      ::= {prtExVc3CnfgEntry 4}

prtExVc3TransGain OBJECT-TYPE
      SYNTAX  Integer32
      MAX-ACCESS  read-write
      STATUS  current
      DESCRIPTION
      "Transmit gain in dBm."
      ::= {prtExVc3CnfgEntry 5}

prtExVc3ReceiveGain OBJECT-TYPE
      SYNTAX  Integer32
      MAX-ACCESS  read-write
      STATUS  current
      DESCRIPTION
      "Receive gain in dBm."
      ::= {prtExVc3CnfgEntry 6}

prtExVc3Wire OBJECT-TYPE
      SYNTAX  INTEGER
       {
          w2wire   (1),
          w4wire   (2)
       }
      MAX-ACCESS  read-write
      STATUS  current
      DESCRIPTION
      "This object is equal for all the ports in the specific
       card because of HW limitations"
      ::= {prtExVc3CnfgEntry 7}

prtExVc3Rate OBJECT-TYPE
      SYNTAX  INTEGER
       {
          r9600bps    (1),
    r4800bps    (2)
       }
      MAX-ACCESS  read-write
      STATUS  current
      DESCRIPTION
      "Rate in bps."
      ::= {prtExVc3CnfgEntry 8}

prtExVc3EchoCanceler OBJECT-TYPE
      SYNTAX  INTEGER
       {
          off    (2),
          on     (3)
       }
      MAX-ACCESS  read-write
      STATUS  current
      DESCRIPTION
      "Echo canceler activation. The value will be the same for
       all the card's external ports."
      ::= {prtExVc3CnfgEntry 9}

--prtInVc3CnfgTable defines the parameters of the
-- VC-3 or VF-3 cards family internal ports

prtInVc3CnfgTable OBJECT-TYPE
      SYNTAX SEQUENCE OF PrtInVc3CnfgEntry
      MAX-ACCESS not-accessible
      STATUS  current
      DESCRIPTION
       "The write operation into the Table Objects is valid only
        to the TmpCnfg entry."
      ::= { prtVc3Cnfg 2}

prtInVc3CnfgEntry OBJECT-TYPE
      SYNTAX PrtInVc3CnfgEntry
      MAX-ACCESS not-accessible
      STATUS current
	DESCRIPTION  "An entry in table."
	INDEX {prtInVc3CnfgIdx, prtInVc3SltIdx, prtInVc3PrtIdx }
      ::= { prtInVc3CnfgTable 1}

PrtInVc3CnfgEntry ::=
      SEQUENCE {
        prtInVc3CnfgIdx        Integer32,
        prtInVc3SltIdx         INTEGER,
        prtInVc3PrtIdx         INTEGER,

        prtInVc3Connect        INTEGER,
        prtInVc3Rate           INTEGER,
        prtInVc3Oos            INTEGER,
        prtInVc3LinkTo         INTEGER

      }

prtInVc3CnfgIdx OBJECT-TYPE
      SYNTAX  Integer32  (1..255)
      MAX-ACCESS  read-only
      STATUS  current
      DESCRIPTION
      "This attribute indicates the Idx of the Cnfg (1..100) being
       accessed.
       Idx  255 relates to the TmpCnfg"
      ::= {prtInVc3CnfgEntry 1}

prtInVc3SltIdx OBJECT-TYPE
      SYNTAX  INTEGER
 {
       io1   (5),
       io2   (6),
       io3   (7),
       io4   (8),
       io5   (9),
       io6  (10),
       io7  (11),
       io8  (12),
       io9  (13),
       io10 (14),
       io11 (15),
       io12 (16)
 }
      MAX-ACCESS  read-only
      STATUS  current
      DESCRIPTION
      "This attribute indicates a unique  slot  position where
       the card is inserted.
       In the ?004 Unit the entries io6(10)..io12(16) are not valid."
      ::= {prtInVc3CnfgEntry 2}

prtInVc3PrtIdx OBJECT-TYPE
      SYNTAX  INTEGER
 {
       inPrt1    (101)
 }
      MAX-ACCESS  read-only
      STATUS  current
      DESCRIPTION
      "A unique identifier of the port, within the card."
      ::= {prtInVc3CnfgEntry 3}

prtInVc3Connect OBJECT-TYPE
      SYNTAX  INTEGER
              {
                no  (2),
                yes (3)
              }
      MAX-ACCESS  read-write
      STATUS  current
      DESCRIPTION
      "This attribute indicates whether the  port  should be
       considered in any of the mux algorithms."
      ::= {prtInVc3CnfgEntry 4}

prtInVc3Rate OBJECT-TYPE
      SYNTAX  INTEGER
       {
          r32000bps    (1),
    r16000bps    (2)
       }
      MAX-ACCESS  read-write
      STATUS  current
      DESCRIPTION
      "Rate in bps."
      ::= {prtInVc3CnfgEntry 5}

prtInVc3Oos OBJECT-TYPE
      SYNTAX  INTEGER
       {
          forcedIdle     (1),
          forcedBusy     (2),
          busyIdle       (3),
          idleBusy       (4)
       }
      MAX-ACCESS  read-write
      STATUS  current
      DESCRIPTION
      " This object is equal for all the ports in the specific
        card because of HW limitations"
      ::= {prtInVc3CnfgEntry 6}

prtInVc3LinkTo OBJECT-TYPE
      SYNTAX  INTEGER
       {
       io1   (5),
       io2   (6),
       io3   (7),
       io4   (8),
       io5   (9),
       io6  (10),
       io7  (11),
       io8  (12),
       io9  (13),
       io10 (14),
       io11 (15),
       io12 (16)
       }
      MAX-ACCESS  read-write
      STATUS  deprecated
      DESCRIPTION
      "This attribute indicates the slot of the ML card to which
       the VC card is mapped.
       In the ?004 Unit the entries io6(10)..io12(16) are not valid.
       STATUS  deprecated - this object is replaced by prtGenCnfgLinkToSlot
       and prtGenCnfgLinkToPort."
      ::= {prtInVc3CnfgEntry 7}


--
-- Megaplex?000/?004 VC-3 TDM I/O family port.
-- (VC-PBX, VC-PBX/T1,VC-PBX/E1)
--
--

--prtExVcPbxCnfgTable defines the parameters of the
-- VC-PBX or VF-PBX cards family external ports

prtExVcPbxCnfgTable OBJECT-TYPE
      SYNTAX SEQUENCE OF PrtExVcPbxCnfgEntry
      MAX-ACCESS not-accessible
      STATUS  current
      DESCRIPTION
       "The write operation into the Table Objects is valid only
        to the TmpCnfg entry."
      ::= { prtVcPbxCnfg 1}

prtExVcPbxCnfgEntry OBJECT-TYPE
      SYNTAX PrtExVcPbxCnfgEntry
      MAX-ACCESS not-accessible
      STATUS current
	DESCRIPTION  "An entry in table."
	INDEX {prtExVcPbxCnfgIdx, prtExVcPbxSltIdx, prtExVcPbxPrtIdx }
      ::= { prtExVcPbxCnfgTable 1}

PrtExVcPbxCnfgEntry ::=
      SEQUENCE {
        prtExVcPbxCnfgIdx        Integer32,
        prtExVcPbxSltIdx         INTEGER,
        prtExVcPbxPrtIdx         INTEGER,

        prtExVcPbxConnect        INTEGER,
        prtExVcPbxGroup          INTEGER,
        prtExVcPbxTransparent    INTEGER,
        prtExVcPbxTransSignalTs  Integer32,
        prtExVcPbxFrame          INTEGER,
        prtExVcPbxRestoreTime    INTEGER,
  prtExVcPbxLineCode       INTEGER,
        prtExVcPbxLineLength     INTEGER,
        prtExVcPbxLinkTo         INTEGER,
     prtExVcPbxSignalOper     INTEGER,
  prtExVcPbxIdleCode       INTEGER
      }

prtExVcPbxCnfgIdx OBJECT-TYPE
      SYNTAX  Integer32  (1..255)
      MAX-ACCESS  read-only
      STATUS  current
      DESCRIPTION
      "This object indicates the Idx of the Cnfg (1..100) being
       accessed.
       Idx  255 relates to the TmpCnfg"
      ::= {prtExVcPbxCnfgEntry 1}

prtExVcPbxSltIdx OBJECT-TYPE
      SYNTAX  INTEGER
 {
       io1   (5),
       io2   (6),
       io3   (7),
       io4   (8),
       io5   (9),
       io6  (10),
       io7  (11),
       io8  (12),
       io9  (13),
       io10 (14),
       io11 (15),
       io12 (16)
 }
      MAX-ACCESS  read-only
      STATUS  current
      DESCRIPTION
      "This object indicates a unique  slot  position where
       the card is inserted.
       In the ?004 Unit the entries io6(10)..io12(16) are not valid."
      ::= {prtExVcPbxCnfgEntry 2}

prtExVcPbxPrtIdx OBJECT-TYPE
      SYNTAX  INTEGER
 {
       exPrt1    (1)
 }
      MAX-ACCESS  read-only
      STATUS  current
      DESCRIPTION
      "A unique identifier of the port, within the card."
      ::= {prtExVcPbxCnfgEntry 3}

prtExVcPbxConnect OBJECT-TYPE
      SYNTAX  INTEGER
              {
                no  (2),
                yes (3)
              }
      MAX-ACCESS  read-write
      STATUS  current
      DESCRIPTION
      "This object indicates whether the  port  should be
       considered in any of the mux algorithms."
      ::= {prtExVcPbxCnfgEntry 4}

prtExVcPbxGroup OBJECT-TYPE
      SYNTAX  INTEGER
 {
       io1   (5),
       io2   (6),
       io3   (7),
       io4   (8),
       io5   (9),
       io6  (10),
       io7  (11),
       io8  (12),
       io9  (13),
       io10 (14),
       io11 (15),
       io12 (16),
    notApplicable (255)
 }
      MAX-ACCESS  read-only
      STATUS  current
      DESCRIPTION
      "The group object links together several VC-PBX cards,
       concerning compression of the same input T1/E1 link
       time-slots.
       When ports of different slots have the same group, they are
       linked.
       When ports have a different group, they are not linked.
    For VC-PBX/T1 and E1 cards, this object is - their own
    IO Slot.
       In the ?004 Unit the entries io6(10)..io12(16) are not valid."
      ::= {prtExVcPbxCnfgEntry 5}

prtExVcPbxTransparent     OBJECT-TYPE
      SYNTAX  INTEGER
              {
                no  (2),
                yes (3),
    notApplicable (255)
              }
      MAX-ACCESS  read-write
      STATUS  current
      DESCRIPTION
      "This object indicates whether the Transparent transfer
       of Time-Slots is required or not.
       Time-Slots transferred by Transparent, will not be
       compressed.
       no  - applicable only for VC-PBX/T1 and VC-PBX/E1 cards
       yes - applicable only for VC-PBX/T1 and VC-PBX/E1 cards
       notApplicable - only for VC-PBX cards."
      ::= {prtExVcPbxCnfgEntry 6}

prtExVcPbxTransSignalTs     OBJECT-TYPE
      SYNTAX  Integer32
      MAX-ACCESS  read-write
      STATUS  current
      DESCRIPTION
      "This object specifies the ML Time-Slot dedicated to
       the signaling of the PABX Transparent TSs.
       None = 255.
       When prtExVcPbxTransparent=no this object's value=None (255)
       When prtExVcPbxTransparent=notApplicable, this object's
       value=None (255).
       When prtExVcPbxTransparent=yes:
    - for VC-PBX/T1 ports, this object's valid values are 1..16
      or None (255).
       - for VC-PBX/E1 ports, this object's value will be 16 or None
      (255)."
      ::= {prtExVcPbxCnfgEntry 7}

prtExVcPbxFrame OBJECT-TYPE
      SYNTAX  INTEGER
       {
  esfT1          (2), --> dsx1ESF
  sfT1           (3), --> dsx1D4
  g732nE1        (4), --> dsx1E1
  g732nE1CRC     (5), --> dsx1E1-CRC
  g732sE1        (6), --> dsx1E1-MF
  g732sE1CRC     (7),  --> dsx1E1-MF-CRC
  notApplicable  (255)
       }
      MAX-ACCESS  read-write
      STATUS  current
      DESCRIPTION
      "This object is the frame parameter for T1/E1 interface.
       The user should select only the parameters which are relevant
       to the specific card:
       T1 values for the VC-PBX/T1 card.
       E1 values for the VC-PBX/E1 card.
    notApplicable - for the VC-PBX card.
       This parameter has the same values as dsx1LineType in T1/E1
       MIB (RFC-1406). The parameters in dsx1LineType are:
                     other          (1)
      esfT1          dsx1ESF        (2)
      sfT1           dsx1D4         (3)
      g732nE1        dsx1E1         (4)
      g732nE1CRC     dsx1E1-CRC     (5)
      g732sE1        dsx1E1-MF      (6)
      g732sE1CRC     dsx1E1-MF-CRC  (7)  "
      ::= {prtExVcPbxCnfgEntry 8}

prtExVcPbxRestoreTime OBJECT-TYPE
      SYNTAX  INTEGER
       {
        restoreT1secFast      (2),
        restoreT10sec62411    (3),
        ccittE1               (4),
  notApplicable         (255)
       }
      MAX-ACCESS  read-write
      STATUS  current
      DESCRIPTION
      "The time passing from the disappearance of the loss of
       synchronization condition (red alarm) to the restoration of
       normal service. The options 1secFast(2) and 10sec62411(3)
       for E1 interfaces are proprietary implementation of the T1
       standard to the E1 interface.
       ccittE1 - is applicable only for VC-PBX/E1 card
       notApplicable - is applicable for VC-PBX card"
      ::= {prtExVcPbxCnfgEntry 9}

prtExVcPbxLineCode OBJECT-TYPE
      SYNTAX  INTEGER
       {
  b7zsT1 (1),  --> dsx1JBZS
  b8zsT1 (2),  --> dsx1B8ZS
        transT1(3),  --> dsx1AMI
        hdb3E1 (4),  --> dsx1HDB3
  notApplicable (255)
       }
      MAX-ACCESS  read-write
      STATUS  current
      DESCRIPTION
      "This object is the line code parameter used for T1/E1
       interface.
       The user should select only the parameters which are relevant
       to the specific card:
       T1 line code parameters for VC-PBX/T1
       E1 line code parameters for VC-PBX/E1
    notApplicable - for VC-PBX
       This parameter has the same values as dsx1LineCoding in T1/E1
       MIB (RFC-1406).  The parameters in dsx1LineCoding are:
     dsx1JBZS  (1)
     dsx1B8ZS  (2)
     dsx1HDB3  (3)
     dsx1ZBTSI (4)
     dsx1AMI   (5)
     other     (6)"
      ::= {prtExVcPbxCnfgEntry 10}

prtExVcPbxLineLength OBJECT-TYPE
      SYNTAX  INTEGER
       {
        unknown      (1),
        len0p133ft   (2),
        len134p266ft (3),
        len267p399ft (4),
        len400p533ft (5),
        len534p655ft (6),
        notApplicable (255)
       }
      MAX-ACCESS  read-write
      STATUS  current
      DESCRIPTION
      "This object is the line length parameter.
       It is applicable only for the VC-PBX/T1 card.
       notApplicable - for the VC-PBX and VC-PBX/E1 card.
       lenXXXpXXXft = len-XXX-XXXft."
      ::= {prtExVcPbxCnfgEntry 11}

prtExVcPbxLinkTo OBJECT-TYPE
      SYNTAX  INTEGER
       {
       io1   (5),
       io2   (6),
       io3   (7),
       io4   (8),
       io5   (9),
       io6  (10),
       io7  (11),
       io8  (12),
       io9  (13),
       io10 (14),
       io11 (15),
       io12 (16),
    notApplicable (255)
       }
      MAX-ACCESS  read-write
      STATUS  deprecated
      DESCRIPTION
      "This object indicates the slot of the ML card to which
       the VC-PBX/T1, VC-PBX/E1 card Transparent TSs are mapped.
       notApplicable - for VC-PBX card AND
       for VC-PBX/T1, VC-PBX/E1 cards, when prtExVcPbxTransparent=no .
       In the ?004 Unit the entries io6(10)..io12(16) are not valid.
       STATUS  deprecated - this object is replaced by prtGenCnfgLinkToSlot
       and prtGenCnfgLinkToPort."
      ::= {prtExVcPbxCnfgEntry 12}

prtExVcPbxSignalOper OBJECT-TYPE
      SYNTAX  INTEGER
          {
          notApplicable (1),
          normal        (2),
          bEqA          (3),
    inverseA      (4)
          }
      MAX-ACCESS  read-write
      STATUS  current
      DESCRIPTION
      "This object indicates the Signaling Operation of the
       VC-PBX/T1, VC-PBX/E1 external port.
       notApplicable - for VC-PBX card
    normal - all 4 signaling bits are transferred.
    bEqA   - copy the A bit into the B bit. Applicable only for
             VC-PBX/T1."
      ::= {prtExVcPbxCnfgEntry 13}

prtExVcPbxIdleCode OBJECT-TYPE
      SYNTAX  INTEGER
          {
          notApplicable  (1),
          hff            (2),
          he4            (3),
    hd5            (4),
    h9e            (5),
    h98            (6),
    h7f            (7),
    h7e            (8),
    h54            (9),
    h1a           (10)
          }
      MAX-ACCESS  read-write
      STATUS  current
      DESCRIPTION
      "Determines the code for transmission in empty time slots.
       notApplicable - for VC-PBX card ."
      ::= {prtExVcPbxCnfgEntry 14}



--prtIn1p6VcPbxCnfgTable defines the parameters of the
-- VC-PBX or VF-PBX cards family internal ports 1-6

prtIn1p6VcPbxCnfgTable OBJECT-TYPE
      SYNTAX SEQUENCE OF PrtIn1p6VcPbxCnfgEntry
      MAX-ACCESS not-accessible
      STATUS  current
      DESCRIPTION
       "The write operation into the Table Objects is valid only
        to the TmpCnfg entry."
      ::= { prtVcPbxCnfg 2}

prtIn1p6VcPbxCnfgEntry OBJECT-TYPE
      SYNTAX PrtIn1p6VcPbxCnfgEntry
      MAX-ACCESS not-accessible
      STATUS current
	DESCRIPTION  "An entry in table."
	INDEX {prtIn1p6VcPbxCnfgIdx, prtIn1p6VcPbxSltIdx, prtIn1p6VcPbxPrtIdx }
      ::= { prtIn1p6VcPbxCnfgTable 1}

PrtIn1p6VcPbxCnfgEntry ::=
      SEQUENCE {
        prtIn1p6VcPbxCnfgIdx        Integer32,
        prtIn1p6VcPbxSltIdx         INTEGER,
        prtIn1p6VcPbxPrtIdx         INTEGER,

        prtIn1p6VcPbxConnect      INTEGER,
        prtIn1p6VcPbxRate         INTEGER,
        prtIn1p6VcPbxEchoCanceler INTEGER,
        prtIn1p6VcPbxPabxTs       Integer32 
	}

prtIn1p6VcPbxCnfgIdx OBJECT-TYPE
      SYNTAX  Integer32  (1..255)
      MAX-ACCESS  read-only
      STATUS  current
      DESCRIPTION
      "This object indicates the Idx of the Cnfg (1..100) being
       accessed.
       Idx  255 relates to the TmpCnfg"
      ::= {prtIn1p6VcPbxCnfgEntry 1}

prtIn1p6VcPbxSltIdx OBJECT-TYPE
      SYNTAX  INTEGER
 {
       io1   (5),
       io2   (6),
       io3   (7),
       io4   (8),
       io5   (9),
       io6  (10),
       io7  (11),
       io8  (12),
       io9  (13),
       io10 (14),
       io11 (15),
       io12 (16)
 }
      MAX-ACCESS  read-only
      STATUS  current
      DESCRIPTION
      "This object indicates a unique  slot  position where
       the card is inserted.
       In the ?004 Unit the entries io6(10)..io12(16) are not valid."
      ::= {prtIn1p6VcPbxCnfgEntry 2}

prtIn1p6VcPbxPrtIdx OBJECT-TYPE
      SYNTAX  INTEGER
 {
       inPrt1  (101) ,
       inPrt2  (102) ,
       inPrt3  (103) ,
       inPrt4  (104) ,
       inPrt5  (105) ,
       inPrt6  (106)
 }
      MAX-ACCESS  read-only
      STATUS  current
      DESCRIPTION
      "A unique identifier of the port, within the card."
      ::= {prtIn1p6VcPbxCnfgEntry 3}

prtIn1p6VcPbxConnect OBJECT-TYPE
      SYNTAX  INTEGER
              {
                no  (2),
                yes (3)
              }
      MAX-ACCESS  read-write
      STATUS  current
      DESCRIPTION
      "This object indicates whether the  port  should be
       considered in any of the mux algorithms."
      ::= {prtIn1p6VcPbxCnfgEntry 4}

prtIn1p6VcPbxRate OBJECT-TYPE
      SYNTAX  INTEGER
              {
                r4800bps  (1),
                r6400bps  (2),
                r7200bps  (3),
                r8000bps  (4),
    r9600bps  (5),
    r12800bps (6)
              }
      MAX-ACCESS  read-write
      STATUS  current
      DESCRIPTION
      "This object indicates the port Rate.
       For Normal mode (prtIn7p8VcPbxMode=normal), only part of the values
       are valid (constant rate).
       For Server mode (prtIn7p8VcPbxMode=server), all values are
       applicable (user can select the desired compression rate). "
      ::= {prtIn1p6VcPbxCnfgEntry 5}

prtIn1p6VcPbxEchoCanceler OBJECT-TYPE
      SYNTAX  INTEGER
       {
          off    (2),
          on     (3)
       }
      MAX-ACCESS  read-write
      STATUS  current
      DESCRIPTION
      "Echo canceler activation."
      ::= {prtIn1p6VcPbxCnfgEntry 6}

prtIn1p6VcPbxPabxTs OBJECT-TYPE
      SYNTAX  Integer32 (1..31)
      MAX-ACCESS  read-only
      STATUS  current
      DESCRIPTION
      "This object defines the PABX Time-Slot assigned to this
       internal port.
       For a  T1 link, the valid values are: 1 .. 24.
       For an E1 link, the valid values are: 1 .. 31.
       This object is NOT applicable when prtIn1p6VcPbxConnect=no.
       This object is applicable for all cards of VC-PBX family.
       Default=the internal port index (1..6)."
      ::= {prtIn1p6VcPbxCnfgEntry 7}

--prtIn7p8VcPbxCnfgTable defines the parameters of the
-- VC-PBX or VF-PBX cards family internal ports 7-8

prtIn7p8VcPbxCnfgTable OBJECT-TYPE
      SYNTAX SEQUENCE OF PrtIn7p8VcPbxCnfgEntry
      MAX-ACCESS not-accessible
      STATUS  current
      DESCRIPTION
       "The write operation into the Table Objects is valid only
        to the TmpCnfg entry."
      ::= { prtVcPbxCnfg 3}

prtIn7p8VcPbxCnfgEntry OBJECT-TYPE
      SYNTAX PrtIn7p8VcPbxCnfgEntry
      MAX-ACCESS not-accessible
      STATUS current
	DESCRIPTION  "An entry in table."
	INDEX {prtIn7p8VcPbxCnfgIdx, prtIn7p8VcPbxSltIdx, prtIn7p8VcPbxPrtIdx }
      ::= { prtIn7p8VcPbxCnfgTable 1}

PrtIn7p8VcPbxCnfgEntry ::=
      SEQUENCE {
        prtIn7p8VcPbxCnfgIdx        Integer32,
        prtIn7p8VcPbxSltIdx         INTEGER,
        prtIn7p8VcPbxPrtIdx         INTEGER,

        prtIn7p8VcPbxConnect      INTEGER,
        prtIn7p8VcPbxMode         INTEGER,
        prtIn7p8VcPbxRate         INTEGER,
        prtIn7p8VcPbxSignalMode   INTEGER,
        prtIn7p8VcPbxOos          INTEGER,
        prtIn7p8VcPbxLinkTo       INTEGER
      }

prtIn7p8VcPbxCnfgIdx OBJECT-TYPE
      SYNTAX  Integer32  (1..255)
      MAX-ACCESS  read-only
      STATUS  current
      DESCRIPTION
      "This object indicates the Idx of the Cnfg (1..100) being
       accessed.
       Idx  255 relates to the TmpCnfg"
      ::= {prtIn7p8VcPbxCnfgEntry 1}

prtIn7p8VcPbxSltIdx OBJECT-TYPE
      SYNTAX  INTEGER
 {
       io1   (5),
       io2   (6),
       io3   (7),
       io4   (8),
       io5   (9),
       io6  (10),
       io7  (11),
       io8  (12),
       io9  (13),
       io10 (14),
       io11 (15),
       io12 (16)
 }
      MAX-ACCESS  read-only
      STATUS  current
      DESCRIPTION
      "This object indicates a unique  slot  position where
       the card is inserted.
       In the ?004 Unit the entries io6(10)..io12(16) are not valid."
      ::= {prtIn7p8VcPbxCnfgEntry 2}

prtIn7p8VcPbxPrtIdx OBJECT-TYPE
      SYNTAX  INTEGER
 {
       inPrt7  (107) ,
       inPrt8  (108)
 }
      MAX-ACCESS  read-only
      STATUS  current
      DESCRIPTION
      "A unique identifier of the port, within the card."
      ::= {prtIn7p8VcPbxCnfgEntry 3}

prtIn7p8VcPbxConnect OBJECT-TYPE
      SYNTAX  INTEGER
              {
                no  (2),
                yes (3)
              }
      MAX-ACCESS  read-write
      STATUS  current
      DESCRIPTION
      "This object indicates whether the  port  should be
       considered in any of the mux algorithms."
      ::= {prtIn7p8VcPbxCnfgEntry 4}

prtIn7p8VcPbxMode OBJECT-TYPE
      SYNTAX  INTEGER
              {
                normal  (1),
                server  (2)
              }
      MAX-ACCESS  read-write
      STATUS  current
      DESCRIPTION
      "This object indicates the working mode of the port:
       - normal - the compressed voice will be sent to an MTML
                  card inside the Mux.
       - server - the compressed voice will be sent to the Digital
                  Voice connector, as a service to an outside user."
      ::= {prtIn7p8VcPbxCnfgEntry 5}

prtIn7p8VcPbxRate OBJECT-TYPE
      SYNTAX  INTEGER
              {
                r32Kbps  (1),
    r16Kbps  (2),
                notApplicable (255)
              }
      MAX-ACCESS  read-write
      STATUS  current
      DESCRIPTION
      "This object indicates the port Main Rate.
       For Server mode (prtIn7p8VcPbxMode=server), the value will
       be notApplicable. "
      ::= {prtIn7p8VcPbxCnfgEntry 6}

prtIn7p8VcPbxSignalMode OBJECT-TYPE
      SYNTAX  INTEGER
              {
                none    (1),
                aBit    (2),
    abcBit  (3),
    abcdBit (4)
              }
      MAX-ACCESS  read-write
      STATUS  current
      DESCRIPTION
      "This object indicates the Signal Mode.
       For Server mode (prtIn7p8VcPbxMode=server), the only valid
       values are:
       - none
       - aBit "
      ::= {prtIn7p8VcPbxCnfgEntry 7}

prtIn7p8VcPbxOos OBJECT-TYPE
      SYNTAX  INTEGER
       {
          forcedIdle     (1),
          forcedBusy     (2)
       }
      MAX-ACCESS  read-write
      STATUS  current
      DESCRIPTION
      " Out of service Signaling mode."
      ::= {prtIn7p8VcPbxCnfgEntry 8}

prtIn7p8VcPbxLinkTo OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       notApplicable (255)
       }
      MAX-ACCESS  read-write
      STATUS  deprecated
      DESCRIPTION
      "This object indicates the slot of the ML card to which
       the VC card is mapped.
       In the ?004 Unit the entries io6(10)..io12(16) are not valid.
       For Server mode (prtIn7p8VcPbxMode=server), this object is
       not applicable.
       Both ports, 7 and 8 should be linked to the same Slot.
       STATUS  deprecated - this object is replaced by prtGenCnfgLinkToSlot
       and prtGenCnfgLinkToPort."
      ::= {prtIn7p8VcPbxCnfgEntry 9}

--prtExVcPbxTsTable defines PABX Time Slots assignment of the
-- VC-PBX E1/T1 cards

prtExVcPbxTsTable OBJECT-TYPE
      SYNTAX SEQUENCE OF PrtExVcPbxTsEntry
      MAX-ACCESS not-accessible
      STATUS  current
      DESCRIPTION
       "The write operation into the table objects is valid only
        to the TmpCnfg entry."
      ::= { prtVcPbxCnfg 4}

prtExVcPbxTsEntry OBJECT-TYPE
      SYNTAX PrtExVcPbxTsEntry
      MAX-ACCESS not-accessible
      STATUS current
	DESCRIPTION  "An entry in table."
	INDEX {prtExVcPbxTsCnfgIdx, prtExVcPbxTsSltIdx, prtExVcPbxTsPrtIdx, prtExVcPbxTsIdx }
      ::= { prtExVcPbxTsTable 1}

PrtExVcPbxTsEntry ::=
      SEQUENCE {
      prtExVcPbxTsCnfgIdx        Integer32,
      prtExVcPbxTsSltIdx         INTEGER,
      prtExVcPbxTsPrtIdx         INTEGER,
      prtExVcPbxTsIdx            Integer32,
      prtExVcPbxTsMode           INTEGER,
      prtExVcPbxTsIConSlot       INTEGER,
      prtExVcPbxTsIConPrt        INTEGER
      }

prtExVcPbxTsCnfgIdx OBJECT-TYPE
      SYNTAX  Integer32  (1..255)
      MAX-ACCESS  read-only
      STATUS  current
      DESCRIPTION
      "This attribute indicates the Idx of the Cnfg (1..100) being
       accessed.
       Idx 255 relates to the TmpCnfg. "
      ::= { prtExVcPbxTsEntry 1}

prtExVcPbxTsSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      MAX-ACCESS  read-only
      STATUS  current
      DESCRIPTION
      "This attribute indicates a unique  slot  position where
       the card is inserted.
       In the ?004 Unit the entries io6(10)..io12(16) are not valid"
      ::= { prtExVcPbxTsEntry 2}

prtExVcPbxTsPrtIdx OBJECT-TYPE
      SYNTAX  INTEGER
      {
          exPrt1    (1)
      }
      MAX-ACCESS  read-only
      STATUS  current
      DESCRIPTION
      "This attribute indicates a unique  port number.
       VCPBX/E1 and VCPBX/T1 cards have only one external interface."
      ::= { prtExVcPbxTsEntry 3}

prtExVcPbxTsIdx OBJECT-TYPE
      SYNTAX  Integer32
      MAX-ACCESS  read-only
      STATUS  current
      DESCRIPTION
      "This attribute indicates a unique PABX time slot  position.
       The valid time slots are 1..24 for VC-PBX/T1 and
       1..31 for VC-PBX/E1."
      ::= { prtExVcPbxTsEntry 4}

prtExVcPbxTsMode OBJECT-TYPE
      SYNTAX  INTEGER
              {
                unused      (1),
                compressed  (2),
                transparent (3)
              }
      MAX-ACCESS  read-write
      STATUS  current
      DESCRIPTION
      "This attribute indicates the usage, process and way of the
       specific PABX TS towards its destination:
       unused - the TS is not used (no processing, no destination).
       compressed - the TS is used, sent for compression to an
                internal port 1..6 of either the same card or a
                VC-PBX card of the same group.
       transparent - the TS is used, no processing, it is sent
                directly to the ML card the VC-PBX/T1,(E1) is
                linked to."
      ::= { prtExVcPbxTsEntry 5}

prtExVcPbxTsIConSlot OBJECT-TYPE
      SYNTAX  INTEGER
       {
       noConnect (2),
          io1       (5),
          io2       (6),
          io3       (7),
          io4       (8),
          io5       (9),
          io6      (10),
          io7      (11),
          io8      (12),
          io9      (13),
          io10     (14),
          io11     (15),
          io12     (16)
       }
      MAX-ACCESS  read-write
      STATUS  current
      DESCRIPTION
      "The object's io1..io12 values are applicable only when
       prtExVcPbxTsMode=compressed. Otherwise, its value should be
       noConnect.
       This object indicates whether the specified compressed
       time slot is connected/routed internally in the Agent and
       to which card it is connected.
       The valid selectable slots are either the current one,
    (prtExVcPbxTsSltIdx), or a slot containing a VC-PBX card.
       In the ?004 Unit the entries io6(10)..io12(16) are not valid."
      ::= {prtExVcPbxTsEntry 6}

prtExVcPbxTsIConPrt OBJECT-TYPE
      SYNTAX  INTEGER
       {
          noConnect (100),

       inPrt1  (101) ,
       inPrt2  (102) ,
       inPrt3  (103) ,
       inPrt4  (104) ,
       inPrt5  (105) ,
          inPrt6  (106)
       }
      MAX-ACCESS  read-write
      STATUS  current
      DESCRIPTION
      "This attribute indicates the internal VC-PBX port to which
       this PABX TS is connected for compression.
       noConnect - when prtExVcPbxTsIConSlot=noConnect."
      ::= {prtExVcPbxTsEntry 7}

-- The following tables contains information specific to
-- the isdn access modules

prtIsdnCnfgTable OBJECT-TYPE
      SYNTAX SEQUENCE OF PrtIsdnCnfgEntry
      MAX-ACCESS not-accessible
      STATUS  current
      DESCRIPTION
       "The write operation into the table objects is valid only
        to the TmpCnfg entry."
      ::= { prtIsdnCnfg 1}

prtIsdnCnfgEntry OBJECT-TYPE
      SYNTAX PrtIsdnCnfgEntry
      MAX-ACCESS not-accessible
      STATUS current
	DESCRIPTION  "An entry in table."
	INDEX {prtIsdnCnfgIdx, prtIsdnSltIdx, prtIsdnPrtIdx}
      ::= { prtIsdnCnfgTable 1}

PrtIsdnCnfgEntry ::=
      SEQUENCE {
      prtIsdnCnfgIdx           Integer32,
      prtIsdnSltIdx            INTEGER,
      prtIsdnPrtIdx            Integer32,
      prtIsdnConnect           INTEGER,
      prtIsdnSignalingProtocol      INTEGER,
      prtIsdnBasicRateLineTopology  INTEGER,
      prtIsdnMode              INTEGER,
      prtIsdnFilter            INTEGER,
      prtIsdnSimultaneousCall  INTEGER,
      prtIsdnNumOfAbstractTerm Integer32,
      prtIsdnSwitchMode        INTEGER,
	  prtIsdnAbSide            INTEGER,
	  prtIsdnQsigRole          INTEGER,
	  prtIsdnInterface         INTEGER,
	  prtIsdnCallMode          INTEGER,
	  prtIsdnCallBackTimeout   INTEGER
        }

prtIsdnCnfgIdx OBJECT-TYPE
      SYNTAX  Integer32  (1..255)
      MAX-ACCESS  read-only
      STATUS  current
      DESCRIPTION
      "This attribute indicates the Idx of the Cnfg (1..100) being
       accessed.
       Idx 255 relates to the TmpCnfg. "
      ::= { prtIsdnCnfgEntry 1}

prtIsdnSltIdx OBJECT-TYPE
      SYNTAX  INTEGER
            {
              io1  (5),
              io2  (6),
              io3  (7),
              io4  (8),
              io5  (9),
              io6 (10),
              io7 (11),
              io8 (12),
              io9 (13),
              io10(14),
              io11(15),
              io12(16),
              kmxMlA (103),
              kmxMlB (104),
              notApplicable(255)
            }
      MAX-ACCESS  read-only
      STATUS  current
      DESCRIPTION
      "This attribute indicates a unique  slot  position where
       the card is inserted.
       In the ?004 Unit the entries io6(10)..io12(16) are not valid
       For KM2100/4 Valid entries are 'kmxMlA ' or 'kmxMlB'"
      ::= { prtIsdnCnfgEntry 2}

prtIsdnPrtIdx OBJECT-TYPE
      SYNTAX  Integer32
      MAX-ACCESS  read-only
      STATUS  current
      DESCRIPTION
      "This attribute indicates a unique  port number.
       For MAXcess the values will be:
          exPrt1(1),
          exPrt2(2),
          exPrt3(3),
          exPrt4(4),
       For KM-2100 the port index is calculated as follows:
       100*Slot+Ch"
       ::= { prtIsdnCnfgEntry 3}

prtIsdnConnect OBJECT-TYPE
      SYNTAX  INTEGER { no(2), yes(3) }
      MAX-ACCESS  read-write
      STATUS  current
      DESCRIPTION
      "This attribute indicates if the port is connected."
      ::= { prtIsdnCnfgEntry 4 }

prtIsdnSignalingProtocol OBJECT-TYPE
      SYNTAX  INTEGER
      {
        other(1), etsi(3), ess5(6), dms100(7), ni1(9),
        ni2(10), ins64(17), ins1500(18), qsig(21),
        notApplicable(255)
      }
      MAX-ACCESS  read-write
      STATUS  current
      DESCRIPTION
      "This attribute fixes which signaling protocol
        is used at this port (D-Channel).
        It is equivalent to isdnSignalingProtocol
        in the isdn MIB."
      DEFVAL { etsi }
      ::= { prtIsdnCnfgEntry 5 }

prtIsdnBasicRateLineTopology OBJECT-TYPE
      SYNTAX  INTEGER
      {
        pointToPoint(1),
        pointToMultipoint(2),
        notApplicable(255)
      }
      MAX-ACCESS  read-write
      STATUS  current
      DESCRIPTION
      "This attribute is relevant for ISDN BRI only.
        It is equivalent to isdnBasicRateLineTopology
        in the isdn MIB."
      ::= { prtIsdnCnfgEntry 6 }

prtIsdnMode OBJECT-TYPE
      SYNTAX  INTEGER
      {
        dialup(1),
        leased(2),
		syncLeased(3),
        notApplicable(255)
      }
      MAX-ACCESS  read-write
      STATUS  current
      DESCRIPTION
      "This attribute allows the user to configure the port as
       leased(2) in case of connection to a TDM network."
      ::= { prtIsdnCnfgEntry 7}

prtIsdnFilter OBJECT-TYPE
      SYNTAX  INTEGER
      { notApplicable(1),
        answerAll(2),
        rejectAll(3),
        selective(4),
		callBack (5)
      }
      MAX-ACCESS  read-write
      STATUS  current
      DESCRIPTION
      "This attribute allows the user to configure the port:
       answerAll(2): accept all incoming calls,
       rejectAll(3): reject all incoming calls,
       selective(4): accept or reject according directory table.
       callBack (5): In this mode the ISDN Ch will reject incoming calls
       and will initiate call back to the rejected phone number."
      ::= { prtIsdnCnfgEntry 8}

prtIsdnSimultaneousCall OBJECT-TYPE
      SYNTAX  INTEGER
      { notApplicable(1),
 accept(2), reject(3) }
      MAX-ACCESS  read-write
      STATUS  current
      DESCRIPTION
      "In case of simultaneous call (local,remote and remote,local):
       accept(2): accept the incoming call,
       reject(3): reject the incoming call."
      ::= { prtIsdnCnfgEntry 9}

prtIsdnNumOfAbstractTerm OBJECT-TYPE
      SYNTAX  Integer32
      MAX-ACCESS  read-write
      STATUS  current
      DESCRIPTION
      "An object for KM2100/4 agents.
    255=Not Applicable
       When ISDN Standard = ETSI or NTT (European) the value should be 255 (NotApplicable)
       else If ML speed is 64Kbps value should be 1.
       If ML speed is 128Kbps value can be either 1 or 2 (user selection)."
      ::= { prtIsdnCnfgEntry 10}

prtIsdnSwitchMode OBJECT-TYPE
      SYNTAX  INTEGER
      {
        notApplicable(1),
        auto   (2),
        manual (3),
		connect(4)
      }
      MAX-ACCESS  read-write
      STATUS  current
      DESCRIPTION
      "For KM2100.
       auto   - The call is initiated automatically by one of the IO cards connected
                to KML.10(ISDN card) having ISDN Switch Mode.
       manual - The call is initiated by the user manually,  for KML.10
                having ISDN Switch Mode (via mdlSCmd).
       connect- The call is initiated 'immediately', for KML.10 having ISDN Switch Mode.
                'immediately'- means: immediately after power-up (when product performed
                                      Reset) OR, since this value appears in the active
                 					  configuration.
                In this case, the call can be disconnected only by power-off of the
                product or by changing this object to another value (or actual Remove
                of the KML.10 relevant card).
       notApplicable - For other card types."
      ::= { prtIsdnCnfgEntry 11}

prtIsdnAbSide OBJECT-TYPE
      SYNTAX  INTEGER
      {
        notApplicable(1),
        aSide (2),
        bSide (3)
      }
      MAX-ACCESS  read-write
      STATUS  current
      DESCRIPTION
      "This parameter indicates the QSIG side in layer 3.
       This definition is from the QSIG Standard."
      ::= { prtIsdnCnfgEntry 12}

prtIsdnQsigRole OBJECT-TYPE
      SYNTAX  INTEGER
      {
        notApplicable(1),
        slave    (2),
        master   (3)
      }
      MAX-ACCESS  read-write
      STATUS  current
      DESCRIPTION
      "This parameter indicates the QSIG side in layer 1 & 2."
      ::= { prtIsdnCnfgEntry 13}

prtIsdnInterface  OBJECT-TYPE
      SYNTAX  INTEGER
       {
       lt   (1),
       nt   (2),
       te   (3),
       notApplicable (255)
       }
      MAX-ACCESS  read-write
      STATUS  current
      DESCRIPTION
      "It indicates the interface type:
       lt = line termination
       nt = network termination
       te = terminal equipment."
      ::= { prtIsdnCnfgEntry 14}

prtIsdnCallMode     OBJECT-TYPE
      SYNTAX  INTEGER  { 
                 notApplicable(1), 
                 initiate     (2), 
                 listen       (3) 
                 }
      MAX-ACCESS  read-write
      STATUS  current
      DESCRIPTION
      "This object indicates the acceptance of incoming calls.
       Initiate - Callout
       Listen   - Callin. "
      ::= { prtIsdnCnfgEntry 15}


prtIsdnCallBackTimeout  OBJECT-TYPE
      SYNTAX  INTEGER 
      MAX-ACCESS  read-write
      STATUS  current
      DESCRIPTION
      "This object is applicable only if 'prtIsdnFilter' is 'CallBack'
       and determines how long to wait from receiving the incoming call
       until initiating the call back call.
       The vaules range should be '1..20 sec' and the default 10 sec."
      ::= { prtIsdnCnfgEntry 16}



prtIsdnEndpointTable OBJECT-TYPE
      SYNTAX SEQUENCE OF PrtIsdnEndpointEntry
      MAX-ACCESS not-accessible
      STATUS  current
      DESCRIPTION
       "The write operation into the table objects is valid only
        to the TmpCnfg entry."
      ::= { prtIsdnCnfg 2}

prtIsdnEndpointEntry OBJECT-TYPE
      SYNTAX PrtIsdnEndpointEntry
      MAX-ACCESS not-accessible
      STATUS current
	DESCRIPTION  "An entry in table."
	INDEX {prtIsdnEndpointCnfgIdx, prtIsdnEndpointSltIdx,
        prtIsdnEndpointPrtIdx, prtIsdnEndpointIdx }
      ::= { prtIsdnEndpointTable 1}

PrtIsdnEndpointEntry ::=
      SEQUENCE {
      prtIsdnEndpointCnfgIdx        Integer32,
      prtIsdnEndpointSltIdx         INTEGER,
      prtIsdnEndpointPrtIdx         Integer32,
      prtIsdnEndpointIdx            INTEGER,
      prtIsdnEndpointTeiType        INTEGER,
      prtIsdnEndpointTeiValue       Integer32,
      prtIsdnEndpointSpid           DisplayString,
	  prtIsdnEndpointBearerCh       INTEGER,
      prtIsdnEndpointRowStatus      RowStatus
        }

prtIsdnEndpointCnfgIdx OBJECT-TYPE
      SYNTAX  Integer32  (1..255)
      MAX-ACCESS  read-only
      STATUS  current
      DESCRIPTION
      "This attribute indicates the Idx of the Cnfg (1..100) being
       accessed.
       Idx 255 relates to the TmpCnfg. "
      ::= { prtIsdnEndpointEntry 1}

prtIsdnEndpointSltIdx OBJECT-TYPE
      SYNTAX  INTEGER
            {
              io1(5),
              io2(6),
              io3(7),
              io4(8),
              io5(9),
              io6(10),
              io7(11),
              io8(12),
              io9(13),
              io10(14),
              io11(15),
              io12(16),
              kmxMlA (103),
              kmxMlB (104),
              notApplicable(255)
            }
      MAX-ACCESS  read-only
      STATUS  current
      DESCRIPTION
      "This attribute indicates a unique  slot  position where
       the card is inserted.
       In ?004 Unit the entries io6(10)..io12(16) are not valid
       For KM2100/4 Valid entries are 'kmxMlA ' or 'kmxMlB'"
      ::= { prtIsdnEndpointEntry 2}

prtIsdnEndpointPrtIdx OBJECT-TYPE
        SYNTAX  Integer32
        MAX-ACCESS read-only
        STATUS current
        DESCRIPTION
       "This attribute indicates a unique  port number.
         For MAXcess the values will be:
          exPrt1(1),
          exPrt2(2),
          exPrt3(3),
          exPrt4(4),
         For KM-2100 the port index is calculated as follows:
         100*Slot+Ch"
       ::= { prtIsdnEndpointEntry 3}

prtIsdnEndpointIdx OBJECT-TYPE
        SYNTAX  INTEGER { atei1(1), atei2(2) }
        MAX-ACCESS read-only
        STATUS current
        DESCRIPTION
        "Since more than one endpoint may be defined per
        isdn entity, this field is a simple index.
        It corresponds to isdnEndpointIdx in the isdn MIB."
         DEFVAL { atei1 }
        ::= { prtIsdnEndpointEntry 4}

prtIsdnEndpointTeiType OBJECT-TYPE
        SYNTAX  INTEGER { dynamic(1), static(2), notApplicable(255) }
        MAX-ACCESS read-create
        STATUS current
        DESCRIPTION
        "The type of TEI (Terminal Endpoint Identifier)
             used for this Terminal Endpoint. In case of dynamic(1),
             the TEI value is selected by the switch. In
             case of static(2), a valid TEI value has to be
             entered in the isdnEndpointTeiValue object.
             interface type as well as the Terminal Endpoint type.
             static(2). On Basic Rate interfaces the default value
             is dynamic(1) for isdn(63) Terminal Endpoints.
        It corresponds to isdnEndpointTeiType in the isdn MIB."
        ::= { prtIsdnEndpointEntry 5}

prtIsdnEndpointTeiValue OBJECT-TYPE
        SYNTAX  Integer32
        MAX-ACCESS read-create
        STATUS current
        DESCRIPTION
        "When the TEI Type is static, the value of the TEI should be
         between 0 and 63. Else, it is not selectable by user.
		 255 = notApplicable.
         It corresponds to isdnEndpointTeiValue in the isdn MIB"
        ::= { prtIsdnEndpointEntry 6 }

prtIsdnEndpointSpid OBJECT-TYPE
        SYNTAX  DisplayString
        MAX-ACCESS read-create
        STATUS current
        DESCRIPTION
        "The Service profile IDentifier (SPID) information
         for this Terminal Endpoint. It is is composed of
         9-20 numeric characters.
        It corresponds to isdnEndpointSpid in the isdn MIB."
        ::= { prtIsdnEndpointEntry 7 }

prtIsdnEndpointBearerCh OBJECT-TYPE
        SYNTAX  INTEGER {
                notApplicable(1),
                anyChannel (2),
                channelB1  (3),
                channelB2  (4) }
        MAX-ACCESS read-create
        STATUS current
        DESCRIPTION
        "This is the selected dialing channel.
         anyChannel - the system selects the dialing channel."
        ::= { prtIsdnEndpointEntry 8}

prtIsdnEndpointRowStatus OBJECT-TYPE
        SYNTAX  RowStatus
        MAX-ACCESS read-create
        STATUS current
        DESCRIPTION
        "This field indicates whether to consider this endpoint or not.
         The only possible supported RowStatus vaules are
         active (1) and destroy (6)."
        ::= { prtIsdnEndpointEntry 9}

prtIsdnDirectoryTable OBJECT-TYPE
      SYNTAX SEQUENCE OF PrtIsdnDirectoryEntry
      MAX-ACCESS not-accessible
      STATUS  current
      DESCRIPTION
       "The write operation into the table objects is valid only
        to the TmpCnfg entry."
      ::= { prtIsdnCnfg 3}

prtIsdnDirectoryEntry OBJECT-TYPE
      SYNTAX PrtIsdnDirectoryEntry
      MAX-ACCESS not-accessible
      STATUS current
	DESCRIPTION  "An entry in table."
	INDEX { prtIsdnDirectoryCnfgIdx, prtIsdnDirectorySltIdx, prtIsdnDirectoryPrtIdx }
      ::= { prtIsdnDirectoryTable 1}

PrtIsdnDirectoryEntry ::=
      SEQUENCE {
      prtIsdnDirectoryCnfgIdx   Integer32,
      prtIsdnDirectorySltIdx         INTEGER,
      prtIsdnDirectoryPrtIdx         Integer32,
      prtIsdnDirectoryLocalAddr    DisplayString,
      prtIsdnDirectoryLocalSubAddr   DisplayString,
      prtIsdnDirectoryRemoteAddr    DisplayString,
      prtIsdnDirectoryRemoteSubAddr  DisplayString,
      prtIsdnDirectoryPrtNu          Integer32,
      prtIsdnDirectoryTeiId          Integer32,
      prtIsdnDirectoryRowStatus      RowStatus,
      prtIsdnDirectoryLocalAddr2     DisplayString,
      prtIsdnDirectoryLocalSubAddr2  DisplayString,
      prtIsdnDirectoryRemoteAddr2    DisplayString,
      prtIsdnDirectoryRemoteSubAddr2 DisplayString
      }

prtIsdnDirectoryCnfgIdx OBJECT-TYPE
      SYNTAX  Integer32  (1..255)
      MAX-ACCESS  read-only
      STATUS  current
      DESCRIPTION
      "This attribute indicates the Idx of the Cnfg (1..100) being
       accessed.
       Idx 255 relates to the TmpCnfg. "
      ::= { prtIsdnDirectoryEntry 1}

prtIsdnDirectorySltIdx OBJECT-TYPE
      SYNTAX  INTEGER
            {
              io1(5),
              io2(6),
              io3(7),
              io4(8),
              io5(9),
              io6(10),
              io7(11),
              io8(12),
              io9(13),
              io10(14),
              io11(15),
              io12(16),
              kmxMlA (103),
              kmxMlB (104),
			  notApplicable (255)
            }
      MAX-ACCESS  read-only
      STATUS  current
      DESCRIPTION
      "This attribute indicates a unique  slot  position where
       the card is inserted.
       For MX300/30 ports:
       io1(5) = isdn1(5) and io2(6) = isdn2(6).
       In ?004 Unit the entries io6(10)..io12(16) are not valid
       For KM2100/4 Valid entries are 'kmxMlA ' or 'kmxMlB'"
      ::= { prtIsdnDirectoryEntry 2}

prtIsdnDirectoryPrtIdx OBJECT-TYPE
        SYNTAX  Integer32
        MAX-ACCESS read-only
        STATUS current
        DESCRIPTION
        "For MAXcess this is the internal port number: 101, 102,....
         For KM-2100 the port index is calculated as follows:
         100*Slot+Ch"
        ::= { prtIsdnDirectoryEntry 3}

prtIsdnDirectoryLocalAddr OBJECT-TYPE
        SYNTAX DisplayString (SIZE(17..20))
        MAX-ACCESS read-create
        STATUS current
        DESCRIPTION
        "This is the local address associated with this
         entry.
         - For MX: Size=17 , Default=0	(17 characters)
         - For KM: Size=20, Default=blank (20 characters) "
        ::= { prtIsdnDirectoryEntry 4}

prtIsdnDirectoryLocalSubAddr OBJECT-TYPE
        SYNTAX DisplayString (SIZE(4..6))
        MAX-ACCESS read-create
        STATUS current
        DESCRIPTION
        "This is the local subaddress associated with this
         entry.
         - For MX: Size=6 , Default=0	(6 characters)
         - For KM: Size=4 , Default=blank (4 characters)"
        ::= { prtIsdnDirectoryEntry 5}

prtIsdnDirectoryRemoteAddr OBJECT-TYPE
        SYNTAX DisplayString (SIZE(17..20))
        MAX-ACCESS read-create
        STATUS current
        DESCRIPTION
        "This is the remote address associated with this
         entry.
         - For MX: Size=17 , Default=0	(17 characters)
         - For KM: Size=20, Default=blank (20 characters)"
        ::= { prtIsdnDirectoryEntry 6}

prtIsdnDirectoryRemoteSubAddr OBJECT-TYPE
        SYNTAX  DisplayString (SIZE(4..6))
        MAX-ACCESS read-create
        STATUS current
        DESCRIPTION
        "This is the remote subaddress associated with this
         entry.
         - For MX: Size=6 , Default=0 (6 characters)
         - For KM: Size=4 , Default=blank (4 characters)"
        ::= { prtIsdnDirectoryEntry 7}


prtIsdnDirectoryPrtNu OBJECT-TYPE
        SYNTAX  Integer32
        MAX-ACCESS read-create
        STATUS current
        DESCRIPTION
        "This is the external port number connected to
         this entry."
         DEFVAL { 1 }
        ::= { prtIsdnDirectoryEntry 8}

prtIsdnDirectoryTeiId OBJECT-TYPE
        SYNTAX  Integer32
        MAX-ACCESS read-create
        STATUS current
        DESCRIPTION
        "This is the abstract terminal id if relevant,
        connected to this entry."
        DEFVAL { 1 }
        ::= { prtIsdnDirectoryEntry 9}

prtIsdnDirectoryRowStatus OBJECT-TYPE
        SYNTAX  RowStatus
        MAX-ACCESS read-create
        STATUS current
        DESCRIPTION
        "This is the status for the row. It allows to know
        whether to consider this row or not.
        The only possible supported RowStatus vaules are
        active (1) and destroy (6)."
        ::= { prtIsdnDirectoryEntry 10}

prtIsdnDirectoryLocalAddr2 OBJECT-TYPE
        SYNTAX DisplayString (SIZE(17..20))
        MAX-ACCESS read-create
        STATUS current
        DESCRIPTION
        "This is the second local address associated with this
         entry.
         - For MX: Size=17 , Default=0 (17 characters)
         - For KM: Size=20, Default=blank (20 characters)"
        ::= { prtIsdnDirectoryEntry 11}

prtIsdnDirectoryLocalSubAddr2 OBJECT-TYPE
        SYNTAX DisplayString (SIZE(4..6))
        MAX-ACCESS read-create
        STATUS current
        DESCRIPTION
        "This is the second local subaddress associated with this
         entry.
         - For MX: Size=6 , Default=0 (6 characters)
         - For KM: Size=4 , Default=blank (4 characters)"
        ::= { prtIsdnDirectoryEntry 12}

prtIsdnDirectoryRemoteAddr2 OBJECT-TYPE
        SYNTAX DisplayString (SIZE(17..20))
        MAX-ACCESS read-create
        STATUS current
        DESCRIPTION
        "This is the second remote address associated with this
         entry.
         - For MX: Size=17 , Default=0 (17 characters)
         - For KM: Size=20, Default=blank(20 characters) "
        ::= { prtIsdnDirectoryEntry 13}

prtIsdnDirectoryRemoteSubAddr2 OBJECT-TYPE
        SYNTAX  DisplayString (SIZE(4..6))
        MAX-ACCESS read-create
        STATUS current
        DESCRIPTION
        "This is the second remote subaddress associated with this
         entry.
         - For MX: Size=6 , Default=0 (6 characters)
         - For KM: Size=4 , Default=blank (4 characters) "
        ::= { prtIsdnDirectoryEntry 14}



-- This table is an extension for new version of MAXcess
-- modules.
prtFrPlusCnfgTable  OBJECT-TYPE
     SYNTAX SEQUENCE OF PrtFrPlusCnfgEntry
     MAX-ACCESS not-accessible
     STATUS  current
     DESCRIPTION
      "The write operation into the Table Objects is valid only
       to the TmpCnfg entry."
     ::= {prtFrPlusCnfg 1}

prtFrPlusCnfgEntry OBJECT-TYPE
      SYNTAX PrtFrPlusCnfgEntry
      MAX-ACCESS not-accessible
      STATUS current
	DESCRIPTION  "An entry in table."
	INDEX {prtFrPlusCnfgIdx, prtFrPlusSltIdx, prtFrPlusPrtIdx }
      ::= { prtFrPlusCnfgTable 1}

PrtFrPlusCnfgEntry ::=
      SEQUENCE {
      prtFrPlusCnfgIdx   Integer32,
      prtFrPlusSltIdx    INTEGER,
      prtFrPlusPrtIdx   Integer32,
      prtFrPlusNotSegmentedPriorities  OCTET STRING
}

prtFrPlusCnfgIdx OBJECT-TYPE
      SYNTAX  Integer32 (1..255)
      MAX-ACCESS  read-only
      STATUS  current
      DESCRIPTION
      "This attribute indicates the Idx of the Cnfg (1..100) being
       accessed.
       Idx 255 relates to the TmpCnfg. "
      ::= { prtFrPlusCnfgEntry 1}

prtFrPlusSltIdx OBJECT-TYPE
      SYNTAX  INTEGER
            {
              io1   (5),
              io2   (6),
              io3   (7),
              io4   (8),
              io5   (9),
              io6  (10),
              io7  (11),
              io8  (12),
              io9  (13),
              io10 (14),
              io11 (15),
              io12 (16),
       notApplicable(255)
            }
      MAX-ACCESS  read-only
      STATUS  current
      DESCRIPTION
        "Slot Index.
         For ISDN BRI Ports of MX300/30,
    io1(5) = isdn1(5) and io2(6) = isdn2(6)."
      ::= { prtFrPlusCnfgEntry 2}

prtFrPlusPrtIdx  OBJECT-TYPE
      SYNTAX  Integer32
      MAX-ACCESS  read-only
      STATUS  current
      DESCRIPTION
      "This attribute indicates a unique  port number.
       This port number should be:
       - for ISDN cards: inPrt1(101)->inPrt50(150)
       - for MHS1 card : exPrt1(1)
       - for MHS3, MLS3 cards: exPrt1(1)->exPrt3(3)
       - for MLS6 cards: exPrt1(1)->exPrt6(6)."
      ::= { prtFrPlusCnfgEntry 3}

prtFrPlusNotSegmentedPriorities OBJECT-TYPE
       SYNTAX OCTET STRING(SIZE(1))
       MAX-ACCESS   read-write
       STATUS   current
       DESCRIPTION
      "This parameter is relevant only for FR+ protocol and
       asks the MXcess NOT to segment data with specified
       priorities:  from LSB:
       bit 1  is for priority 1,
       bit 2  is for priority 2, .... till bit 7 for priority 7.
	   - a priority selected to be segmented : its bit will be '0'
	   - a priority not to be segmented : its bit will be '1'
       Default is 00000000; i.e, segment all priorities."
     DEFVAL { '00'H }
     ::= { prtFrPlusCnfgEntry 4 }


-- This table is an extension of prtExPh1MlCnfgTable for MTML-4 cards
-- of MP-2200

    prtMl4CnfgTable  OBJECT-TYPE
     SYNTAX SEQUENCE OF PrtMl4CnfgEntry
     MAX-ACCESS not-accessible
     STATUS  current
     DESCRIPTION
      "This is an extension table for MTML-4 card parameters."
     ::= {prtMl4Cnfg 1}

prtMl4CnfgEntry OBJECT-TYPE
      SYNTAX PrtMl4CnfgEntry
      MAX-ACCESS not-accessible
      STATUS current
	DESCRIPTION  "An entry in table."
	INDEX {prtMl4CnfgIdx, prtMl4SltIdx, prtMl4PrtIdx }
      ::= { prtMl4CnfgTable 1}

PrtMl4CnfgEntry ::=
      SEQUENCE {
      prtMl4CnfgIdx        Integer32,
      prtMl4SltIdx         INTEGER,
      prtMl4PrtIdx         INTEGER,
      prtMl4SigProfile     INTEGER,
      prtMl4CGA            INTEGER,
      prtMl4Oos            INTEGER,
      prtMl4VoiceOos  OCTET STRING,
      prtMl4DataOos   OCTET STRING,
	  prtMl4Service        INTEGER,
	  prtMl4IpAddress      IpAddress,
	  prtMl4IpMask         IpAddress,
	  prtMl4SignalingMode  INTEGER,
	  prtMl4EchoCanceler   INTEGER,
	  prtMl4OosErrorSource INTEGER,
	  prtMl4OosEntryThreshold Integer32,
	  prtMl4OosExitThreshold  Integer32
      }


prtMl4CnfgIdx OBJECT-TYPE
      SYNTAX  Integer32 (1..255)
      MAX-ACCESS  read-only
      STATUS  current
      DESCRIPTION
      "This attribute indicates the Idx of the Cnfg (1..100) being
       accessed.
       Idx 255 relates to the TmpCnfg. The write operation is valid only
       to the TmpCnfg."
      ::= { prtMl4CnfgEntry 1}

prtMl4SltIdx OBJECT-TYPE
      SYNTAX  INTEGER
     {
	   notApplicable (1),
       io1   (5),
       io2   (6),
       io3   (7),
       io4   (8),
       io5   (9),
       io6  (10),
       io7  (11),
       io8  (12),
       io9  (13),
       io10 (14),
       io11 (15),
       io12 (16)
     }
      MAX-ACCESS  read-only
      STATUS  current
      DESCRIPTION
      "This attribute indicates a unique  slot  position where
       the module is inserted."
      ::= { prtMl4CnfgEntry 2}

prtMl4PrtIdx OBJECT-TYPE
      SYNTAX  INTEGER
       {
       exPrt1    (1),
       exPrt2    (2),
       exPrt3    (3),
       exPrt4    (4),
       inPrt1  (101),
       inPrt2  (102),
       inPrt3  (103),
       inPrt4  (104)
       }
      MAX-ACCESS  read-only
      STATUS  current
      DESCRIPTION
      "This attribute indicates a unique  port number."
      ::= { prtMl4CnfgEntry 3}

prtMl4SigProfile OBJECT-TYPE
      SYNTAX  INTEGER
       {
       notApplicable (1),
       none          (2),
       p1            (3),
       p2            (4),
       p3            (5),
       p4            (6),
       p5            (7)
       }
      MAX-ACCESS  read-write
      STATUS  current
      DESCRIPTION
      "This object indicates the Signaling Profile of the port.
       none - when the Frame is G732N (no MF).
       p1  = profile 1
       p2  = profile 2
       p3  = profile 3
       p4  = profile 4
       p5  = profile 5 "
	  ::= {prtMl4CnfgEntry 4}

prtMl4CGA OBJECT-TYPE
    SYNTAX  INTEGER {
      none (1),
      trans(2),
      full (3)
            }
    MAX-ACCESS  read-write
    STATUS  current
    DESCRIPTION
    "This object selects the method used to signal the CGA state
     to the other end, through the main link.
     'none'  - non-transparent mode. When one of the links
               (main) will be in Out Of Service state, both
               'Data/Voice Oos' and 'Oos' will be
               transmitted to the other end.
     'trans' - when one of the links (main) will be in Out
               Of Service state, 'Data/Voice Oos' will be
               transmitted to the other end.
     'full'  - fully-transparent mode. When one of the links
                  (main) will be in Out Of Service state,
                  neither 'Data/Voice Oos' nor 'Oos' will
                  be transmitted to the other end."
 ::= { prtMl4CnfgEntry 5 }

prtMl4Oos  OBJECT-TYPE
      SYNTAX  INTEGER
       {
        notSupported  (2),
        forcedIdle    (3),
        forcedBusy    (4),
        busyIdle      (5),
        idleBusy      (6)
       }
      MAX-ACCESS  read-write
      STATUS  current
      DESCRIPTION
      "'idle' = '0' = on-hook, idle state
       'busy' = '1' = off-hook, busy state
       'forcedIdle' = SP = both A and B signaling bits are forced
                      to '0' during out-of-service periods.
       'forcedBusy' = MK = both A and B signaling bits are forced
                      to '1' during out-of-service periods.
       'busyIdle'   = MK_SP = A and B bits are forced to '1' for
                      2.5 seconds; then they are switched to '0'
                      until out-of-service condition disappears.
       'idleBusy'   = SP_MK = A and B bits are forced to '0' for
                      2.5 seconds; then they are switched to '1'
                      until out-of-service condition disappears.
       - for T1:    '0'=0   ;  '1'=1
       - for E1:    '0'=1   ;  '1'=0   "
   ::= { prtMl4CnfgEntry 6 }

prtMl4VoiceOos  OBJECT-TYPE
 SYNTAX  OCTET STRING (SIZE (0..4))
    MAX-ACCESS  read-write
    STATUS  current
    DESCRIPTION
    "Voice Out-Of-Service code. Valid range: (0 - FF HEX).
     For agents that do not support this feature, the value will
     always be 0."
   ::= { prtMl4CnfgEntry 7 }

prtMl4DataOos  OBJECT-TYPE
 SYNTAX  OCTET STRING (SIZE (0..4))
    MAX-ACCESS  read-write
    STATUS  current
    DESCRIPTION
    "Data Out-Of-Service code. Valid range: (0 - FF HEX).
     For agents that do not support this feature, the value will
     always be 0."
   ::= { prtMl4CnfgEntry 8 }

prtMl4Service OBJECT-TYPE
      SYNTAX  INTEGER
       {
       notApplicable (1),
       leasedLine    (2),
       v51           (3)
       }
      MAX-ACCESS  read-write
      STATUS  current
      DESCRIPTION
      "Link Service.
       leasedLine - usual TDM interface.
       v51        - V5.1 interface. "
      ::= {prtMl4CnfgEntry 9}

prtMl4IpAddress OBJECT-TYPE
      SYNTAX  IpAddress
      MAX-ACCESS  read-write
      STATUS  current
      DESCRIPTION
      "IP Address of the port."
      ::= {prtMl4CnfgEntry 10}

prtMl4IpMask OBJECT-TYPE
      SYNTAX  IpAddress
      MAX-ACCESS  read-write
      STATUS  current
      DESCRIPTION
      "IP subnet mask of the port."
      ::= {prtMl4CnfgEntry 11}

prtMl4SignalingMode OBJECT-TYPE
      SYNTAX INTEGER { notApplicable(1),
		cas(2),
		ccs(3),
		robbedBit(4)
		}
      MAX-ACCESS read-write
      STATUS current
      DESCRIPTION
      "Refers to the signaling mode of the Framer module.
      cas(2) means Channel Associated Signaling. Used for E1 Links.
      ccs(3) is the Common Channel Signaling (the signaling is not within
             the channels time slot - a TS for signaling is used).
      robbedBit(4) is a method implementing 7 bits for the voice and 1 bit
                   dedicated for signaling. Used for T1 Links."
      ::= {prtMl4CnfgEntry 12}

prtMl4EchoCanceler OBJECT-TYPE
      SYNTAX  INTEGER
       {
       notApplicable (1),
       off    (2),
       on     (3)
       }
      MAX-ACCESS  read-write
      STATUS  current
      DESCRIPTION
      "Echo canceler activation."
      ::= {prtMl4CnfgEntry 13}

prtMl4OosErrorSource OBJECT-TYPE
      SYNTAX  INTEGER
       {
       notApplicable (1),
       none          (2),
       framing       (3),
	   bpv		     (4)
       }
      MAX-ACCESS  read-write
      STATUS  current
      DESCRIPTION
      "OOS (Out-of-Service) Error Source.
       This object is applicable for T1 ports only."
      ::= {prtMl4CnfgEntry 14}

prtMl4OosEntryThreshold OBJECT-TYPE
      SYNTAX  Integer32 (0..999)
      MAX-ACCESS  read-write
      STATUS  current
      DESCRIPTION
      "This object defines the number of Errors per Second that determine the 
       minimum unacceptable noise level. This value will be the Entry Threshold
       to the OOS (Out-of-Service) state.
       This object is applicable only when prtMl4OosErrorSource=framing(3) or bpv(4).
       0=notApplicable."
      ::= { prtMl4CnfgEntry 15}

prtMl4OosExitThreshold OBJECT-TYPE
      SYNTAX  Integer32 (0..99)
      MAX-ACCESS  read-write
      STATUS  current
      DESCRIPTION
      "This object defines the number of consecutive Error-Free-Seconds before
       going from OOS state to Normal state. This value will be the Exit Threshold
       from the OOS (Out-of-Service) state.
	   Units=seconds
       This object is applicable only when prtMl4OosErrorSource=framing(3) or bpv(4).
       0=notApplicable."
      ::= { prtMl4CnfgEntry 16}


--prtAcmCnfgTable defines the parameters of the
--ACM cards family external ports 1-8

prtAcmCnfgTable  OBJECT-TYPE
     SYNTAX SEQUENCE OF PrtAcmCnfgEntry
     MAX-ACCESS not-accessible
     STATUS  current
     DESCRIPTION
      "This is a table for ACM port parameters."
     ::= {prtAcmCnfg 1}

prtAcmCnfgEntry OBJECT-TYPE
      SYNTAX PrtAcmCnfgEntry
      MAX-ACCESS not-accessible
      STATUS current
	DESCRIPTION  "An entry in table."
	INDEX {prtAcmCnfgIdx, prtAcmSltIdx, prtAcmPrtIdx }
      ::= { prtAcmCnfgTable 1}

PrtAcmCnfgEntry ::=
      SEQUENCE {
      prtAcmCnfgIdx        Integer32,
      prtAcmSltIdx         INTEGER,
      prtAcmPrtIdx         INTEGER,
      prtAcmConnect        INTEGER,
      prtAcmActiveState    INTEGER,
      prtAcmAlrString      DisplayString
      }

prtAcmCnfgIdx OBJECT-TYPE
      SYNTAX  Integer32 (1..255)
      MAX-ACCESS  read-only
      STATUS  current
      DESCRIPTION
      "This attribute indicates the Idx of the Cnfg (1..100) being
       accessed.
       Idx 255 relates to the TmpCnfg. The write operation is valid only
       to the TmpCnfg."
      ::= { prtAcmCnfgEntry 1}

prtAcmSltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      MAX-ACCESS  read-only
      STATUS  current
      DESCRIPTION
      "This attribute indicates a unique  slot  position where
       the module is inserted."
      ::= { prtAcmCnfgEntry 2}

prtAcmPrtIdx OBJECT-TYPE
      SYNTAX  INTEGER
       {
       exPrt1    (1),
       exPrt2    (2),
       exPrt3    (3),
       exPrt4    (4),
       exPrt5    (5),
       exPrt6    (6),
       exPrt7    (7),
       exPrt8    (8) ,
       exPrt9    (9) ,
       exPrt10  (10) ,
       exPrt11  (11) ,
       exPrt12  (12)
       }
      MAX-ACCESS  read-only
      STATUS  current
      DESCRIPTION
      "This attribute indicates a unique  port number."
      ::= { prtAcmCnfgEntry 3}

prtAcmConnect OBJECT-TYPE
      SYNTAX  INTEGER
              {
                no  (2),
                yes (3)
              }
      MAX-ACCESS  read-write
      STATUS  current
      DESCRIPTION
      "This attribute indicates whether the port should be
       connected or not. Only a connected port can perform activity."
      ::= {prtAcmCnfgEntry 4}

prtAcmActiveState OBJECT-TYPE
      SYNTAX  INTEGER
              {
                low  (2),
                high (3)
              }
      MAX-ACCESS  read-write
      STATUS  current
      DESCRIPTION
      "This attribute indicates the Electric Active State of the port."
      ::= {prtAcmCnfgEntry 5}

prtAcmAlrString OBJECT-TYPE
        SYNTAX DisplayString (SIZE(0..35))
        MAX-ACCESS read-write
        STATUS current
        DESCRIPTION
        "Alarm string selected by user for the Inbound ports.
         This object is applicable only for the Inbound Ports: ext-5..ext-12.
         For the Outbound Ports (ext-1..ext-4), the size of this string will be 0."
      ::= {prtAcmCnfgEntry 6}

--prtE2CnfgTable defines the parameters of the
--E2 card ports 

prtE2CnfgTable  OBJECT-TYPE
     SYNTAX SEQUENCE OF PrtE2CnfgEntry
     MAX-ACCESS not-accessible
     STATUS  current
     DESCRIPTION
      "This is a table for E2 port parameters."
     ::= {prtE2Cnfg 1}

prtE2CnfgEntry OBJECT-TYPE
      SYNTAX PrtE2CnfgEntry
      MAX-ACCESS not-accessible
      STATUS current
	DESCRIPTION  "An entry in table."
	INDEX {prtE2CnfgIdx, prtE2SltIdx, prtE2PrtIdx }
      ::= { prtE2CnfgTable 1}

PrtE2CnfgEntry ::=
      SEQUENCE {
      prtE2CnfgIdx        Integer32,
      prtE2SltIdx         INTEGER,
      prtE2PrtIdx         INTEGER,
      prtE2Connect        INTEGER,
      prtE2MngOnNationalBit INTEGER
      }

prtE2CnfgIdx OBJECT-TYPE
      SYNTAX  Integer32 (1..255)
      MAX-ACCESS  read-only
      STATUS  current
      DESCRIPTION
      "This attribute indicates the Idx of the Cnfg (1..100) being
       accessed.
       Idx 255 relates to the TmpCnfg. The write operation is valid only
       to the TmpCnfg."
      ::= { prtE2CnfgEntry 1}

prtE2SltIdx OBJECT-TYPE
      SYNTAX  INTEGER
     {
       io1   (5),
       io2   (6),
       io3   (7),
       io4   (8),
       io5   (9),
       io6  (10),
       io7  (11),
       io8  (12),
       io9  (13),
       io10 (14),
       io11 (15),
       io12 (16)
     }
      MAX-ACCESS  read-only
      STATUS  current
      DESCRIPTION
      "This attribute indicates a unique  slot  position where
       the module is inserted."
      ::= { prtE2CnfgEntry 2}

prtE2PrtIdx OBJECT-TYPE
      SYNTAX  INTEGER
       {
       exPrt1    (1),
       exPrt2    (2)
       }
      MAX-ACCESS  read-only
      STATUS  current
      DESCRIPTION
      "This attribute indicates a unique  port number."
      ::= { prtE2CnfgEntry 3}

prtE2Connect OBJECT-TYPE
      SYNTAX  INTEGER
              {
                no  (2),
                yes (3)
              }
      MAX-ACCESS  read-write
      STATUS  current
      DESCRIPTION
      "This attribute indicates whether the port should be
       connected or not. Only a connected port can perform activity."
      ::= {prtE2CnfgEntry 4}

prtE2MngOnNationalBit OBJECT-TYPE
      SYNTAX  INTEGER
              {
                no  (2),
                yes (3)
              }
      MAX-ACCESS  read-write
      STATUS  current
      DESCRIPTION
      "This attribute indicates whether National Bit will be used for
       Management or not."
      ::= {prtE2CnfgEntry 5}

--
-- The following table includes the IP addresses of all the NMS to which
-- Traps will be sent
--

--mngTrapIpTable  OBJECT-TYPE
--      SYNTAX  SEQUENCE OF MngTrapIpEntry
--      MAX-ACCESS  not-accessible
--      STATUS current
--      DESCRIPTION
--        "This table indicates  the destination address of the traps.
--         Internally it will be limited to ten addresses. "
--      ::= { agnt 7 }
--
--mngTrapIpEntry OBJECT-TYPE
--      SYNTAX  MngTrapIpEntry
--      MAX-ACCESS  not-accessible
--      STATUS  current
--      INDEX   { mngTrapIpIdx }
--      ::= { mngTrapIpTable 1 }
--
--MngTrapIpEntry  ::=
--      SEQUENCE {
--      mngTrapIpIdx   Integer32,
--      mngTrapIpIP    IpAddress,
--      mngTrapIpIPMask IpAddress
--      }
--
--mngTrapIpIdx OBJECT-TYPE
--      SYNTAX  Integer32
--      MAX-ACCESS  read-only
--      STATUS current
--      DESCRIPTION
--      " This value indicates an index of a specific IP address"
--      ::= { mngTrapIpEntry 1 }
--
--mngTrapIpIP OBJECT-TYPE
--      SYNTAX  IpAddress
--      MAX-ACCESS  read-write
--      STATUS current
--      DESCRIPTION
--      "This value indicates  the  destination addresses of the traps. "
--      ::= { mngTrapIpEntry 2 }
--
--mngTrapIpIPMask OBJECT-TYPE
--      SYNTAX  IpAddress
--      MAX-ACCESS  read-write
--      STATUS current
--      DESCRIPTION
--      "This value indicates  the  mask of the destination addresses of the traps. "
--      ::= { mngTrapIpEntry 3 }
--
--
-- Traps

--NOTIFICATIONS

 muxHubEvents OBJECT-IDENTITY
     STATUS  current
     DESCRIPTION
     "The events for ."
     ::= { muxHub 0 }

 alarmsTrap  NOTIFICATION-TYPE
     OBJECTS       { alrBufDescription }
     STATUS current
     DESCRIPTION
     "This trap is sent whenever alarm occurs in the agent."
     ::= { muxHubEvents 1 }

  sanityTrap  NOTIFICATION-TYPE
     OBJECTS       { agnSSanityCheckStatus, agnCSaveCnfgIdxCmd }
     STATUS current
     DESCRIPTION
     "This trap is sent after a data base update.
      It returns the sanity result status and the configuration no.
      checked.
      If the result is of Flip DB Sanity Check, the configuration
      no. sent will be 0.
      If the result is of Variant Sanity Check, the configuration
      no. sent will be 100."
     ::= { muxHubEvents 2 }

  cnfgFlipTrap  NOTIFICATION-TYPE
     OBJECTS       { agnSActiveCnfg }
     STATUS current
     DESCRIPTION
     "This trap is sent upon change of the active Configuration DB.
      Attached, is the new active Configuration no."
     ::= { muxHubEvents 3 }

  flipDbChangeTrap  NOTIFICATION-TYPE
     STATUS current
     DESCRIPTION
     "This trap is sent upon change of the active Flip tables
      (Flip DB)."
     ::= { muxHubEvents 4 }

  statusChangedTrap  NOTIFICATION-TYPE
     OBJECTS       { agnLed }
     STATUS current
     DESCRIPTION
     "This trap is sent upon any change of the LEDs status."
     ::= { muxHubEvents 5 }
-- 
-- file :v:\doc\rdv\mib\ver485\ethIf.txt
-- 
--01/08/2000
--By: Smadar Tauber
--File:      s:\doc\rdv\mib\ver485\ethIf.txt


--EthIf MIB - separated from mpmx.txt

--diverseIfWanGen	OBJECT IDENTIFIER ::= {wanGen 6}

--Last update: 20-Jan-2002 by Ilana Schvetz


--
-- diverseIf - diverse NON-WAN interfaces of WAN products 	
--

--Ethernet Interface


ethIf OBJECT IDENTIFIER ::= {diverseIfWanGen 1}	  --Ethernet Interface

ethIfTable OBJECT-TYPE
      SYNTAX SEQUENCE OF EthIfEntry
      MAX-ACCESS not-accessible
      STATUS current
	DESCRIPTION  "A table."
	::=  { ethIf 1}

ethIfEntry OBJECT-TYPE
      SYNTAX EthIfEntry
      MAX-ACCESS not-accessible
      STATUS current
	DESCRIPTION  "An entry in table."
	INDEX {ethIfIdx}
      ::= {ethIfTable 1}

EthIfEntry ::=
      SEQUENCE {
      ethIfIdx                Integer32,
      ethMode                 INTEGER,
      ethBridgingMode         INTEGER,
	  ethEncapsulationCRCMode INTEGER,
	  ethBackPressure		  INTEGER,
	  ethLimit4				  INTEGER,
	  ethSkipInitReset		  INTEGER,
	  ethMulticastBlock	  	  INTEGER,
	  ethBroadcastBlock	  	  INTEGER,
	  ethSpeed				  INTEGER
	 		      }

ethIfIdx     OBJECT-TYPE
      SYNTAX  Integer32
      MAX-ACCESS  read-only
      STATUS  current
      DESCRIPTION
      "A unique index of the ethernet interface/port."
      ::=  {ethIfEntry 1}

ethMode    OBJECT-TYPE
      SYNTAX  INTEGER
        {
          halfDuplex  (1),
          fullDuplex  (2),
		  notApplicable(255)
     }
      MAX-ACCESS  read-write
      STATUS  current
      DESCRIPTION
      "This object indicates the Ethernet mode of operation."
      ::=  {ethIfEntry 2}

ethBridgingMode  OBJECT-TYPE
      SYNTAX  INTEGER
      {
         filtered    (1),
         transparent (2)
      }
      MAX-ACCESS  read-write
      STATUS  current
      DESCRIPTION
      "This object indicates the bridging mode of the Ethernet
       interface. "
      ::=  {ethIfEntry 3}

ethEncapsulationCRCMode  OBJECT-TYPE
      SYNTAX  INTEGER
      {
			  notApplicable (1),
			  withCRC	    (2),
			  withoutCRC	(3)
      }
      MAX-ACCESS  read-write
      STATUS  current
      DESCRIPTION
       "This object define the encapsulation type requested for the
			  Ethernet interface. It indicates if we transfer the Ethernet
				frame to the other side with or without the CRC. "
      ::=  {ethIfEntry 4}

ethBackPressure  OBJECT-TYPE
      SYNTAX  INTEGER
      {
			  notApplicable (1),
			  disable	    (2),
			  enable		(3)
      }
      MAX-ACCESS  read-write
      STATUS  current
      DESCRIPTION
        "This parameter defines whether to enable or disable Back pressure.
         Back Pressure is a flow control parameter. "
      ::=  {ethIfEntry 5}
      
ethLimit4  OBJECT-TYPE
      SYNTAX  INTEGER
      {
			  notApplicable (1),
			  disable	    (2),
			  enable		(3)
      }
      MAX-ACCESS  read-write
      STATUS  current
      DESCRIPTION
       "This parameter determine the Back off algorithm mode.
        Every 4 following collisions the Framer will be thrown out
        (4 times more than usuall)."
      ::=  {ethIfEntry 6}
      
ethSkipInitReset  OBJECT-TYPE
      SYNTAX  INTEGER
      {
			  notApplicable (1),
			  notSkip	    (2),
			  skip			(3)
      }
      MAX-ACCESS  read-write
      STATUS  current
      DESCRIPTION
       "This parameter defines whether read status on reset. "
      ::=  {ethIfEntry 7}
      
ethMulticastBlock  OBJECT-TYPE
      SYNTAX  INTEGER
      {
			  notApplicable (1),
			  unBlock	    (2),
			  block			(3)
      }
      MAX-ACCESS  read-write
      STATUS  current
      DESCRIPTION
       "This parameter defines whether to send multicast message to WAN from LAN or not. "
      ::=  {ethIfEntry 8}

ethBroadcastBlock  OBJECT-TYPE
      SYNTAX  INTEGER
      {
			  notApplicable (1),
			  unBlock	    (2),
			  block			(3)
      }
      MAX-ACCESS  read-write
      STATUS  current
      DESCRIPTION
       "This parameter defines whether to send broadcast message to WAN from LAN or not."
      ::=  {ethIfEntry 9}

ethSpeed  OBJECT-TYPE
      SYNTAX  INTEGER
      {
			  notApplicable (1),
			  s10Mbps	    (2),
			  s100Mbps		(3)
      }
      MAX-ACCESS  read-write
      STATUS  current
      DESCRIPTION
       "This parameter defines the line speed."
      ::=  {ethIfEntry 10}


ethIfPerformance OBJECT IDENTIFIER ::= {ethIf 2}

ethIfCurrentTable OBJECT-TYPE
      SYNTAX SEQUENCE OF EthIfCurrentEntry
      MAX-ACCESS not-accessible
      STATUS current
	DESCRIPTION
         "The Ethernet Current table."
	  ::=  { ethIfPerformance 1}

ethIfCurrentEntry OBJECT-TYPE
      SYNTAX EthIfCurrentEntry
      MAX-ACCESS not-accessible
      STATUS current
	DESCRIPTION
         "An entry in the Ethernet Current table."
	INDEX {ethIfCurrentIndex}
      ::= {ethIfCurrentTable 1}

EthIfCurrentEntry ::=
      SEQUENCE {
      ethIfCurrentIndex
           Integer32,
	  ethIfCurrentStatus
	       OCTET STRING,
      ethIfCurrentInFrames
      	   Gauge32,
      ethIfCurrentInOctets
      	   Gauge32,
      ethIfCurrentAlignmentErrors
      	   Gauge32,
      ethIfCurrentFCSErrors
      	   Gauge32,
      ethIfCurrentLengthError
      	   Gauge32,
      ethIfCurrentOutFrames
      	   Gauge32,
      ethIfCurrentOutOctets
      	   Gauge32,
      ethIfCurrentSingleCollisionFrames
      	   Gauge32,
      ethIfCurrentMultipleCollisionFrames
           Gauge32,
      ethIfCurrentDeferredTransmissions
      	   Gauge32,
      ethIfCurrentLateCollisions
      	   Gauge32,
      ethIfCurrentCarrierSenseErrors
      	   Gauge32
      }

ethIfCurrentIndex OBJECT-TYPE
      SYNTAX      Integer32
      MAX-ACCESS  read-only
      STATUS      current
      DESCRIPTION
        "The index of the Ethernet interface. 
        It may be ifIndex."
     ::= { ethIfCurrentEntry 1 }

ethIfCurrentStatus OBJECT-TYPE
	 SYNTAX OCTET STRING  (SIZE (4))
     MAX-ACCESS  read-only
     STATUS  current
     DESCRIPTION
      "The statuses of the current interval:
         0 - Valid.
         1 - redundantLinkSwitch - the link has been switched 
             by a redundancy mechanism.
         2 - discontinuity - module was partialy out.
         4 - notValid - module is out."
      ::= { ethIfCurrentEntry 2 }

ethIfCurrentInFrames OBJECT-TYPE
      SYNTAX  Gauge32  
      MAX-ACCESS  read-only
      STATUS  current
      DESCRIPTION
	  "The counter associated with the number of received frames, 
	  encountered by the Ethernet interface in the current 15 minute 
	  interval."
      ::= { ethIfCurrentEntry 3 }

ethIfCurrentInOctets OBJECT-TYPE
      SYNTAX  Gauge32  
      MAX-ACCESS  read-only
      STATUS  current
      DESCRIPTION
	  "The counter associated with the number of received octets, 
	  encountered by the Ethernet interface in the current 15 minute 
	  interval."
      ::= { ethIfCurrentEntry 4 }

ethIfCurrentAlignmentErrors OBJECT-TYPE
      SYNTAX  Gauge32  
      MAX-ACCESS  read-only
      STATUS  current
      DESCRIPTION
	  "The counter associated with the number of received frames, 
	  which are not complete (The result of dividing the number 
	  of bits by 8 is not an Integer), encountered by the Ethernet 
	  interface in the current 15 minute interval."
      ::= { ethIfCurrentEntry 5 }

ethIfCurrentFCSErrors OBJECT-TYPE
      SYNTAX  Gauge32  
      MAX-ACCESS  read-only
      STATUS  current
      DESCRIPTION
	  "The counter associated with the number of received frames 
	  that didn't pass the FCS test, encountered by the Ethernet 
	  interface in the current 15 minute interval."
      ::= { ethIfCurrentEntry 6 }

ethIfCurrentLengthError OBJECT-TYPE
      SYNTAX  Gauge32  
      MAX-ACCESS  read-only
      STATUS  current
      DESCRIPTION
	  "The counter associated with the number of received frames 
	  with length error, encountered by the Ethernet interface in 
	  the current 15 minute interval."
      ::= { ethIfCurrentEntry 7 }

ethIfCurrentOutFrames OBJECT-TYPE
      SYNTAX  Gauge32  
      MAX-ACCESS  read-only
      STATUS  current
      DESCRIPTION
	  "The counter associated with the number of transmitted frames, 
	  encountered by the Ethernet interface in the current 15 minute 
	  interval."
      ::= { ethIfCurrentEntry 8 }

ethIfCurrentOutOctets OBJECT-TYPE
      SYNTAX  Gauge32  
      MAX-ACCESS  read-only
      STATUS  current
      DESCRIPTION
	  "The counter associated with the number of transmitted octets, 
	  encountered by the Ethernet interface in the current 15 minute 
	  interval."
      ::= { ethIfCurrentEntry 9 }

ethIfCurrentSingleCollisionFrames OBJECT-TYPE
      SYNTAX  Gauge32  
      MAX-ACCESS  read-only
      STATUS  current
      DESCRIPTION
	  "The counter associated with the number of successfully
	  transmitted frames for which transmission was inhibited by
	  exactly one collision, encountered by the Ethernet interface 
	  in the current 15 minute interval."
      ::= { ethIfCurrentEntry 10 }

ethIfCurrentMultipleCollisionFrames OBJECT-TYPE
      SYNTAX  Gauge32  
      MAX-ACCESS  read-only
      STATUS  current
      DESCRIPTION
	  "The counter associated with the number of successfully
	  transmitted frames for which transmission was inhibited by
	  more than one collision, encountered by the Ethernet interface 
	  in the current 15 minute interval."
      ::= { ethIfCurrentEntry 11 }

ethIfCurrentDeferredTransmissions OBJECT-TYPE
      SYNTAX  Gauge32  
      MAX-ACCESS  read-only
      STATUS  current
      DESCRIPTION
	  "The counter associated with the number of transmitted frames 
	  for which the first transmission attempt was delayed due to a 
	  busy media, encountered by the Ethernet interface in the 
	  current 15 minute interval."
      ::= { ethIfCurrentEntry 12 }

ethIfCurrentLateCollisions OBJECT-TYPE
      SYNTAX  Gauge32  
      MAX-ACCESS  read-only
      STATUS  current
      DESCRIPTION
	  "The counter associated with the number of times that a 
	  collision was detected later than the first 64 bytes of the 
	  frame, encountered by the Ethernet interface in the current 
	  15 minute interval."
      ::= { ethIfCurrentEntry 13 }

ethIfCurrentCarrierSenseErrors OBJECT-TYPE
      SYNTAX  Gauge32  
      MAX-ACCESS  read-only
      STATUS  current
      DESCRIPTION
	  "The counter associated with the number of times that the 
	  carrier sense condition was lost or never asserted when 
	  attempting to transmit a frame, encountered by the Ethernet 
	  interface in the current 15 minute interval."
      ::= { ethIfCurrentEntry 14 }


--Interval Table

ethIfIntervalTable OBJECT-TYPE
      SYNTAX SEQUENCE OF EthIfIntervalEntry
      MAX-ACCESS not-accessible
      STATUS current
	DESCRIPTION
         "The Ethernet Interval table."
	  ::=  { ethIfPerformance 2 }

ethIfIntervalEntry OBJECT-TYPE
      SYNTAX EthIfIntervalEntry
      MAX-ACCESS not-accessible
      STATUS current
	DESCRIPTION
         "An entry in the Ethernet Interval table."
    INDEX { ethIfIntervalIndex, ethIfIntervalNumber }
      ::= {ethIfIntervalTable 1}

EthIfIntervalEntry ::=
      SEQUENCE {
      ethIfIntervalIndex
           Integer32,
      ethIfIntervalNumber
           Integer32,
	  ethIfIntervalStatus
	       OCTET STRING,
      ethIfIntervalInFrames
      	   Gauge32,
      ethIfIntervalInOctets
      	   Gauge32,
      ethIfIntervalAlignmentErrors
      	   Gauge32,
      ethIfIntervalFCSErrors
      	   Gauge32,
      ethIfIntervalLengthError
      	   Gauge32,
      ethIfIntervalOutFrames
      	   Gauge32,
      ethIfIntervalOutOctets
      	   Gauge32,
      ethIfIntervalSingleCollisionFrames
      	   Gauge32,
      ethIfIntervalMultipleCollisionFrames
           Gauge32,
      ethIfIntervalDeferredTransmissions
      	   Gauge32,
      ethIfIntervalLateCollisions
      	   Gauge32,
      ethIfIntervalCarrierSenseErrors
      	   Gauge32
      }

ethIfIntervalIndex OBJECT-TYPE
    SYNTAX      Integer32
    MAX-ACCESS  read-only
    STATUS      current
    DESCRIPTION
        "The index of the Ethernet interface. 
        It may be ifIndex."
    ::= { ethIfIntervalEntry 1 }

ethIfIntervalNumber OBJECT-TYPE
    SYNTAX  Integer32 (1..96)
    MAX-ACCESS  read-only
    STATUS  current
    DESCRIPTION
        "A number between 1 and 96, where 1 is the most
         recently completed 15 minute interval and 96 is
         the least recently completed 15 minutes interval
         (assuming that all 96 intervals exist)."
    ::= { ethIfIntervalEntry 2 }

ethIfIntervalStatus OBJECT-TYPE
	 SYNTAX OCTET STRING  (SIZE (4))
     MAX-ACCESS  read-only
     STATUS  current
     DESCRIPTION
      "The statuses of the current interval:
         0 - Valid.
         1 - redundantLinkSwitch - the link has been switched 
             by a redundancy mechanism.
         2 - discontinuity - module was partialy out.
         4 - notValid - module is out."
      ::= { ethIfIntervalEntry 3 }

ethIfIntervalInFrames OBJECT-TYPE
      SYNTAX  Gauge32  
      MAX-ACCESS  read-only
      STATUS  current
      DESCRIPTION
	  "The counter associated with the number of received frames, 
	  encountered by the Ethernet interface in one of the previous 
	  96, individual 15 minute, intervals."
      ::= { ethIfIntervalEntry 4 }

ethIfIntervalInOctets OBJECT-TYPE
      SYNTAX  Gauge32  
      MAX-ACCESS  read-only
      STATUS  current
      DESCRIPTION
	  "The counter associated with the number of received octets, 
	  encountered by the Ethernet interface in one of the previous 
	  96, individual 15 minute, intervals."
      ::= { ethIfIntervalEntry 5 }

ethIfIntervalAlignmentErrors OBJECT-TYPE
      SYNTAX  Gauge32  
      MAX-ACCESS  read-only
      STATUS  current
      DESCRIPTION
	  "The counter associated with the number of received frames, 
	  which are not complete (The result of dividing the number 
	  of bits by 8 is not an Integer), encountered by the Ethernet 
	  interface in one of the previous 96, individual 15 minute, 
	  intervals."
      ::= { ethIfIntervalEntry 6 }

ethIfIntervalFCSErrors OBJECT-TYPE
      SYNTAX  Gauge32  
      MAX-ACCESS  read-only
      STATUS  current
      DESCRIPTION
	  "The counter associated with the number of received frames 
	  that didn't pass the FCS test, encountered by the Ethernet 
	  interface in one of the previous 96, individual 15 minute, 
	  intervals."
      ::= { ethIfIntervalEntry 7 }

ethIfIntervalLengthError OBJECT-TYPE
      SYNTAX  Gauge32  
      MAX-ACCESS  read-only
      STATUS  current
      DESCRIPTION
	  "The counter associated with the number of received frames 
	  with length error, encountered by the Ethernet interface in 
	  one of the previous 96, individual 15 minute, intervals."
      ::= { ethIfIntervalEntry 8 }

ethIfIntervalOutFrames OBJECT-TYPE
      SYNTAX  Gauge32  
      MAX-ACCESS  read-only
      STATUS  current
      DESCRIPTION
	  "The counter associated with the number of transmitted frames, 
	  encountered by the Ethernet interface in one of the previous 
	  96, individual 15 minute, intervals."
      ::= { ethIfIntervalEntry 9 }

ethIfIntervalOutOctets OBJECT-TYPE
      SYNTAX  Gauge32  
      MAX-ACCESS  read-only
      STATUS  current
      DESCRIPTION
	  "The counter associated with the number of transmitted octets, 
	  encountered by the Ethernet interface in one of the previous 
	  96, individual 15 minute, intervals."
      ::= { ethIfIntervalEntry 10 }

ethIfIntervalSingleCollisionFrames OBJECT-TYPE
      SYNTAX  Gauge32  
      MAX-ACCESS  read-only
      STATUS  current
      DESCRIPTION
	  "The counter associated with the number of successfully
	  transmitted frames for which transmission was inhibited by
	  exactly one collision, encountered by the Ethernet 
	  interface in one of the previous 96, individual 15 minute, 
	  intervals."
      ::= { ethIfIntervalEntry 11 }

ethIfIntervalMultipleCollisionFrames OBJECT-TYPE
      SYNTAX  Gauge32  
      MAX-ACCESS  read-only
      STATUS  current
      DESCRIPTION
	  "The counter associated with the number of successfully
	  transmitted frames for which transmission was inhibited by
	  more than one collision, encountered by the Ethernet 
	  interface in one of the previous 96, individual 15 minute, 
	  intervals."
      ::= { ethIfIntervalEntry 12 }

ethIfIntervalDeferredTransmissions OBJECT-TYPE
      SYNTAX  Gauge32  
      MAX-ACCESS  read-only
      STATUS  current
      DESCRIPTION
	  "The counter associated with the number of transmitted frames 
	  for which the first transmission attempt was delayed due to a 
	  busy media, encountered by the Ethernet interface in one of 
	  the previous 96, individual 15 minute, intervals."
      ::= { ethIfIntervalEntry 13 }

ethIfIntervalLateCollisions OBJECT-TYPE
      SYNTAX  Gauge32  
      MAX-ACCESS  read-only
      STATUS  current
      DESCRIPTION
	  "The counter associated with the number of times that a 
	  collision was detected later than the first 64 bytes of the 
	  frame, encountered by the Ethernet interface in one of the 
	  previous 96, individual 15 minute, intervals."
      ::= { ethIfIntervalEntry 14 }

ethIfIntervalCarrierSenseErrors OBJECT-TYPE
      SYNTAX  Gauge32  
      MAX-ACCESS  read-only
      STATUS  current
      DESCRIPTION
	  "The counter associated with the number of times that the 
	  carrier sense condition was lost or never asserted when 
	  attempting to transmit a frame, encountered by the Ethernet 
	  interface in one of the previous 96, individual 15 minute, 
	  intervals."
      ::= { ethIfIntervalEntry 15 }




-- 
-- file :v:\doc\rdv\mib\ver480\tsa.txt
-- 

--Title:  RAD's WAN TSA (Time-Slot Assignment) MIB
--By:     Smadar Tauber
--Date :  30.11.1998

--Last Update: 16/10/01   
--By: Smadar 
--File:  v:\doc\rdv\mib\ver480\tsa.txt

--***********************************************************************
--Products that use this file WITHOUT the MPMX.TXT file,have to add the
--following definitions to their *.pkb files:
--
--wanGen   OBJECT IDENTIFIER ::= {radWan 1}
--agnWanGen   OBJECT IDENTIFIER ::= {wanGen 2}
--agnSystemTs      OBJECT IDENTIFIER ::= {agnWanGen 11}
--***********************************************************************

--
-- TS Assignment Table from system point of view
--

agnTsTable  OBJECT-TYPE
     SYNTAX SEQUENCE OF AgnTsEntry
     MAX-ACCESS not-accessible
     STATUS  current
     DESCRIPTION
     "The write operation into the Table Objects is valid only
      to the TmpCnfg entry."
     ::= { agnSystemTs 1}

agnTsEntry OBJECT-TYPE
      SYNTAX AgnTsEntry
      MAX-ACCESS not-accessible
      STATUS current
	DESCRIPTION  "An entry in table."
	INDEX {agnTsCnfgIdx, agnTsSltIdx, agnTsPrtIdx, agnTsIdx,
             agnTsBitIdx, agnTsConSltIdx, agnTsConPrtIdx, agnTsConIdx }
      ::= { agnTsTable 1}

AgnTsEntry ::=
      SEQUENCE {
     agnTsCnfgIdx   Integer32,
     agnTsSltIdx    INTEGER,
     agnTsPrtIdx    Integer32,
     agnTsIdx       Integer32,
     agnTsBitIdx    Integer32,
     agnTsConSltIdx INTEGER,
     agnTsConPrtIdx Integer32,
     agnTsConIdx    Integer32,
     agnTsType      INTEGER,
     agnTsRowStatus RowStatus,
	 agnTsDirection INTEGER
      }


agnTsCnfgIdx OBJECT-TYPE
      SYNTAX  Integer32 (1..255)
      MAX-ACCESS  read-only
      STATUS  current
      DESCRIPTION
      "This attribute indicates the Idx of the Cnfg (1..100) being
       accessed.
       Idx 255 relates to the TmpCnfg. "
      ::= { agnTsEntry 1}

agnTsSltIdx OBJECT-TYPE
      SYNTAX  INTEGER
     { io1   (5),
       io2   (6),
       io3   (7),
       io4   (8),
       io5   (9),
       io6  (10),
       io7  (11),
       io8  (12),
       io9  (13),
       io10 (14),
       io11 (15),
       io12 (16),
       io13 (17),
       io14 (18),
       io15 (19),
       notApplicable(255)
     }
      MAX-ACCESS  read-only
      STATUS  current
      DESCRIPTION
      "This attribute indicates a unique  slot  position where
       the card is inserted."
      ::= { agnTsEntry 2}

agnTsPrtIdx OBJECT-TYPE
      SYNTAX  Integer32
      MAX-ACCESS  read-only
      STATUS  current
      DESCRIPTION
      "This attribute indicates a unique external or internal port number.
       For MP, the valid values will be (for MLs only):
       -  exPrt1(1)..exPrt4(4) 
       -  inPrt1(101)..inPrt4(104)"
      ::= { agnTsEntry 3}

agnTsIdx OBJECT-TYPE
      SYNTAX  Integer32 (1..32)
      MAX-ACCESS  read-only
      STATUS  current
      DESCRIPTION
      "This attribute indicates a unique index for TS (Time-Slot).
       - for T1 ports - 1..24, Fbit(25)
       - for E1 ports - 1..31
       - for HDSL ports - 1..32 ; 32 will represent TS0."
      ::= { agnTsEntry 4}

agnTsBitIdx OBJECT-TYPE
      SYNTAX  Integer32
      MAX-ACCESS  read-only
      STATUS  current
      DESCRIPTION
      "This attribute indicates a unique index for the Bit
       of each TS (Time-Slot).
       1..8 - Bit 1.. Bit 8
       255  - notApplicable
       This object is applicable only in Split Time-Slot cases."
      ::= { agnTsEntry 5}

agnTsConSltIdx OBJECT-TYPE
      SYNTAX  INTEGER
   {   io1   (5),
       io2   (6),
       io3   (7),
       io4   (8),
       io5   (9),
       io6  (10),
       io7  (11),
       io8  (12),
       io9  (13),
       io10 (14),
       io11 (15),
       io12 (16),
       io13 (17),
       io14 (18),
       io15 (19),
       notApplicable(255)
       }
      MAX-ACCESS  read-only
      STATUS  current
      DESCRIPTION
      "This attribute indicates a unique slot position In the Mux
       where the TS is routed to."
      ::= { agnTsEntry 6}

agnTsConPrtIdx OBJECT-TYPE
      SYNTAX  Integer32
      MAX-ACCESS  read-only
      STATUS  current
      DESCRIPTION
      "This attribute indicates a unique port id the TS is 
       routed to.
	   notApplicable - when agnTsType=mng or spare
       For MP:
       exPrt1    (1) .. exPrt16  (16) ,
       notApplicable(100),
       inPrt1  (101) .. inPrt48 (148). "
      ::= { agnTsEntry 7}


agnTsConIdx OBJECT-TYPE
      SYNTAX  Integer32    (1..255)
      MAX-ACCESS  read-only
      STATUS  current
      DESCRIPTION
      "This attribute indicates a unique TS number the Src TS is 
       routed to.
	   Valid values:
       - for T1 ports - 1..24, Fbit(25)
       - for E1 ports - 1..31
       - for HDSL ports - 1..32 ; 32 will represent TS0.
       - notApplicable - 255 (for ports that don't have TSs)."
      ::= { agnTsEntry 8}

agnTsType  OBJECT-TYPE
      SYNTAX  INTEGER
      {
       unknown   (1),
       voice     (2),
       data      (3),
       vcMP      (4),
       mng       (6),
	   spare     (7),
	   reserved  (8),
	   dChannel  (9)     
      }
      MAX-ACCESS  read-create
      STATUS  current
      DESCRIPTION
      "Time-Slot Type - regarding its connection and media type.
       voice, data, vcMP - connected and the media is specified.
       mng - management. This TS is Dedicated to Management (not
             disconnected, but not connected to another port).
       spare - applicable for ML-20 only. These TSs should be reserved for future
             connection, though at the moment are not connected.
       reserved - these TSs are not connected, but they are Reserved for 
             Protection (back-up) of a certain Path. Therefore, should 
             NOT be used for connection of other Paths.
       dChannel - is used only when the TS is connected to a V5.1 ML (Bypass)
                  and it contains ISDN D Channel data. In this case, 
                  agnTsConSltIdx, agnTsConPrtIdx and agnTsConIdx, will
                  be 'notApplicable', since no TS is assigned for D Ch in V5.1 ML."
   ::= { agnTsEntry 9}

agnTsRowStatus OBJECT-TYPE
      SYNTAX  RowStatus
      MAX-ACCESS  read-create
      STATUS  current
      DESCRIPTION
      "This attribute allows to create/delete a row in this table.
        For creating a row, the NMS should set
        agnTsRowStatus.255.id2.id3.id4.id5.id6.id7.id8 = active(1).
        For destroying a row, the NMS should set:
        agnTsRowStatus.255.id2.id3.id4.id5.id6.id7.id8 = destroy(6).
        Only rows with status active(1) are relevant.
        The only possible supported RowStatus vaules are
        active (1) and destroy (6)."
      ::= { agnTsEntry 10}

agnTsDirection  OBJECT-TYPE
      SYNTAX  INTEGER
      {
       notApplicable (1),
       rx            (2),
       tx            (3),
       both          (4),
       bcastSrc      (5),
	   bcastDst      (6),
	   internal      (7)
      }
      MAX-ACCESS  read-create
      STATUS  current
      DESCRIPTION
      "Direction of the connection. This parameter is especially important
	   when in MP a ML is connected to an IO port that has no TSs, so it doesn't
	   appear in the TS Assignment for the first 5 indexes.
	   notApplicable - for products that do not support this object	or for
	        certain TS Types (for example: mng, spare)
       rx - the ML only Receives from the IO Port (the ML will appear in the
            first 5 indexes).
       tx - the ML only Transmits to the IO Port (the ML will appear in the
            first 5 indexes). Nothing is received back.
       both - the ML Receives and Transmits to the IO Port (the ML will appear in the
            first 5 indexes).
       bcastSrc - the ML is a Broadcast-Bidirectional Source. It Transmits to
            one or several IO Ports (including the one that appears in the last
            3 indexes) and sometimes receives.
            The Port that responds is dynamic (it can be another each time).
            The ML will appear in the first 5 indexes.
       bcastDst - the ML is a Broadcast-Bidirectional Destination. Therefore,
             it Receives and sometimes Transmits.  The ML will appear in the
             first 5 indexes.
       internal - for connection of TSs internally, within the same card. Such an
             assignment has no effect on the external TS connections of the same
             TS. A TS can be connected with 'internal' direction to a port
             of the same card and at the same time, connected by another direction
             to ports (and TSs) of other cards."
      ::= { agnTsEntry 11}

-- 
-- file :v:\doc\rdv\mib\Before~1\sps5.txt
-- 

-- Title:   PS MIB
--
--
-- Version:  1.0
-- Date:       February  1, 95
-- By:         Debby Koren
-- Updated:  Orly Nicklass, Smadar Tauber, Yair Arian, Liora Gafni
-- Last update: 07-Oct-99

-- Comments:  This is the Packet Switching branch in the RAD MIB



--	  X121Address ::= OCTET STRING (SIZE(0..17))
	   -- 0 to 17 bytes in length containing the ASCII
	   -- characters [0-9], each octet contains one digit
	   -- of the address.

-- radPS        OBJECT IDENTIFIER ::= { rad 8 }

-- The groups in this MIB are the PS System Group, the Async Group, the Link Table, X.25 Group,
-- HDLC Table, STM Table.   Whenever an object appears twice with only the final
-- character in the object name differing, the object whose name ends with S is read-write, and represents
-- a scratch value that will take effect upon an activate imperitive action.  The object whose name ends
-- with A represents the current active value and is read-only.   This was done to protect the user against
-- inadvertantly disturbing active communications and to allow switchover to a different set of parameters
-- in real time.

-- The PS System Group contains all the PS system wide cofiguration parameters
-- and the Routing Table


pktSwchSystem    OBJECT IDENTIFIER ::= { radPS 1}

pktSwchSysParam  OBJECT IDENTIFIER ::= { pktSwchSystem 1 }

pktSwchSysSParam  OBJECT IDENTIFIER ::= { pktSwchSysParam 1 }

pktSwchSysX28PromptS  OBJECT-TYPE
    SYNTAX DisplayString (SIZE (0..10))
    MAX-ACCESS  read-write
    STATUS  current
    DESCRIPTION
	"This specifies a different PAD prompt, instead of the standard default character, the *.
		 Up to 10 characters can be entered."
    ::= { pktSwchSysSParam 1 }

pktSwchSysHeraldS  OBJECT-TYPE
    SYNTAX DisplayString (SIZE (0..32))
    MAX-ACCESS  read-write
    STATUS  current
    DESCRIPTION
	"This specifies the PAD herald message for the SPS-6 and SPS-12.  Up to 32 characters
		can be entered.  Other devices will return a zero length octet string and will send an error
		 if this object is set to a string of any other length."
    ::= { pktSwchSysSParam 2 }

pktSwchSysBulletinS  OBJECT-TYPE
    SYNTAX DisplayString (SIZE (0..32))
    MAX-ACCESS  read-write
    STATUS  current
    DESCRIPTION
	"This specifies the PAD bulletin message.  Up to 32 characters can be entered."
    ::= { pktSwchSysSParam 3 }

pktSwchSysComPortSubAddS  OBJECT-TYPE
    SYNTAX Integer32 (0..255)
    MAX-ACCESS  read-write
    STATUS  current
    DESCRIPTION
	"This is the scratch command port with the desired subaddress."
    ::= { pktSwchSysSParam 4 }


pktSwchSysComPortAltSubAddS  OBJECT-TYPE
    SYNTAX Integer32 (0..255)
    MAX-ACCESS  read-write
    STATUS  current
    DESCRIPTION
	"This configures the command port with the second subaddress."
    ::= { pktSwchSysSParam 5 }

pktSwchSysInnerCommLenS  OBJECT-TYPE
    SYNTAX Integer32 (1..5)
    MAX-ACCESS  read-write
    STATUS  current
    DESCRIPTION
	"This specifies the address length in digits for Inner Communication."
    ::= {  pktSwchSysSParam 6 }

pktSwchSysXOnCharS OBJECT-TYPE
    SYNTAX Integer32 (0..127)
    MAX-ACCESS  read-write
    STATUS  current
    DESCRIPTION
	"The ASCII code of the software flow control character that will be used to start/renew the data
		 transfer."
    ::= {  pktSwchSysSParam 7 }


pktSwchSysXOffCharS OBJECT-TYPE
    SYNTAX Integer32 (0..127)
    MAX-ACCESS  read-write
    STATUS  current
    DESCRIPTION
	"The ASCII code of the software flow control character that will be used to stop the data
		 transfer."
    ::= {  pktSwchSysSParam 8 }

pktSwchSysMaxLcnS OBJECT-TYPE
    SYNTAX Integer32
    MAX-ACCESS  read-write
    STATUS  current
    DESCRIPTION
	"The maximum number of LCNs on the device."
    ::= {  pktSwchSysSParam 9 }


pktSwchSysMaxAIDS OBJECT-TYPE
    SYNTAX Integer32
    MAX-ACCESS  read-write
    STATUS  current
    DESCRIPTION
	"The maximum number of AIDs on the device."
    ::= {  pktSwchSysSParam 10 }

pktSwchSysDeviceIdS OBJECT-TYPE
    SYNTAX DisplayString
    MAX-ACCESS  read-write
    STATUS  current
    DESCRIPTION
	"The device Id."
    ::= {  pktSwchSysSParam 11 }


pktSwchSysAParam  OBJECT IDENTIFIER ::= { pktSwchSysParam 2 }

pktSwchSysX28PromptA  OBJECT-TYPE
    SYNTAX DisplayString (SIZE (0..10))
    MAX-ACCESS  read-only
    STATUS  current
    DESCRIPTION
	"This specifies the active PAD prompt."
    ::= { pktSwchSysAParam 1 }

pktSwchSysHeraldA  OBJECT-TYPE
    SYNTAX DisplayString (SIZE (0..32))
    MAX-ACCESS  read-only
    STATUS  current
    DESCRIPTION
	"This specifies the active PAD herald message for the SPS-6 and SPS-12.  Other devices will
		return a zero length string."
    ::= { pktSwchSysAParam 2 }

pktSwchSysBulletinA  OBJECT-TYPE
    SYNTAX DisplayString (SIZE (0..32))
    MAX-ACCESS  read-only
    STATUS  current
    DESCRIPTION
	"This indicates the active PAD bulletin message."
    ::= { pktSwchSysAParam 3 }

pktSwchSysComPortSubAddA  OBJECT-TYPE
    SYNTAX Integer32 (0..255)
    MAX-ACCESS  read-only
    STATUS  current
    DESCRIPTION
	"This is the active command port with the desired subaddress."
    ::= { pktSwchSysAParam 4 }

pktSwchSysComPortAltSubAddA  OBJECT-TYPE
    SYNTAX Integer32 (0..255)
    MAX-ACCESS  read-only
    STATUS  current
    DESCRIPTION
	"This is the active command port with the second subaddress."
    ::= {  pktSwchSysAParam 5 }


pktSwchSysInnerCommLenA  OBJECT-TYPE
    SYNTAX Integer32 (1..5)
    MAX-ACCESS  read-only
    STATUS  current
    DESCRIPTION
	"This specifies the active address length in digits for Inner Communication."
    ::= {  pktSwchSysAParam 6 }

pktSwchSysXOnCharA OBJECT-TYPE
    SYNTAX Integer32 (0..127)
    MAX-ACCESS  read-only
    STATUS  current
    DESCRIPTION
	"The activeASCII code of the software flow control character that is used to start/renew the data
		 transfer."
    ::= {  pktSwchSysAParam 7 }

pktSwchSysXOffCharA OBJECT-TYPE
    SYNTAX Integer32 (0..127)
    MAX-ACCESS  read-only
    STATUS  current
    DESCRIPTION
	"The active ASCII code of the software flow control character that is used to stop the data
		 transfer."
    ::= {  pktSwchSysAParam 8 }


pktSwchSysMaxLcnA OBJECT-TYPE
    SYNTAX Integer32
    MAX-ACCESS  read-only
    STATUS  current
    DESCRIPTION
	"The active maximum number of LCNs on the device."
    ::= {  pktSwchSysAParam 9 }

pktSwchSysMaxAIDA OBJECT-TYPE
    SYNTAX Integer32
    MAX-ACCESS  read-only
    STATUS  current
    DESCRIPTION
	"The active maximum number of AIDs on the device."
    ::= {  pktSwchSysAParam 10 }

pktSwchSysDeviceIdA OBJECT-TYPE
    SYNTAX DisplayString
    MAX-ACCESS  read-only
    STATUS  current
    DESCRIPTION
	"The device Id."
    ::= {  pktSwchSysAParam 11 }


pktSwchSysEvRepS  OBJECT IDENTIFIER ::= { pktSwchSysParam 3 }

pktSwchSysEvRepAdd1S  OBJECT-TYPE
    SYNTAX DisplayString
    MAX-ACCESS  read-write
    STATUS  current
    DESCRIPTION
	"This specifies the X.25 address to which the reports selected by means of
		 pktSwchSysEvRepMask1S and pktSwchSysEvRepPeriod1S will be sent."
    ::= { pktSwchSysEvRepS 1 }

pktSwchSysEvRepAdd2S  OBJECT-TYPE
    SYNTAX DisplayString
    MAX-ACCESS  read-write
    STATUS  current
    DESCRIPTION
	"This specifies the X.25 address to which the reports selected by means of
		 pktSwchSysEvRepMask2S and pktSwchSysEvRepPeriod2S will be sent."
    ::= { pktSwchSysEvRepS 2 }

pktSwchSysEvRepMask1S  OBJECT-TYPE
    SYNTAX Integer32 (0..15)
    MAX-ACCESS  read-write
    STATUS  current
    DESCRIPTION
	"This specifies the conditions on which reports are sent to the address specified in
		 pktSwchSysEvRepAdd1S.  The value is a sum of values (powers of two), where each
		 value in the sum represents a condition.  The values that may be included in the sum and
		 their meanings are:
		0 Disable event reports
		1 Send report when SYNC status has changed
		2 Send report when RTS status has changed
		4 Send report at Power On (Reset)
		8 Report charging information at CLR."
    ::= { pktSwchSysEvRepS 3 }

pktSwchSysEvRepPeriod1S  OBJECT-TYPE
    SYNTAX Integer32 (0..255)
    MAX-ACCESS  read-write
    STATUS  current
    DESCRIPTION
        "This specifies the time interval in minutes at which periodic
reports are sent to the address specified in pktSwchSysEvRepAdd1S.  A value of
                 zero indicates that periodic reports are disabled." ::= {
    pktSwchSysEvRepS 4 }


pktSwchSysEvRepMask2S  OBJECT-TYPE
    SYNTAX Integer32 (0..15)
    MAX-ACCESS  read-write
    STATUS  current
    DESCRIPTION
	"This specifies the conditions on which reports are sent to the address specified in
		 pktSwchSysEvRepAdd2S.  The value is a sum of values (powers of two), where each
		 value in the sum represents a condition.  The values that may be included in the sum and
		  their meanings are:
		0 Disable event reports
		1 Send report when SYNC status has changed
		2 Send report when RTS status has changed
		4 Send report at Power On (Reset)
		8 Report charging information at CLR."
    ::= { pktSwchSysEvRepS 5 }

pktSwchSysEvRepPeriod2S  OBJECT-TYPE
    SYNTAX Integer32 (0..255)
    MAX-ACCESS  read-write
    STATUS  current
    DESCRIPTION
	"This specifies the time interval in minutes at which periodic reports are sent to
		 the address specified in pktSwchSysEvRepAdd2S.  A value of zero indicates that
		 periodic reports are disabled."
    ::= { pktSwchSysEvRepS 6 }


pktSwchSysEvRepRetryCntS  OBJECT-TYPE
    SYNTAX Integer32
	MAX-ACCESS read-write
	STATUS  current
	DESCRIPTION
	"Number of retries to send Event Reports to each port.
	 Possible values:
	 0     - Disable retry mechanism
	 1-255 - Number of retries "
	::= { pktSwchSysEvRepS 7 }

pktSwchSysEvRepRetryDelayS  OBJECT-TYPE
    SYNTAX Integer32
	MAX-ACCESS read-write
	STATUS  current
	DESCRIPTION
	"Time interval between retries (in minutes).
	 Valid values: 1-255 "
	::= { pktSwchSysEvRepS 8 }

pktSwchSysEvRepRetryOptionsS  OBJECT-TYPE
    SYNTAX Integer32
	MAX-ACCESS read-write
	STATUS  current
	DESCRIPTION
	"Event report options. The value is a sum of values (powers of
	two), where each value in the sum represents an option. The
	values that may be included in the sum and their meanings are:
	0 - No Options
	1 - Alternate Mode: Port 1 reports are readdressed to Port 2
	    on failure. (Port 2 mask is not used).
    2 - Condensed Format
	X - Any combination of the above values "
	::= { pktSwchSysEvRepS 9 }



pktSwchSysEvRepA  OBJECT IDENTIFIER ::= { pktSwchSysParam 4 }

pktSwchSysEvRepAdd1A  OBJECT-TYPE
    SYNTAX DisplayString
    MAX-ACCESS  read-only
    STATUS  current
    DESCRIPTION
	"This specifies the active X.25 address to which the reports selected by means of
		 pktSwchSysEvRepMask1A and pktSwchSysEvRepPeriod1A will be sent."
    ::= { pktSwchSysEvRepA 1 }

pktSwchSysEvRepAdd2A  OBJECT-TYPE
    SYNTAX DisplayString
    MAX-ACCESS  read-only
    STATUS  current
    DESCRIPTION
	"This specifies the active X.25 address to which the reports selected by means of
		 pktSwchSysEvRepMask2A and pktSwchSysEvRepPeriod2A will be sent."
    ::= { pktSwchSysEvRepA 2 }


pktSwchSysEvRepMask1A  OBJECT-TYPE
    SYNTAX Integer32 (0..15)
    MAX-ACCESS  read-only
    STATUS  current
    DESCRIPTION
	"This specifies the active conditions on which reports are sent to the address specified in
		 pktSwchSysEvRepAdd1A.  The value is a sum of values (powers of two), where each
		 value in the sum represents a condition.  The values that may be included in the sum and
		 their meanings are:
		0 Disable event reports
		1 Send report when SYNC status has changed
		2 Send report when RTS status has changed
		4 Send report at Power On (Reset)
	  	8 Report charging information at CLR."
    ::= { pktSwchSysEvRepA 3 }


pktSwchSysEvRepPeriod1A  OBJECT-TYPE
    SYNTAX Integer32 (1..255)
    MAX-ACCESS  read-only
    STATUS  current
    DESCRIPTION
	"This specifies the active time interval in minutes at which periodic reports are sent to
		 the address specified in pktSwchSysEvRepAdd1A.  A value of zero indicates that
		 periodic reports are disabled."
    ::= { pktSwchSysEvRepA 4 }

pktSwchSysEvRepMask2A  OBJECT-TYPE
    SYNTAX Integer32 (0..15)
    MAX-ACCESS  read-only
    STATUS  current
    DESCRIPTION
	"This specifies the active conditions on which reports are sent to the address specified in
		 pktSwchSysEvRepAdd2A.  The value is a sum of values (powers of two), where each
		 value in the sum represents a condition.  The values that may be included in the sum and
		  their meanings are:
		0 Disable event reports
		1 Send report when SYNC status has changed
		2 Send report when RTS status has changed
		4 Send report at Power On (Reset)
	  	8 Report charging information at CLR."
    ::= { pktSwchSysEvRepA 5 }

pktSwchSysEvRepPeriod2A  OBJECT-TYPE
    SYNTAX Integer32 (1..255)
    MAX-ACCESS  read-only
    STATUS  current
    DESCRIPTION
	"This specifies the active time interval in minutes at which periodic reports are sent to
		 the address specified in pktSwchSysEvRepAdd2A.  A value of zero indicates that
		 periodic reports are disabled."
    ::= { pktSwchSysEvRepA 6 }

pktSwchSysEvRepRetryCntA  OBJECT-TYPE
    SYNTAX Integer32
	MAX-ACCESS read-only
	STATUS  current
	DESCRIPTION
	"Number of retries to send Event Reports to each port.
	 Possible values:
	 0     - Disable retry mechanism
	 1-255 - Number of retries "
	::= { pktSwchSysEvRepA 7 }

pktSwchSysEvRepRetryDelayA  OBJECT-TYPE
    SYNTAX Integer32
	MAX-ACCESS read-only
	STATUS  current
	DESCRIPTION
	"Time interval between retries (in minutes).
	 Valid values: 1-255 "
	::= { pktSwchSysEvRepA 8 }

pktSwchSysEvRepRetryOptionsA  OBJECT-TYPE
    SYNTAX Integer32
	MAX-ACCESS read-only
	STATUS  current
	DESCRIPTION
	"Event report options. The value is a sum of values (powers of
	two), where each value in the sum represents an option. The
	values that may be included in the sum and their meanings are:
	0 - No Options
	1 - Alternate Mode: Port 1 reports are readdressed to Port 2
	    on failure. (Port 2 mask is not used).
    2 - Condensed Format
	X - Any combination of the above values "
	::= { pktSwchSysEvRepA 9 }


pktSwchSysGen  OBJECT IDENTIFIER ::= { pktSwchSysParam 5 }

pktSwchSysDate OBJECT-TYPE
    SYNTAX DisplayString
    MAX-ACCESS  read-write
    STATUS  current
    DESCRIPTION
	"This is used to update the date on the device."
    ::= {  pktSwchSysGen 1 }


pktSwchSysTime OBJECT-TYPE
    SYNTAX DisplayString
    MAX-ACCESS  read-write
    STATUS  current
    DESCRIPTION
	"This is used to update the time on the device."
    ::= {  pktSwchSysGen 2 }

pktSwchSysAction OBJECT-TYPE
    SYNTAX INTEGER {
       noOp(1),
       reset(2),
       resetStat(3),
       rearrangeNovram(4),
       setDefaultConfig(5)     }
    MAX-ACCESS  read-write
    STATUS  current
    DESCRIPTION
	"This is used to perform imperitive commands on the device.
	 The reset command resets the device with the scratch values."
    ::= {  pktSwchSysGen 3 }

pktSwchSysRamSize OBJECT-TYPE
    SYNTAX Integer32
    MAX-ACCESS  read-only
    STATUS  current
    DESCRIPTION
	"The RAM size on the device."
    ::= {  pktSwchSysGen 4 }

pktSwchSysNovramSize OBJECT-TYPE
    SYNTAX Integer32
    MAX-ACCESS  read-only
    STATUS  current
    DESCRIPTION
	"The NOVRAM size on the device."
    ::= {  pktSwchSysGen 5 }

pktSwchSysNovramUtil OBJECT-TYPE
    SYNTAX Integer32
    MAX-ACCESS  read-only
    STATUS  current
    DESCRIPTION
	"The NOVRAM utilization on the device."
    ::= {  pktSwchSysGen 6 }

pktSwchSysFreeDataBuff OBJECT-TYPE
    SYNTAX Integer32
    MAX-ACCESS  read-only
    STATUS  current
    DESCRIPTION
	"The free data buffers on the device."
    ::= {  pktSwchSysGen 7 }

pktSwchSysMinDataBuffInPool OBJECT-TYPE
    SYNTAX Integer32
    MAX-ACCESS  read-only
    STATUS  current
    DESCRIPTION
	"The minimum data buffers in the pool on the device."
    ::= {  pktSwchSysGen 8 }

pktSwchSysProtocols OBJECT-TYPE
    SYNTAX Integer32
    MAX-ACCESS  read-only
    STATUS  current
    DESCRIPTION
	"The protocols the device can support. The value is a sum of values
	 (powers of two), where each value in the sum represents a protocol.
	 The values that may be included in the sum and their
	 meanings are:
		1     X.25
		2     Frame Relay
		4     HDLC
	  	8     SDLC
		16    MPE
		32    ASYNC
		64    STM-4
        128   STM-8
        256   STM-16
        512   STM-24
		1024  BISYNC
		2048  SLIP
        4096  ETHERNET
        8192  PPP
       16384  ISDN
	  	XX - Any combination of the values specified above ."
       ::= {  pktSwchSysGen 9 }


pktSwchSysChannelProtocols OBJECT-TYPE
    SYNTAX Integer32
    MAX-ACCESS  read-only
    STATUS  current
    DESCRIPTION
        "The protocols the device can support on the async channels.
		1     ASYNC
		2     SLIP
                3     PPP  "
       ::= {  pktSwchSysGen 10 }


pktSwchSysStatus OBJECT-TYPE
    SYNTAX  INTEGER {
       valid(1),
       createRequest(2),
       underCreation(3),
       invalid(4)
     }
    MAX-ACCESS  read-write
    STATUS  current
    DESCRIPTION
	"The status of the System data.  The choices are those defined in the SNMPv2 Textual Conventions
		 for RowStatus.  This will allow easy replacement of the INTEGER syntax with the RowStatus
		 textual convention SYNTAX."
  ::= { pktSwchSysParam 6 }



-- The routing subgroup in the pktSwch System Group contains the routing table, the local PVC table
-- and the net PVC table

pktSwchRouting  OBJECT IDENTIFIER ::= {  pktSwchSystem 2}

pktSwchRoutSTable    OBJECT-TYPE
    SYNTAX  SEQUENCE  OF PktSwchRoutSEntry
    MAX-ACCESS  not-accessible
    STATUS  current
    DESCRIPTION
	"The Scratch Routing Table defines the routes for incoming and
	 outgoing data on the device."
    ::=  { pktSwchRouting 1 }

pktSwchRoutSEntry OBJECT-TYPE
    SYNTAX  PktSwchRoutSEntry
    MAX-ACCESS  not-accessible
    STATUS  current
    DESCRIPTION
	"Defines the contents of each line in the Scratch Routing Table."
    INDEX   { pktSwchRoutIdS }
    ::=  { pktSwchRoutSTable 1  }

PktSwchRoutSEntry ::=  SEQUENCE {
	pktSwchRoutIdS
	 Integer32,
    pktSwchRoutAddressS
     DisplayString,
    pktSwchRoutDestLink1S
     DisplayString,
	pktSwchRoutDestLink2S
     DisplayString,
	pktSwchRoutDestLink3S
     DisplayString,
    pktSwchRoutLinkPrio1S
     Integer32,
	pktSwchRoutLinkPrio2S
     Integer32,
	pktSwchRoutLinkPrio3S
     Integer32,
	pktSwchRoutSearchStatusS
	 INTEGER,
    pktSwchRoutStatusS
     INTEGER
    }

pktSwchRoutIdS OBJECT-TYPE
    SYNTAX Integer32 (1..2000)
	MAX-ACCESS  read-write
	STATUS  current
	DESCRIPTION
	"Index of the pktSwchRoutSTable."
	::= { pktSwchRoutSEntry 1 }

pktSwchRoutAddressS OBJECT-TYPE
    SYNTAX DisplayString
    MAX-ACCESS  read-write
    STATUS  current
    DESCRIPTION
	"The address to which the entry applies.  The use of the octet
	 string syntax allows the use of the letter x as a wild card in
	 the addresses."
    ::= { pktSwchRoutSEntry 2 }

pktSwchRoutDestLink1S OBJECT-TYPE
    SYNTAX 	DisplayString -- (SIZE(6))
    MAX-ACCESS  read-write
    STATUS  current
    DESCRIPTION
        "First destination link through which the data will be routed.
         For X.25 destination: any valid x.25 link no.
         For Frame Relay Link: any valid dlci with an x.25 encapsulation
                               protocol, presented in the form of {port:dlci}.
         For a local destination: 100 .
         For ISDN:             ISDN routing entry number preceeded by the
                               letter 'I' (example: I4)"
    ::= { pktSwchRoutSEntry 3 }

pktSwchRoutDestLink2S OBJECT-TYPE
    SYNTAX DisplayString -- (SIZE(6))
    MAX-ACCESS  read-write
    STATUS  current
    DESCRIPTION
        "Second destination link through which the data will be routed.
         For X.25 destination: any valid x.25 link no.
         For Frame Relay Link: any valid dlci with an x.25 encapsulation
                               protocol, presented in the form of {port:dlci}.
         For a local destination: 100 .
         For ISDN:             ISDN routing entry number preceeded by the
                               letter 'I' (example: I4)"
    ::= { pktSwchRoutSEntry 4 }

pktSwchRoutDestLink3S OBJECT-TYPE
    SYNTAX DisplayString -- (SIZE(6))
    MAX-ACCESS  read-write
    STATUS  current
    DESCRIPTION
        "Third destination link through which the data will be routed.
         For X.25 destination: any valid x.25 link no.
         For Frame Relay Link: any valid dlci with an x.25 encapsulation
                               protocol, presented in the form of {port:dlci}.
         For a local destination: 100 .
         For ISDN:             ISDN routing entry number preceeded by the
                               letter 'I' (example: I4)"
    ::= { pktSwchRoutSEntry 5 }


pktSwchRoutLinkPrio1S OBJECT-TYPE
    SYNTAX Integer32
    MAX-ACCESS  read-write
    STATUS  current
    DESCRIPTION
	"A priority of the associated destination of link 1."
    ::= { pktSwchRoutSEntry 6 }

pktSwchRoutLinkPrio2S OBJECT-TYPE
    SYNTAX Integer32
    MAX-ACCESS  read-write
    STATUS  current
    DESCRIPTION
	"A priority of the associated destination of link 2."
    ::= { pktSwchRoutSEntry 7 }

pktSwchRoutLinkPrio3S OBJECT-TYPE
    SYNTAX Integer32
    MAX-ACCESS  read-write
    STATUS  current
    DESCRIPTION
	"A priority of the associated destination of link 3."
    ::= { pktSwchRoutSEntry 8 }

pktSwchRoutSearchStatusS OBJECT-TYPE
    SYNTAX  INTEGER {
       off(2),
       on(3)
    }
    MAX-ACCESS  read-write
    STATUS  current
    DESCRIPTION
	" off - The device stops searching for a matching address.
	  on - The device continues searching for a matching address in the
	       links of the next entry."
  ::= { pktSwchRoutSEntry 9 }


pktSwchRoutStatusS OBJECT-TYPE
    SYNTAX  INTEGER {
       valid(1),
       createRequest(2),
       underCreation(3),
       invalid(4)
    }
    MAX-ACCESS  read-write
    STATUS  current
    DESCRIPTION
	"The status of this routing table entry.  The choices are those defined in the SNMPv2 Textual
		 Conventions for RowStatus.  This will allow easy replacement of the INTEGER syntax with
		 the RowStatus textual convention SYNTAX."
  ::= { pktSwchRoutSEntry 10 }

pktSwchRoutATable    OBJECT-TYPE
    SYNTAX  SEQUENCE  OF PktSwchRoutAEntry
    MAX-ACCESS  not-accessible
    STATUS  current
    DESCRIPTION
	"The Active Routing Table defines the active routes for incoming and outgoing data
		on the device."
    ::=  { pktSwchRouting 2 }

pktSwchRoutAEntry OBJECT-TYPE
    SYNTAX  PktSwchRoutAEntry
    MAX-ACCESS  not-accessible
    STATUS  current
    DESCRIPTION
	"Defines the contents of each line in the Active Routing Table."
    INDEX   { pktSwchRoutIdA }
    ::=  { pktSwchRoutATable 1  }

PktSwchRoutAEntry ::= SEQUENCE {
    pktSwchRoutIdA
	 Integer32,
    pktSwchRoutAddressA
     DisplayString,
    pktSwchRoutDestLink1A
     DisplayString,
	pktSwchRoutDestLink2A
     DisplayString,
	pktSwchRoutDestLink3A
     DisplayString,
    pktSwchRoutLinkPrio1A
     Integer32,
	pktSwchRoutLinkPrio2A
     Integer32,
	pktSwchRoutLinkPrio3A
     Integer32,
	pktSwchRoutSearchStatusA
	 INTEGER
    }

pktSwchRoutIdA OBJECT-TYPE
    SYNTAX Integer32 (1..2000)
	MAX-ACCESS  read-only
	STATUS  current
	DESCRIPTION
	"Index of the pktSwchRoutATable."
	::= { pktSwchRoutAEntry 1 }


pktSwchRoutAddressA OBJECT-TYPE
    SYNTAX DisplayString
    MAX-ACCESS  read-only
    STATUS  current
    DESCRIPTION
	"The address to which the entry applies.  The use of the octet string syntax allows
		 the use of the letter x as a wild card in the addresses."
    ::= { pktSwchRoutAEntry 2 }

pktSwchRoutDestLink1A OBJECT-TYPE
    SYNTAX DisplayString -- (SIZE(6))
    MAX-ACCESS  read-only
    STATUS  current
    DESCRIPTION
        "First destination link through which the data will be routed.
         For X.25 destination: any valid x.25 link no.
         For Frame Relay Link: any valid dlci with an x.25 encapsulation
                               protocol, presented in the form of {port:dlci}.
         For a local destination: 100 .
         For ISDN:             ISDN routing entry number preceeded by the
                               letter 'I' (example: I4)"
    ::= { pktSwchRoutAEntry 3 }

pktSwchRoutDestLink2A OBJECT-TYPE
    SYNTAX DisplayString -- (SIZE(6))
    MAX-ACCESS  read-only
    STATUS  current
    DESCRIPTION
        "Second destination link through which the data will be routed.
         For X.25 destination: any valid x.25 link no.
         For Frame Relay Link: any valid dlci with an x.25 encapsulation
                               protocol, presented in the form of {port:dlci}.
         For a local destination: 100 .
         For ISDN:             ISDN routing entry number preceeded by the
                               letter 'I' (example: I4)"
    ::= { pktSwchRoutAEntry 4 }

pktSwchRoutDestLink3A OBJECT-TYPE
    SYNTAX DisplayString -- (SIZE(6))
    MAX-ACCESS  read-only
    STATUS  current
    DESCRIPTION
        "Third destination link through which the data will be routed.
         For X.25 destination: any valid x.25 link no.
         For Frame Relay Link: any valid dlci with an x.25 encapsulation
                               protocol, presented in the form of {port:dlci}.
         For a local destination: 100 .
         For ISDN:             ISDN routing entry number preceeded by the
                               letter 'I' (example: I4)"
    ::= { pktSwchRoutAEntry 5 }


pktSwchRoutLinkPrio1A OBJECT-TYPE
    SYNTAX Integer32
    MAX-ACCESS  read-only
    STATUS  current
    DESCRIPTION
	"A priority of the associated destination of link 1."
    ::= { pktSwchRoutAEntry 6 }

pktSwchRoutLinkPrio2A OBJECT-TYPE
    SYNTAX Integer32
    MAX-ACCESS  read-only
    STATUS  current
    DESCRIPTION
	"A priority of the associated destination of link 2."
    ::= { pktSwchRoutAEntry 7 }

pktSwchRoutLinkPrio3A OBJECT-TYPE
    SYNTAX Integer32
    MAX-ACCESS  read-only
    STATUS  current
    DESCRIPTION
	"A priority of the associated destination of link 3."
    ::= { pktSwchRoutAEntry 8 }

pktSwchRoutSearchStatusA OBJECT-TYPE
    SYNTAX  INTEGER {
       off(2),
       on(3)
    }
    MAX-ACCESS  read-only
    STATUS  current
    DESCRIPTION
	" off - The device stops searching for a matching address.
	  on - The device continues searching for a matching address in the
	       links of the next entry."
  ::= { pktSwchRoutAEntry 9 }



pktSwchPvcSTable    OBJECT-TYPE
    SYNTAX  SEQUENCE  OF PktSwchPvcSEntry
    MAX-ACCESS  not-accessible
    STATUS  current
    DESCRIPTION
	"The Scratch Network PVC Table defines the network PVCs."
    ::=  { pktSwchRouting 3 }

pktSwchPvcSEntry OBJECT-TYPE
    SYNTAX  PktSwchPvcSEntry
    MAX-ACCESS  not-accessible
    STATUS  current
    DESCRIPTION
	"Defines the contents of each line in the Scratch Network PVC table."
    INDEX   { pktSwchPvcNumS }
    ::=  { pktSwchPvcSTable 1  }

PktSwchPvcSEntry ::= SEQUENCE {
    pktSwchPvcNumS
     Integer32,
    pktSwchPvcSrcLinkS
     Integer32,
    pktSwchPvcSrcLcnS
     DisplayString,
    pktSwchPvcDstLinkS
     Integer32,
    pktSwchPvcDstLcnS
     Integer32,
    pktSwchPvcStatusS
     INTEGER
    }

pktSwchPvcNumS OBJECT-TYPE
    SYNTAX Integer32 (1..200)
    MAX-ACCESS  read-write
    STATUS  current
    DESCRIPTION
	"The PVC number corresponding to this entry."
    ::= { pktSwchPvcSEntry 1 }

pktSwchPvcSrcLinkS OBJECT-TYPE
    SYNTAX Integer32 (0..100)
    MAX-ACCESS  read-write
    STATUS  current
    DESCRIPTION
	"The number of the link (1 through 6 for SPS-6 and 1 through 12 for SPS-12) that will be
		 used as a source link to create a connection by means of the PVC.
		  0 means that the PVC will not be active, 100 means that this pvc is Local."
    ::= { pktSwchPvcSEntry 2 }

pktSwchPvcSrcLcnS OBJECT-TYPE
    SYNTAX DisplayString -- (SIZE(1..6))
    MAX-ACCESS  read-write
    STATUS  current
    DESCRIPTION
	"    Network pvc:
    The number of the logical channel (0-255) that will be used as the source
    logical channel to create a connection by means of the PVC.

    Local pvc:
    For asynchronous channel to X.25 PVC,
      Any valid Async Channel number.

   For encapsulation of transparent HDLC over X25 PVC,
     valid Channel numbers are:
        HxM - for the main PVC.
        HxB - for the backup PVC.
              x is a valid HDLC link number.

   For encapsulation of Multi Point Encapsulator (MPE) over X25 PVC,
     valid channel numbers are:
        Nx - where x is a valid MPE link number.

   For encapsulation of IP Over X.25 PVC, Enter IP."
    ::= { pktSwchPvcSEntry 3 }

pktSwchPvcDstLinkS OBJECT-TYPE
    SYNTAX Integer32 (0..12)
    MAX-ACCESS  read-write
    STATUS  current
    DESCRIPTION
	"The number of the destination link that will be used.
	 0 means that the PVC will not be active."
    ::= { pktSwchPvcSEntry 4 }

pktSwchPvcDstLcnS OBJECT-TYPE
    SYNTAX Integer32 (0..255)
    MAX-ACCESS  read-write
    STATUS  current
    DESCRIPTION
	"The number of the logical channel for the destination link."
    ::= { pktSwchPvcSEntry 5 }

pktSwchPvcStatusS OBJECT-TYPE
    SYNTAX  INTEGER {
       valid(1),
       createRequest(2),
       underCreation(3),
       invalid(4)
     }
    MAX-ACCESS  read-write
    STATUS  current
    DESCRIPTION
	"The status of this Network PVC table entry.  The choices are those defined in the SNMPv2
		 Textual Conventions for RowStatus.  This will allow easy replacement of the INTEGER syntax
		 with the RowStatus textual convention SYNTAX."
  ::= { pktSwchPvcSEntry 6 }

pktSwchPvcATable   OBJECT-TYPE
    SYNTAX  SEQUENCE  OF PktSwchPvcAEntry
    MAX-ACCESS  not-accessible
    STATUS  current
    DESCRIPTION
	"The Active Network PVC Table defines the active network PVCs."
    ::=  { pktSwchRouting 4 }

pktSwchPvcAEntry OBJECT-TYPE
    SYNTAX  PktSwchPvcAEntry
    MAX-ACCESS  not-accessible
    STATUS  current
    DESCRIPTION
	"Defines the contents of each line in the Active Network PVC table."
    INDEX   { pktSwchPvcNumA }
    ::=  { pktSwchPvcATable 1  }

PktSwchPvcAEntry ::= SEQUENCE {
    pktSwchPvcNumA
     Integer32,
    pktSwchPvcSrcLinkA
     Integer32,
    pktSwchPvcSrcLcnA
     DisplayString,
    pktSwchPvcDstLinkA
     Integer32,
    pktSwchPvcDstLcnA
     Integer32
    }

pktSwchPvcNumA OBJECT-TYPE
    SYNTAX Integer32 (1..200)
    MAX-ACCESS  read-only
    STATUS  current
    DESCRIPTION
	"The PVC number corresponding to this entry."
    ::= { pktSwchPvcAEntry 1 }

pktSwchPvcSrcLinkA OBJECT-TYPE
    SYNTAX Integer32 (0..100)
    MAX-ACCESS  read-only
    STATUS  current
    DESCRIPTION
	"The number of the link (1 through 6 for SPS-6 and 1 through 12 for SPS-12) that is
		 used as a source link to create a connection by means of the PVC.
		  0 means that the PVC will not be active, 100 means that this pvc is Local."
    ::= { pktSwchPvcAEntry 2 }

pktSwchPvcSrcLcnA OBJECT-TYPE
    SYNTAX DisplayString -- (SIZE(1..6))
    MAX-ACCESS  read-only
    STATUS  current
    DESCRIPTION
	"    Network pvc:
    The number of the logical channel (0-255) that will be used as the source
    logical channel to create a connection by means of the PVC.

    Local pvc:
    For asynchronous channel to X.25 PVC,
      Any valid Async Channel number.

   For encapsulation of transparent HDLC over X25 PVC,
     valid Channel numbers are:
        HxM - for the main PVC.
        HxB - for the backup PVC.
              x is a valid HDLC link number.

   For encapsulation of Multi Point Encapsulator (MPE) over X25 PVC,
     valid channel numbers are:
        Nx - where x is a valid MPE link number.

   For encapsulation of IP Over X.25 PVC, Enter IP."
    ::= { pktSwchPvcAEntry 3 }

pktSwchPvcDstLinkA OBJECT-TYPE
    SYNTAX Integer32 (0..12)
    MAX-ACCESS  read-only
    STATUS  current
    DESCRIPTION
	"The number of the destination link that is used.
	0 means that the PVC will not be active."
    ::= { pktSwchPvcAEntry 4 }

pktSwchPvcDstLcnA OBJECT-TYPE
    SYNTAX Integer32 (0..255)
    MAX-ACCESS  read-only
    STATUS  current
    DESCRIPTION
	"The number of the logical channel for the destination link."
    ::= { pktSwchPvcAEntry 5 }


-- NUI Table

pktSwchNui  OBJECT IDENTIFIER ::= { pktSwchSystem 3 }

-- The NUI Table contains the Network User Identification
-- password information.

pktSwchNuiSTable    OBJECT-TYPE
    SYNTAX  SEQUENCE  OF PktSwchNuiSEntry
    MAX-ACCESS  not-accessible
    STATUS  current
    DESCRIPTION
	"The NUI Table defines the NUIs that can be used by the device."
    ::=  {  pktSwchNui 1 }

pktSwchNuiSEntry OBJECT-TYPE
    SYNTAX  PktSwchNuiSEntry
    MAX-ACCESS  not-accessible
    STATUS  current
    DESCRIPTION
	"Defines the contents of each line in the NUI Table."
    INDEX   { pktSwchNuiIndexS }
    ::=  { pktSwchNuiSTable 1  }

PktSwchNuiSEntry ::= SEQUENCE {
    pktSwchNuiIndexS
     Integer32,
    pktSwchNuiGroupIdS
     Integer32,
    pktSwchNuiInPasswdS
     DisplayString,
    pktSwchNuiOutPasswdPointerS
     Integer32,
    pktSwchNuiInAddrS
     DisplayString,
    pktSwchNuiOutAddrPointerS
     Integer32,
    pktSwchNuiStatusS
     INTEGER
    }

pktSwchNuiIndexS OBJECT-TYPE
    SYNTAX Integer32
    MAX-ACCESS  read-write
    STATUS  current
    DESCRIPTION
	"The index of this entry."
    ::= { pktSwchNuiSEntry 1 }

pktSwchNuiGroupIdS OBJECT-TYPE
    SYNTAX  Integer32
    MAX-ACCESS  read-write
    STATUS  current
    DESCRIPTION
	"The group Id for this NUI entry."
    ::= { pktSwchNuiSEntry 2 }

pktSwchNuiInPasswdS OBJECT-TYPE
    SYNTAX  DisplayString
    MAX-ACCESS  read-write
    STATUS  current
    DESCRIPTION
	"The password for the incoming call. 15 chars."
    ::= { pktSwchNuiSEntry 3 }

pktSwchNuiOutPasswdPointerS OBJECT-TYPE
    SYNTAX  Integer32
    MAX-ACCESS  read-write
    STATUS  current
    DESCRIPTION
	"A pointer to the password in the OutPasswdTable for an outgoing call."
    ::= { pktSwchNuiSEntry 4 }

pktSwchNuiInAddrS OBJECT-TYPE
    SYNTAX  DisplayString
    MAX-ACCESS  read-write
    STATUS  current
    DESCRIPTION
	"The addresss for the incoming call. 15 digits."
    ::= { pktSwchNuiSEntry 5 }

pktSwchNuiOutAddrPointerS OBJECT-TYPE
    SYNTAX  Integer32
    MAX-ACCESS  read-write
    STATUS  current
    DESCRIPTION
	"A pointer to the address in the OutAddrTable for an outgoing call."
    ::= { pktSwchNuiSEntry 6 }

pktSwchNuiStatusS OBJECT-TYPE
    SYNTAX  INTEGER {
       valid(1),
       createRequest(2),
       underCreation(3),
       invalid(4)
     }
    MAX-ACCESS  read-write
    STATUS  current
    DESCRIPTION
	"The status of this NUI table entry.  The choices are those defined in the SNMPv2 Textual
		 Conventions for RowStatus.  This will allow easy replacement of the INTEGER syntax with
		 the RowStatus textual convention SYNTAX."
  ::= { pktSwchNuiSEntry 7 }


pktSwchNuiATable    OBJECT-TYPE
    SYNTAX  SEQUENCE  OF PktSwchNuiAEntry
    MAX-ACCESS  not-accessible
    STATUS  current
    DESCRIPTION
	"The NUI Table defines the NUIs that can be used by the device."
    ::=  {  pktSwchNui 2 }

pktSwchNuiAEntry OBJECT-TYPE
    SYNTAX  PktSwchNuiAEntry
    MAX-ACCESS  not-accessible
    STATUS  current
    DESCRIPTION
	"Defines the contents of each line in the NUI Table."
    INDEX   { pktSwchNuiIndexA }
    ::=  { pktSwchNuiATable 1  }

PktSwchNuiAEntry ::= SEQUENCE {
    pktSwchNuiIndexA
     Integer32,
    pktSwchNuiGroupIdA
     Integer32,
    pktSwchNuiInPasswdA
     DisplayString,
    pktSwchNuiOutPasswdPointerA
     Integer32,
    pktSwchNuiInAddrA
     DisplayString,
    pktSwchNuiOutAddrPointerA
     Integer32,
    pktSwchNuiStatusA
     INTEGER
    }

pktSwchNuiIndexA OBJECT-TYPE
    SYNTAX Integer32
    MAX-ACCESS  read-only
    STATUS  current
    DESCRIPTION
	"The index of this entry."
    ::= { pktSwchNuiAEntry 1 }

pktSwchNuiGroupIdA OBJECT-TYPE
    SYNTAX  Integer32
    MAX-ACCESS  read-only
    STATUS  current
    DESCRIPTION
	"The group Id for this NUI entry."
    ::= { pktSwchNuiAEntry 2 }

pktSwchNuiInPasswdA OBJECT-TYPE
    SYNTAX  DisplayString
    MAX-ACCESS  read-only
    STATUS  current
    DESCRIPTION
	"The password for the incoming call. 15 chars."
    ::= { pktSwchNuiAEntry 3 }

pktSwchNuiOutPasswdPointerA OBJECT-TYPE
    SYNTAX  Integer32
    MAX-ACCESS  read-only
    STATUS  current
    DESCRIPTION
	"A pointer to the password in the OutPasswdTable for an outgoing call."
    ::= { pktSwchNuiAEntry 4 }

pktSwchNuiInAddrA OBJECT-TYPE
    SYNTAX  DisplayString
    MAX-ACCESS  read-only
    STATUS  current
    DESCRIPTION
	"The addresss for the incoming call. 15 digits."
    ::= { pktSwchNuiAEntry 5 }

pktSwchNuiOutAddrPointerA OBJECT-TYPE
    SYNTAX  Integer32
    MAX-ACCESS  read-only
    STATUS  current
    DESCRIPTION
	"A pointer to the address in the OutAddrTable for an outgoing call."
    ::= { pktSwchNuiAEntry 6 }

pktSwchNuiStatusA OBJECT-TYPE
    SYNTAX  INTEGER {
       valid(1),
       createRequest(2),
       underCreation(3),
       invalid(4)
     }
    MAX-ACCESS  read-only
    STATUS  current
    DESCRIPTION
	"The status of this NUI table entry.  The choices are those defined in the SNMPv2 Textual
		 Conventions for RowStatus.  This will allow easy replacement of the INTEGER syntax with
		 the RowStatus textual convention SYNTAX."
  ::= { pktSwchNuiAEntry 7 }


pktSwchNuiOutPasswdSTable    OBJECT-TYPE
    SYNTAX  SEQUENCE  OF PktSwchNuiOutPasswdSEntry
    MAX-ACCESS  not-accessible
    STATUS  current
    DESCRIPTION
	"The table defines the passwords that can be used by the device."
    ::=  {  pktSwchNui 3 }

pktSwchNuiOutPasswdSEntry OBJECT-TYPE
    SYNTAX  PktSwchNuiOutPasswdSEntry
    MAX-ACCESS  not-accessible
    STATUS  current
    DESCRIPTION
	"Defines the contents of each line in OutPasswd Table."
    INDEX   { pktSwchNuiOutPasswdIndexS }
    ::=  { pktSwchNuiOutPasswdSTable 1  }

PktSwchNuiOutPasswdSEntry ::= SEQUENCE {
    pktSwchNuiOutPasswdIndexS
     Integer32,
    pktSwchNuiOutPasswdValueS
     DisplayString,
    pktSwchNuiOutPasswdStatusS
     INTEGER
    }

pktSwchNuiOutPasswdIndexS OBJECT-TYPE
    SYNTAX Integer32
    MAX-ACCESS  read-write
    STATUS  current
    DESCRIPTION
	"The index of this entry."
    ::= { pktSwchNuiOutPasswdSEntry 1 }

pktSwchNuiOutPasswdValueS OBJECT-TYPE
    SYNTAX DisplayString
    MAX-ACCESS  read-write
    STATUS  current
    DESCRIPTION
	"The password of this entry. 15 chars."
    ::= { pktSwchNuiOutPasswdSEntry 2 }

pktSwchNuiOutPasswdStatusS OBJECT-TYPE
    SYNTAX  INTEGER {
       valid(1),
       createRequest(2),
       underCreation(3),
       invalid(4)
     }
    MAX-ACCESS  read-write
    STATUS  current
    DESCRIPTION
	"The status of this NuiOutPasswd table entry."
  ::= { pktSwchNuiOutPasswdSEntry 3 }


pktSwchNuiOutPasswdATable    OBJECT-TYPE
    SYNTAX  SEQUENCE  OF PktSwchNuiOutPasswdAEntry
    MAX-ACCESS  not-accessible
    STATUS  current
    DESCRIPTION
	"The table defines the passwords that can be used by the device."
    ::=  {  pktSwchNui 4 }

pktSwchNuiOutPasswdAEntry OBJECT-TYPE
    SYNTAX  PktSwchNuiOutPasswdAEntry
    MAX-ACCESS  not-accessible
    STATUS  current
    DESCRIPTION
	"Defines the contents of each line in OutPasswd Table."
    INDEX   { pktSwchNuiOutPasswdIndexA }
    ::=  { pktSwchNuiOutPasswdATable 1  }

PktSwchNuiOutPasswdAEntry ::= SEQUENCE {
    pktSwchNuiOutPasswdIndexA
     Integer32,
    pktSwchNuiOutPasswdValueA
     DisplayString,
    pktSwchNuiOutPasswdStatusA
     INTEGER
    }

pktSwchNuiOutPasswdIndexA OBJECT-TYPE
    SYNTAX Integer32
    MAX-ACCESS  read-only
    STATUS  current
    DESCRIPTION
	"The index of this entry."
    ::= { pktSwchNuiOutPasswdAEntry 1 }

pktSwchNuiOutPasswdValueA OBJECT-TYPE
    SYNTAX DisplayString
    MAX-ACCESS  read-only
    STATUS  current
    DESCRIPTION
	"The password of this entry. 15 chars."
    ::= { pktSwchNuiOutPasswdAEntry 2 }

pktSwchNuiOutPasswdStatusA OBJECT-TYPE
    SYNTAX  INTEGER {
       valid(1),
       createRequest(2),
       underCreation(3),
       invalid(4)
     }
    MAX-ACCESS  read-only
    STATUS  current
    DESCRIPTION
	"The status of this NuiOutPasswd table entry."
  ::= { pktSwchNuiOutPasswdAEntry 3 }


pktSwchNuiOutAddrSTable    OBJECT-TYPE
    SYNTAX  SEQUENCE  OF PktSwchNuiOutAddrSEntry
    MAX-ACCESS  not-accessible
    STATUS  current
    DESCRIPTION
	"The table defines the Addresses that can be used by the device."
    ::=  {  pktSwchNui 5 }

pktSwchNuiOutAddrSEntry OBJECT-TYPE
    SYNTAX  PktSwchNuiOutAddrSEntry
    MAX-ACCESS  not-accessible
    STATUS  current
    DESCRIPTION
	"Defines the contents of each line in OutAddr Table."
    INDEX   { pktSwchNuiOutAddrIndexS }
    ::=  { pktSwchNuiOutAddrSTable 1  }

PktSwchNuiOutAddrSEntry ::= SEQUENCE {
    pktSwchNuiOutAddrIndexS
     Integer32,
    pktSwchNuiOutAddrValueS
     DisplayString,
    pktSwchNuiOutAddrStatusS
     INTEGER
    }

pktSwchNuiOutAddrIndexS OBJECT-TYPE
    SYNTAX Integer32
    MAX-ACCESS  read-write
    STATUS  current
    DESCRIPTION
	"The index of this entry."
    ::= { pktSwchNuiOutAddrSEntry 1 }

pktSwchNuiOutAddrValueS OBJECT-TYPE
    SYNTAX DisplayString
    MAX-ACCESS  read-write
    STATUS  current
    DESCRIPTION
	"The address of this entry. 15 digits."
    ::= { pktSwchNuiOutAddrSEntry 2 }

pktSwchNuiOutAddrStatusS OBJECT-TYPE
    SYNTAX  INTEGER {
       valid(1),
       createRequest(2),
       underCreation(3),
       invalid(4)
     }
    MAX-ACCESS  read-write
    STATUS  current
    DESCRIPTION
	"The status of this NuiOutAddr table entry."
  ::= { pktSwchNuiOutAddrSEntry 3 }


pktSwchNuiOutAddrATable    OBJECT-TYPE
    SYNTAX  SEQUENCE  OF PktSwchNuiOutAddrAEntry
    MAX-ACCESS  not-accessible
    STATUS  current
    DESCRIPTION
	"The table defines the Addresses that can be used by the device."
    ::=  {  pktSwchNui 6 }

pktSwchNuiOutAddrAEntry OBJECT-TYPE
    SYNTAX  PktSwchNuiOutAddrAEntry
    MAX-ACCESS  not-accessible
    STATUS  current
    DESCRIPTION
	"Defines the contents of each line in OutAddr Table."
    INDEX   { pktSwchNuiOutAddrIndexA }
    ::=  { pktSwchNuiOutAddrATable 1  }

PktSwchNuiOutAddrAEntry ::= SEQUENCE {
    pktSwchNuiOutAddrIndexA
     Integer32,
    pktSwchNuiOutAddrValueA
     DisplayString,
    pktSwchNuiOutAddrStatusA
     INTEGER
    }

pktSwchNuiOutAddrIndexA OBJECT-TYPE
    SYNTAX Integer32
    MAX-ACCESS  read-only
    STATUS  current
    DESCRIPTION
	"The index of this entry."
    ::= { pktSwchNuiOutAddrAEntry 1 }

pktSwchNuiOutAddrValueA OBJECT-TYPE
    SYNTAX DisplayString
    MAX-ACCESS  read-only
    STATUS  current
    DESCRIPTION
	"The address of this entry. 15 digits."
    ::= { pktSwchNuiOutAddrAEntry 2 }

pktSwchNuiOutAddrStatusA OBJECT-TYPE
    SYNTAX  INTEGER {
       valid(1),
       createRequest(2),
       underCreation(3),
       invalid(4)
     }
    MAX-ACCESS  read-only
    STATUS  current
    DESCRIPTION
	"The status of this NuiOutAddr table entry."
  ::= { pktSwchNuiOutAddrAEntry 3 }


-- X25 Manager Table

pktSwchMng  OBJECT IDENTIFIER ::= { pktSwchSystem 4 }

pktSwchMngX25TrapIpTable  OBJECT-TYPE
	SYNTAX  SEQUENCE OF PktSwchMngX25Entry
	MAX-ACCESS  not-accessible
	STATUS current
	DESCRIPTION
	"This table indicates  the destination address of the traps.
	  Internally it will be limited to ten addresses. "
	::= { pktSwchMng 1 }

pktSwchMngX25Entry OBJECT-TYPE
	SYNTAX PktSwchMngX25Entry
	MAX-ACCESS  not-accessible
	STATUS current
    DESCRIPTION
	"An entry in table pktSwchMngX25TrapIpTable."
	INDEX {  pktSwchMngID }
	::= {pktSwchMngX25TrapIpTable  1 }


PktSwchMngX25Entry  ::=
	    SEQUENCE {
	pktSwchMngID
	  Integer32,
	pktSwchMngIP
	  IpAddress,
	pktSwchMngPhyAddr
	  DisplayString,
	pktSwchTrapEnable
	  Integer32,
	pktSwchEncapsulationMode
	  INTEGER
	}

pktSwchMngID OBJECT-TYPE
	SYNTAX  Integer32
	MAX-ACCESS  read-only
	STATUS current
	DESCRIPTION
	" This value indicates an index of a specific IP address"
	::= { pktSwchMngX25Entry 1 }

pktSwchMngIP OBJECT-TYPE
	SYNTAX  IpAddress
	MAX-ACCESS  read-write
        STATUS  current
	DESCRIPTION
	"This value indicates  the  destination address of the traps. IP 0.0.0.0 removes the entry. "
	::= { pktSwchMngX25Entry 2 }

pktSwchMngPhyAddr OBJECT-TYPE
	SYNTAX  DisplayString
	MAX-ACCESS  read-write
	STATUS  deprecated
	DESCRIPTION
	"This value indicates  the  physical destination  address of the traps."
	::= { pktSwchMngX25Entry 3 }

pktSwchTrapEnable OBJECT-TYPE
	SYNTAX  Integer32
	MAX-ACCESS  read-write
        STATUS  current
	DESCRIPTION
	"This value indicates which traps should be sent.
	 The value is a sum of values (powers of two), where each value in
	 the sum represents	a trap that should be reported to the Management
	 Station. The values that may be included in the sum and their meanings are:
		0   No traps would be reported.
		1   Link Down
		2   Link Up
		4   rtsChange
		8   resetX25
		16  restartX25
		32  frDLCIStatusChange
		64  coldStart
		128 linkProtocolChanged
        256 enrollmentPS
		512 ledStatusChange         "
	::= { pktSwchMngX25Entry 4 }

pktSwchEncapsulationMode OBJECT-TYPE
    SYNTAX  INTEGER	{
	 ipPid(1),
	 snapPid(2)
	 }
	MAX-ACCESS  read-write
        STATUS  deprecated
	DESCRIPTION
	"Format type for IP over X25"
	::= { pktSwchMngX25Entry 5 }


-- XID Table

pktSwchXid  OBJECT IDENTIFIER ::= { pktSwchSystem 5 }

pktSwchXidSTable  OBJECT-TYPE
	SYNTAX  SEQUENCE OF PktSwchXidSEntry
	MAX-ACCESS  not-accessible
	STATUS current
	DESCRIPTION
	"The Exchange Id table contains a list of 13 incoming pairs of allowed
	 dial-up phone numbers and passwords. Also included is one pair of
	 outgoing phone number and password (InternalIndex=14)."
	::= { pktSwchXid 1 }

pktSwchXidSEntry OBJECT-TYPE
	SYNTAX PktSwchXidSEntry
	MAX-ACCESS  not-accessible
	STATUS current
	DESCRIPTION
	"An entry in table pktSwchXidSTable."
	INDEX {  pktSwchXidIndexS, pktSwchXidInternalIndexS }
	::= {pktSwchXidSTable  1 }


PktSwchXidSEntry  ::=
	    SEQUENCE {
	pktSwchXidIndexS
	  Integer32,
	pktSwchXidInternalIndexS
	  Integer32,
	pktSwchXidPasswdS
	  DisplayString,
	pktSwchXidPhoneS
	  DisplayString,
	pktSwchXidStatusS
	  INTEGER
	}

pktSwchXidIndexS OBJECT-TYPE
	SYNTAX  Integer32
	MAX-ACCESS  read-write
	STATUS current
	DESCRIPTION
	" This Index of the XID table."
	::= { pktSwchXidSEntry 1 }

pktSwchXidInternalIndexS OBJECT-TYPE
	SYNTAX  Integer32
	MAX-ACCESS  read-write
	STATUS current
	DESCRIPTION
	"An internal index for each XidIndex of the table. The first 13 entries
	 refer to Incoming calls. The 14th entry refers to an Outgoing call."
	::= { pktSwchXidSEntry 2 }

pktSwchXidPasswdS OBJECT-TYPE
	SYNTAX  DisplayString
	MAX-ACCESS  read-write
	STATUS current
	DESCRIPTION
	"Password of size 16 chars."
	::= { pktSwchXidSEntry 3 }

pktSwchXidPhoneS OBJECT-TYPE
	SYNTAX  DisplayString
	MAX-ACCESS  read-write
	STATUS current
	DESCRIPTION
	"Phone number of size 16 digits."
	::= { pktSwchXidSEntry 4 }

pktSwchXidStatusS OBJECT-TYPE
    SYNTAX  INTEGER {
       valid(1),
       createRequest(2),
       underCreation(3),
       invalid(4)
     }
    MAX-ACCESS  read-write
    STATUS  current
    DESCRIPTION
	"The status of the XID table entry. The status applies to the XidIndex,
	 i.e., setting the staus to invalid results in the removal of all
	 the InternalIndex entries (1..14) belonging to the relevant XidIndex."
  ::= { pktSwchXidSEntry 5 }


pktSwchXidATable  OBJECT-TYPE
	SYNTAX  SEQUENCE OF PktSwchXidAEntry
	MAX-ACCESS  not-accessible
	STATUS current
	DESCRIPTION
	"The Exchange Id table contains a list of 13 incoming pairs of allowed
	 dial-up phone numbers and passwords. Also included is one pair of
	 outgoing phone number and password (InternalIndex=14)."
	::= { pktSwchXid 2 }

pktSwchXidAEntry OBJECT-TYPE
	SYNTAX PktSwchXidAEntry
	MAX-ACCESS  not-accessible
	STATUS current
	DESCRIPTION
	"An entry in table pktSwchXidATable."
	INDEX {  pktSwchXidIndexA, pktSwchXidInternalIndexA }
	::= {pktSwchXidATable  1 }


PktSwchXidAEntry  ::=
	    SEQUENCE {
	pktSwchXidIndexA
	  Integer32,
	pktSwchXidInternalIndexA
	  Integer32,
	pktSwchXidPasswdA
	  DisplayString,
	pktSwchXidPhoneA
	  DisplayString,
	pktSwchXidStatusA
	  INTEGER
	}

pktSwchXidIndexA OBJECT-TYPE
	SYNTAX  Integer32
	MAX-ACCESS  read-only
	STATUS current
	DESCRIPTION
	" This Index of the XID table."
	::= { pktSwchXidAEntry 1 }

pktSwchXidInternalIndexA OBJECT-TYPE
	SYNTAX  Integer32
	MAX-ACCESS  read-only
	STATUS current
	DESCRIPTION
	"An internal index for each XidIndex of the table. The first 13 entries
	 refer to Incoming calls. The 14th entry refers to an Outgoing call."
	::= { pktSwchXidAEntry 2 }

pktSwchXidPasswdA OBJECT-TYPE
	SYNTAX  DisplayString
	MAX-ACCESS  read-only
	STATUS current
	DESCRIPTION
	"Password of size 16 chars."
	::= { pktSwchXidAEntry 3 }

pktSwchXidPhoneA OBJECT-TYPE
	SYNTAX  DisplayString
	MAX-ACCESS  read-only
	STATUS current
	DESCRIPTION
	"Phone number of size 16 digits."
	::= { pktSwchXidAEntry 4 }

pktSwchXidStatusA OBJECT-TYPE
    SYNTAX  INTEGER {
       valid(1),
       createRequest(2),
       underCreation(3),
       invalid(4)
     }
    MAX-ACCESS  read-only
    STATUS  current
    DESCRIPTION
	"The status of the XID table entry. The status applies to the XidIndex,
	 i.e., setting the staus to invalid results in the removal of all
	 the InternalIndex entries (1..14) belonging to the relevant XidIndex."
  ::= { pktSwchXidAEntry 5 }


pktSwchIpRouting  OBJECT IDENTIFIER ::= { pktSwchSystem 6 }

pktSwchIpRoutSTable    OBJECT-TYPE
    SYNTAX  SEQUENCE  OF PktSwchIpRoutSEntry
    MAX-ACCESS  not-accessible
    STATUS  current
    DESCRIPTION
	"The Scratch Routing Table defines the routes for incoming and
	 outgoing ip datagrams on the device."
    ::=  { pktSwchIpRouting 1 }

pktSwchIpRoutSEntry OBJECT-TYPE
    SYNTAX  PktSwchIpRoutSEntry
    MAX-ACCESS  not-accessible
    STATUS  current
    DESCRIPTION
	"Defines the contents of each line in the Scratch IP Routing
	 Table."
    INDEX   { pktSwchIpRoutIdS }
    ::=  { pktSwchIpRoutSTable 1  }

PktSwchIpRoutSEntry ::=  SEQUENCE {
    pktSwchIpRoutIdS
     Integer32,
    pktSwchIpRoutIpAddressS
     IpAddress,
    pktSwchIpRoutIpMaskS
     IpAddress,
    pktSwchIpRoutDestProtocolS
     INTEGER,
    pktSwchIpRoutDestinationS
     DisplayString,
    pktSwchIpRoutInactivityS
     Integer32,
    pktSwchIpRoutStatusS
     INTEGER,
    pktSwchIpRoutMetricS
     Integer32,
    pktSwchIpRoutNextHopS
     IpAddress,
    pktSwchIpRoutInterfaceIdS
     Integer32
    }

pktSwchIpRoutIdS OBJECT-TYPE
    SYNTAX Integer32 (1..200)
	MAX-ACCESS  read-write
	STATUS  current
	DESCRIPTION
	"Index of the pktSwchIpRoutSTable."
	::= { pktSwchIpRoutSEntry 1 }

pktSwchIpRoutIpAddressS OBJECT-TYPE
    SYNTAX IpAddress
    MAX-ACCESS  read-write
    STATUS  current
    DESCRIPTION
        "The IP address to which the entry applies.
         A string of the format: X.X.X.X
         where every X is a number in the range 0-255."
    ::= { pktSwchIpRoutSEntry 2 }

pktSwchIpRoutIpMaskS OBJECT-TYPE
    SYNTAX 	IpAddress
    MAX-ACCESS  read-write
    STATUS  current
    DESCRIPTION
        "The IP mask to which the entry applies.
         A string of the format: X.X.X.X
         where every X is a number in the range 0-255."
    ::= { pktSwchIpRoutSEntry 3 }

pktSwchIpRoutDestProtocolS OBJECT-TYPE
    SYNTAX  INTEGER {
             slip       (1),
             x25SVC     (2),
             x25PVC     (3),
             frameRelay (4),
             hdlc       (5),
             ethernet   (7),     --  (6) is reserved for snmp agent.
             ppp        (8),
             none      (255)
    }
    MAX-ACCESS  read-write
    STATUS  deprecated
    DESCRIPTION
	"Destination protocol for the associated address.
	 None(255) when not used"
    ::= { pktSwchIpRoutSEntry 4 }

pktSwchIpRoutDestinationS OBJECT-TYPE
    SYNTAX DisplayString
    MAX-ACCESS  read-write
    STATUS  deprecated
    DESCRIPTION
    " Destination for the associated address.
    Possible values:
    Default :     Not Used.
    X.25 PVC:     Port:LCN  or a pre defined PVC number
    X.25 SVC:     X.25 Addr or cid followed by a predefined Call ID number
    Frame Relay:  Port:DLCI
    HDLC:         'H' followed by the HDLC Port Number
    SLIP:         'S' followed by the SLIP Channel Number
    Ethernet:     'E' followed by the Ethernet Port Number
    PPP:          'P' followed by the PPP Port Number."
    ::= { pktSwchIpRoutSEntry 5 }

pktSwchIpRoutInactivityS OBJECT-TYPE
    SYNTAX Integer32
    MAX-ACCESS  read-write
    STATUS  deprecated
    DESCRIPTION
	"Inactivity time in steps of 50 mili seconds for X25 SVC
	 protocol only. Range: 0..255. Default: 2."
    ::= { pktSwchIpRoutSEntry 6 }

pktSwchIpRoutStatusS OBJECT-TYPE
    SYNTAX  INTEGER {
       valid        (1),
       createRequest(2),
       underCreation(3),
       invalid      (4)
    }
    MAX-ACCESS  read-write
    STATUS  current
    DESCRIPTION
	"The status of this routing table entry.  The choices are those
	 defined in the SNMPv2 Textual Conventions for RowStatus.
	 This will allow easy replacement of the INTEGER syntax with
	 the RowStatus textual convention SYNTAX."
  ::= { pktSwchIpRoutSEntry 7 }

pktSwchIpRoutMetricS OBJECT-TYPE
    SYNTAX   Integer32
    MAX-ACCESS  read-write
    STATUS  current
    DESCRIPTION
    "No. of hops for this route.
     The default value is 1.
     Legal values: 1 to the max no. of hops this device will support.
     The max no. is defined by pktSwchIpGlobalMaxHopCount."
    ::= { pktSwchIpRoutSEntry 8 }

pktSwchIpRoutNextHopS OBJECT-TYPE
    SYNTAX  IpAddress
    MAX-ACCESS  read-write
    STATUS  current
    DESCRIPTION
    "IP address of the next hop.
     A string of the format: X.X.X.X
     where every X is a number in the range 0-255."
    ::= { pktSwchIpRoutSEntry 9 }

pktSwchIpRoutInterfaceIdS OBJECT-TYPE
    SYNTAX   Integer32
    MAX-ACCESS  read-write
    STATUS  current
    DESCRIPTION
    "ID of the logical IP interface in the pktSwchIpInterface table.
     The IP routing module will route the IP frame according to this
     interface ID.
     Legal values: 1 to 200 and 65535.
     1-200 : ID of interface.
     65535 : No IP interface ID.
     Default value: 65535."
     ::= { pktSwchIpRoutSEntry 10 }

pktSwchIpRoutATable    OBJECT-TYPE
    SYNTAX  SEQUENCE  OF PktSwchIpRoutAEntry
    MAX-ACCESS  not-accessible
    STATUS  current
    DESCRIPTION
	"The Active Routing Table defines the active routes for incoming
	 and outgoing ip datagrams on the device."
    ::=  { pktSwchIpRouting 2 }

pktSwchIpRoutAEntry OBJECT-TYPE
    SYNTAX  PktSwchIpRoutAEntry
    MAX-ACCESS  not-accessible
    STATUS  current
    DESCRIPTION
	"Defines the contents of each line in the Active IP Routing Table."
    INDEX   { pktSwchIpRoutIdA }
    ::=  { pktSwchIpRoutATable 1  }

PktSwchIpRoutAEntry ::=  SEQUENCE {
    pktSwchIpRoutIdA
     Integer32,
    pktSwchIpRoutIpAddressA
     IpAddress,
    pktSwchIpRoutIpMaskA
     IpAddress,
    pktSwchIpRoutDestProtocolA
     INTEGER,
    pktSwchIpRoutDestinationA
     DisplayString,
    pktSwchIpRoutInactivityA
     Integer32,
    pktSwchIpRoutBuffsInA
     Counter32,
    pktSwchIpRoutBuffsOutA
     Counter32,
    pktSwchIpRoutFCA
     INTEGER,
    pktSwchIpRoutMetricA
     Integer32,
    pktSwchIpRoutNextHopA
     IpAddress,
    pktSwchIpRoutInterfaceIdA
     Integer32
    }


pktSwchIpRoutIdA OBJECT-TYPE
    SYNTAX Integer32 (1..200)
    MAX-ACCESS  read-only
	STATUS  current
	DESCRIPTION
	"Index of the IP pktSwchIpRoutATable."
	::= { pktSwchIpRoutAEntry 1 }


pktSwchIpRoutIpAddressA OBJECT-TYPE
    SYNTAX IpAddress
    MAX-ACCESS  read-only
    STATUS  current
    DESCRIPTION
        "The IP address to which the entry applies.
         A string of the format: X.X.X.X
         where every X is a number in the range 0-255."
    ::= { pktSwchIpRoutAEntry 2 }

pktSwchIpRoutIpMaskA OBJECT-TYPE
    SYNTAX 	IpAddress
    MAX-ACCESS  read-only
    STATUS  current
    DESCRIPTION
        "The IP mask to which the entry applies.
         A string of the format: X.X.X.X
         where every X is a number in the range 0-255."
    ::= { pktSwchIpRoutAEntry 3 }


pktSwchIpRoutDestProtocolA OBJECT-TYPE
    SYNTAX  INTEGER {
             slip       (1),
             x25SVC     (2),
             x25PVC     (3),
             frameRelay (4),
             hdlc       (5),
             snmpAgent  (6),
             ethernet   (7),
             ppp        (8),
             none      (255)
    }
    MAX-ACCESS  read-only
    STATUS  deprecated
    DESCRIPTION
	"Destination protocol for the associated address.
	 None(255) when not used."
    ::= { pktSwchIpRoutAEntry 4 }

pktSwchIpRoutDestinationA OBJECT-TYPE
    SYNTAX DisplayString
    MAX-ACCESS  read-only
    STATUS  deprecated
    DESCRIPTION
    " Destination for the associated address.
    Possible values:
    Default :     Not Used.
    X.25 PVC:     Port:LCN  or a pre defined PVC number
    X.25 SVC:     X.25 Addr or cid followed by a predefined Call ID number
    Frame Relay:  Port:DLCI
    HDLC:         'H' followed by the HDLC Port Number
    SLIP:         'S' followed by the SLIP Channel Number
    Ethernet:     'E' followed by the Ethernet Port Number
    PPP:          'P' followed by the PPP Port Number."
    ::= { pktSwchIpRoutAEntry 5 }


pktSwchIpRoutInactivityA OBJECT-TYPE
    SYNTAX Integer32
    MAX-ACCESS  read-only
    STATUS  deprecated
    DESCRIPTION
	"Inactivity time in steps of 50 mili seconds for X25 SVC
	 protocol only. Range: 0..255. Default: 2."
    ::= { pktSwchIpRoutAEntry 6 }

pktSwchIpRoutBuffsInA OBJECT-TYPE
    SYNTAX  Counter32
    MAX-ACCESS  read-only
    STATUS  current
    DESCRIPTION
    "The number of packets in the Input buffer link list,
     received but not routed yet."
    ::= { pktSwchIpRoutAEntry 7 }

pktSwchIpRoutBuffsOutA OBJECT-TYPE
    SYNTAX  Counter32
    MAX-ACCESS  read-only
    STATUS  current
    DESCRIPTION
    "The number of packets in the Output buffer link list,
     routed but not sent yet."
    ::= { pktSwchIpRoutAEntry 8 }

pktSwchIpRoutFCA OBJECT-TYPE
    SYNTAX  INTEGER {
             discard (1),
             flowControl (2),
             normal (3)
    }
    MAX-ACCESS  read-only
    STATUS  current
    DESCRIPTION
        "This is the flow control status of this ip routing
         entry\connection"
    ::= { pktSwchIpRoutAEntry 9 }

pktSwchIpRoutMetricA OBJECT-TYPE
    SYNTAX   Integer32
    MAX-ACCESS  read-only
    STATUS  current
    DESCRIPTION
    "No. of hops for this route.
     The default value is 1.
     Legal values: 1 to the max no. of hops this device will support.
     The max no. is defined by pktSwchIpGlobalMaxHopCount."
    ::= { pktSwchIpRoutAEntry 10 }

pktSwchIpRoutNextHopA OBJECT-TYPE
    SYNTAX  IpAddress
    MAX-ACCESS  read-only
    STATUS  current
    DESCRIPTION
    "IP address of the next hop.
     A string of the format: X.X.X.X
     where every X is a number in the range 0-255."
    ::= { pktSwchIpRoutAEntry 11 }

pktSwchIpRoutInterfaceIdA OBJECT-TYPE
    SYNTAX   Integer32
    MAX-ACCESS  read-only
    STATUS  current
    DESCRIPTION
    "ID of the logical IP interface in the pktSwchIpInterface table.
     The IP routing module will route the IP frame according to this
     interface ID.
     Legal values: 1 to 200 and 65535.
     1-200 : ID of interface.
     65535 : No IP interface ID.
     Default value: 65535."
     ::= { pktSwchIpRoutAEntry 12 }

-- System Priorities

pktSwchPriority  OBJECT IDENTIFIER ::= { pktSwchSystem 7 }

-- This is a table of Tx Priorities.
-- At present, it is used for DLCIs. There are 4 levels of priorities.
-- Each level contains 2 parameters: max delay time and max queue length.

-- This is a status which is used for saving the Tx Priority table.
pktSwchTxPriorityStatus OBJECT-TYPE
    SYNTAX  INTEGER {
       valid(1),
       underCreation(3)
     }
    MAX-ACCESS  read-write
    STATUS  current
    DESCRIPTION
    "The status of the Priorities table.
     Used for saving the Priority parameters. "
         ::= {pktSwchPriority 1}

pktSwchTxPriorityTable    OBJECT-TYPE
    SYNTAX  SEQUENCE  OF PktSwchTxPriorityEntry
    MAX-ACCESS  not-accessible
    STATUS  current
    DESCRIPTION
        "The Tx Priorities table."
         ::= {pktSwchPriority 2}

pktSwchTxPriorityEntry OBJECT-TYPE
    SYNTAX  PktSwchTxPriorityEntry
    MAX-ACCESS  not-accessible
    STATUS  current
    DESCRIPTION
        "The Tx Priority Entry defines the max delay time and max queue
         length for each Priority level."
    INDEX   {pktSwchTxPriorityLevel}
    ::=  { pktSwchTxPriorityTable 1 }

PktSwchTxPriorityEntry ::= SEQUENCE {
pktSwchTxPriorityLevel
Integer32,
pktSwchTxPriorityMaxDelayTime
Integer32,
pktSwchTxPriorityMaxQueueLen
Integer32     }

pktSwchTxPriorityLevel  OBJECT-TYPE
    SYNTAX Integer32 (1..4)
    MAX-ACCESS  read-only
    STATUS  current
    DESCRIPTION
        "Level of an entry in the Tx Priority Table.
         At present, the PS supports 4 priority levels.
         Default level: 1"
    ::= { pktSwchTxPriorityEntry 1 }

pktSwchTxPriorityMaxDelayTime  OBJECT-TYPE
    SYNTAX Integer32 (0..60000)
    MAX-ACCESS  read-write
    STATUS  current
    DESCRIPTION
        "Max delay time in Tx queue (in 100 msec intervals).
         Each frame will wait no more than the Max delay time until
         it is handled.
         0 means that the delay is Unlimited.
         Default value: 0"
    ::= { pktSwchTxPriorityEntry 2 }


pktSwchTxPriorityMaxQueueLen  OBJECT-TYPE
    SYNTAX Integer32 (0..65535)
    MAX-ACCESS  read-write
    STATUS  current
    DESCRIPTION
        "Max allowed length of the Tx queue. Frames will be discarded
         if the length is exceeded.
         0 means that the queue is of Unlimited length.
         Default value: 0"
    ::= { pktSwchTxPriorityEntry 3 }


-- The PS Async Group contains the Profile Table, the Channel Table,
-- the Call ID Table, the Alias Table, and the AsyncStat Table

pktSwchAsync    OBJECT IDENTIFIER ::= { radPS 2 }

-- pktSwchProfile defines the (Scratch and Active) profiles that the Packet Switch devices can use to configure a channel

pktSwchProfile 	OBJECT IDENTIFIER ::= { pktSwchAsync 1 }

-- pktSwchProfileSTable defines the Scratch profiles that the Packet Switch devices can use to configure a channel

pktSwchProfileSTable    OBJECT-TYPE
    SYNTAX  SEQUENCE  OF PktSwchProfileSEntry
    MAX-ACCESS  not-accessible
    STATUS  current
    DESCRIPTION
	"The Profile Table S defines the Scratch profiles that the PS can use to configure
   	a channel."
    ::=  { pktSwchProfile 1 }

pktSwchProfileSEntry OBJECT-TYPE
    SYNTAX  PktSwchProfileSEntry
    MAX-ACCESS  not-accessible
    STATUS  current
    DESCRIPTION
	"Defines the contents of each line in the Profile Table S."
    INDEX   { pktSwchProfileNumberS }
    ::=  { pktSwchProfileSTable 1  }

PktSwchProfileSEntry ::= SEQUENCE {
    pktSwchProfileNumberS
     Integer32,
    pktSwchProfileRecallCharS
     Integer32,
    pktSwchProfileEchoS
     INTEGER,
    pktSwchProfileDataForwCharS
     Integer32,
    pktSwchProfileIdleTimerS
     Integer32,
    pktSwchProfileDevFlowContS
     INTEGER,
    pktSwchProfileServSigS
     INTEGER,
    pktSwchProfileBreakS
     Integer32,
    pktSwchProfileDiscOutS
     INTEGER,
    pktSwchProfileCRPaddingS
     Integer32,
    pktSwchProfileLineFoldS
     Integer32,
    pktSwchProfileSpeedS
     INTEGER,
    pktSwchProfilePadFlowContS
     INTEGER,
    pktSwchProfileLineFeedInsertS
     INTEGER,
    pktSwchProfileLineFeedPadS
     Integer32,
    pktSwchProfileEditingS
     INTEGER,
    pktSwchProfileCharDelS
     Integer32,
	pktSwchProfileLineDelS
     Integer32,
    pktSwchProfileLineDispS
     Integer32,
    pktSwchProfileEditServSigS
     Integer32,
    pktSwchProfileEchomaskS
     Integer32,
    pktSwchProfileParTreatS
     INTEGER,
    pktSwchProfilePageWaitS
     Integer32,
    pktSwchProfileBitsPerCharS
     Integer32,
    pktSwchProfileDvParityS
     INTEGER,
    pktSwchProfileStopBitsS
     INTEGER,
    pktSwchProfileSpecFlowS
     INTEGER,
    pktSwchProfileCountFwdS
     Integer32,
    pktSwchProfileEscDelayS
     Integer32,
    pktSwchProfileCharBreakS
     Integer32,
    pktSwchProfileCharSuppressS
     Integer32,
    pktSwchProfileCharSubsS
     Integer32,
    pktSwchProfileFormFeedPadS
     Integer32,
    pktSwchProfileInactivityS
     Integer32,
    pktSwchProfileOptionsS
     Integer32,
    pktSwchProfileClrTimerS
     Integer32,
    pktSwchProfileSubAddInCUDS
     Integer32,
    pktSwchProfileStatusS
     INTEGER
    }

pktSwchProfileNumberS  OBJECT-TYPE
    SYNTAX Integer32 (1..200)
    MAX-ACCESS  read-only
    STATUS  current
    DESCRIPTION
	"The number by which a profile is identified.  This is also used as the index for the profile table.
		 The maximum profile number is 200."
    ::= { pktSwchProfileSEntry 1  }

pktSwchProfileRecallCharS  OBJECT-TYPE
    SYNTAX Integer32 (0..126)
    MAX-ACCESS  read-write
    STATUS  current
    DESCRIPTION
	"The character specified by this entry is used to escape from the data transfer
		 mode and enter the PAD command mode.  The integer values have the following meanings:
			 (0)                 PAD recall is not possible
			 (1)                 The PAD recall character is DLE
			 (2)  to (126)  The PAD recall character is specified by the user by entering its ASCII
		code."
    ::= { pktSwchProfileSEntry 2  }

pktSwchProfileEchoS OBJECT-TYPE
    SYNTAX  INTEGER {
       echEn(1),
       noEch(2)
     }
    MAX-ACCESS  read-write
    STATUS  current
    DESCRIPTION
	"This determines if an echo of the input characters is retured to the DTE.
		 The options are either  'echo enabled'  or 'no echo'."
   ::= { pktSwchProfileSEntry 3  }

pktSwchProfileDataForwCharS OBJECT-TYPE
    SYNTAX  Integer32 (0..127)
    MAX-ACCESS  read-write
    STATUS  current
    DESCRIPTION
	"The value is a sum of values (powers of two), where each value in the sum represents
		a character (or characters) that is (are) used as a data forwarding character.  The data
		forwarding characters are used to instruct the PAD to complete the assembly of and to
		forward a packet containing the data accumulated up to the reception of such a character.
		The values that may be included in the sum and their meanings are:
		0   Data forwarding characters are not used
		1   Alpha-numeric characters (A to Z, a to z, 0 to 9, inclusive)
		2   Character CR
		4   Characters ESC, BEL, ENQ, ACK
		8   Characters DEL, CAN, DC2
		16 Characters EOT, ETX
		32 Characters HT, LF, VT, FF
		64 All the other characters in colums 0 and 1 of IA5 and not listed above."
   ::= { pktSwchProfileSEntry 4 }

pktSwchProfileIdleTimerS OBJECT-TYPE
    SYNTAX  Integer32 (0..255)
    MAX-ACCESS  read-write
    STATUS  current
    DESCRIPTION
	"Packets will be forwarded when the idle timer expires.  The idle time interval is specified
		 as a multiple of 50 milliseconds.  The multiple is given by the parameter value.  For example,
		 a value of 60 sets an interval of 3 seconds.  If the parameter value is 0, no forwarding occurs
		 after the idle condition."
   ::= { pktSwchProfileSEntry 5 }

pktSwchProfileDevFlowContS OBJECT-TYPE
    SYNTAX  INTEGER  {
       trans(1),
       transAndCom(2),
       noFlow(255)
    }
    MAX-ACCESS  read-write
    STATUS  current
    DESCRIPTION
	"This parameter determines whether or not the PAD uses software flow control for the
		attached device.  The options are either (1) PAD uses flow control during data transfer
		 mode, (2) PAD uses flow control both in the data transfer mode and in the command mode,
		 or (255) PAD does not use flow control."
   ::= { pktSwchProfileSEntry 6 }

pktSwchProfileServSigS OBJECT-TYPE
    SYNTAX  INTEGER  {
       serv(1),
       prompt(4),
       servAndPrompt(5),
       noSig(255)
    }
    MAX-ACCESS  read-write
    STATUS  current
    DESCRIPTION
	"This parameter is used to instruct the PAD whether to transfer PAD service signals and
		 the PAD prompt to the local DTE in standard format.  The options are (1) PAD service
		 signals are transmitted to the DTE using the standard format, (4) The PAD prompt is
		 transmitted using the standard format, (5) PAD service signals and the PAD prompt are
		 transmitted in the standard format, or (255) No PAD service signals are transmitted to the
		 DTE."
    ::= { pktSwchProfileSEntry 7 }

pktSwchProfileBreakS OBJECT-TYPE
    SYNTAX  Integer32 (0..31)
    MAX-ACCESS  read-write
    STATUS  current
    DESCRIPTION
	"The value is a sum of values (powers of two), where each value in the sum represents
		a PAD operation on receipt of the break signal from the DTE.
		The values that may be included in the sum and their meanings are:
		0   Nothing
		1   Send interrupt packet to network
		2   Send RESET packet to network
		4   Send and 'indication of break' message
		8   Escape from data transfer mode
		16 Discard output data waiting to be sent to the DTE ."
   ::= { pktSwchProfileSEntry 8 }

pktSwchProfileDiscOutS OBJECT-TYPE
    SYNTAX  INTEGER {
       discOut(1),
       normal(2)
     }
    MAX-ACCESS  read-only
    STATUS  current
    DESCRIPTION
	"This parameter instructs the PAD whether to forward the user sequences included in
		data packets to the local DTE or discard them.  The options are (1) discard output or
		 (2) normal data delivery.  If the value of radSPSProfileBreak is 21, the value of
		 pktSwchProfileDiscOut is automatically set to (1) when a break signal is received."
   ::= { pktSwchProfileSEntry 9  }

pktSwchProfileCRPaddingS OBJECT-TYPE
    SYNTAX  Integer32 (0..127)
    MAX-ACCESS  read-write
    STATUS  current
    DESCRIPTION
	"This parameter specifies the number of padding characters to be added after a carriage
		 return character is transmitted to the local DTE."
   ::= { pktSwchProfileSEntry 10}

pktSwchProfileLineFoldS OBJECT-TYPE
    SYNTAX  Integer32 (0..255)
    MAX-ACCESS  read-write
    STATUS  current
    DESCRIPTION
	"This parameter specifies the maximum number of characters to be inserted before the
		 format effector.  If the value is zero, there is no insertion of a format effector (line folding)."
    ::= { pktSwchProfileSEntry 11}

pktSwchProfileSpeedS OBJECT-TYPE
    SYNTAX  INTEGER  {
       s110bps(1),
       s300bps(2),
       s1200bps(3),
       s600bps(4),
       s75bps(5),
       s150bps(6),
       s2400bps(12),
       s4800bps(13),
       s9600bps(14),
       s19200bps(15),
       s38400bps(19),
	   s57600bps(20),
	   s115200bps(21)
    }
    MAX-ACCESS  read-write
    STATUS  current
    DESCRIPTION
	"This parameter determines the rate of data transmission to and from the DTE."
    ::= { pktSwchProfileSEntry 12 }

pktSwchProfilePadFlowContS OBJECT-TYPE
    SYNTAX  INTEGER {
       flowCont(1),
       noFlowCont(2)
     }
    MAX-ACCESS  read-write
    STATUS  current
    DESCRIPTION
	"This determines whether or not the terminal can exercise flow control over the PAD.
		 The options are either 'device can exercise flow control' or 'device cannot exercise flow
		 control."
   ::= { pktSwchProfileSEntry 13  }

pktSwchProfileLineFeedInsertS OBJECT-TYPE
    SYNTAX  INTEGER  {
       afterCR(1),
       recCR(2),
       echoCR(4),
       onePlusFour(5),
       twoPlusFour(6),
       oneTwoFour(7),
       noFeed(255)
    }
    MAX-ACCESS  read-write
    STATUS  current
    DESCRIPTION
	"This parameter indicates when there is a line feed insertion after CR.  The options are
		  (1) Insert line feed after transmission of CR to the DTE, (2) Insert line feed after receipt
		 of CR from the DTE, (4) Insert line feed after echoing a CR character to the DTE,
		 (5) Combination of (1) and (4), (6) Insert line feed after any CR to the DTE (combination of
		 (2) and (4)), (7) Combination of (1), (2), and (4), or (255) No line feed insertion."
    ::= { pktSwchProfileSEntry 14 }

pktSwchProfileLineFeedPadS OBJECT-TYPE
    SYNTAX  Integer32 (0..127)
    MAX-ACCESS  read-write
    STATUS  current
    DESCRIPTION
	"This parameter specifies the number of padding characters to be added after a line
		 feed."
   ::= { pktSwchProfileSEntry 15 }

pktSwchProfileEditingS OBJECT-TYPE
    SYNTAX  INTEGER {
       edit(1),
       noEdit(2)
     }
    MAX-ACCESS  read-write
    STATUS  current
    DESCRIPTION
	"This parameter specifies the editing capabilities available in the data transfer mode.
		Editing is always possible when the PAD is in the command mode.  The options are
		 (1) Command editing in the data trasfer mode is enabled or (2) No command editing
		 in the data transfer mode."
   ::= { pktSwchProfileSEntry 16  }

pktSwchProfileCharDelS OBJECT-TYPE
    SYNTAX  Integer32 (0..127)
    MAX-ACCESS  read-write
    STATUS  current
    DESCRIPTION
	"This parameter specifies the character delete, which is one character from IA5.  The default
		selection is 127 (character DEL)."
   ::= { pktSwchProfileSEntry 17}


pktSwchProfileLineDelS OBJECT-TYPE
    SYNTAX  Integer32 (0..127)
    MAX-ACCESS  read-write
    STATUS  current
    DESCRIPTION
	"This parameter specifies the line delete (last line stored in the edit buffer), which is one character from IA5.  The default
		selection is 24 (character CAN)."
   ::= { pktSwchProfileSEntry 18}

pktSwchProfileLineDispS OBJECT-TYPE
    SYNTAX  Integer32 (0..127)
    MAX-ACCESS  read-write
    STATUS  current
    DESCRIPTION
	"This entry specifies the line display character, which is one character
		from IA5.  The default selection is 18 (character DC2)."
   ::= { pktSwchProfileSEntry 19}

pktSwchProfileEditServSigS  OBJECT-TYPE
    SYNTAX Integer32 (0..126)
    MAX-ACCESS  read-write
    STATUS  current
    DESCRIPTION
	"This entry specifies the editing PAD service signals.
		The integer values have the following meanings:
			 (0)                 No editing PAD service signals
			 (1)                 Editing PAD service signals for printing terminals
			 (2)                 Editing PAD service signals for display terminals
			 (3)  to (126)  Editing PAD service signals using the desired character from IA5."
    ::= { pktSwchProfileSEntry 20  }

pktSwchProfileEchomaskS OBJECT-TYPE
    SYNTAX  Integer32 (0..255)
    MAX-ACCESS  read-write
    STATUS  current
    DESCRIPTION
	"The value is a sum of values (powers of two), where each value in the sum represents
		a character (or characters) that is (are) included in the echo mask.  The characters in the
		echo mask are not echoed to the DTE when PAD echo is enabled.
		The values that may be included in the sum and their meanings are:
		0   No echo mask (all the characters are echoed)
		1   No echo of character CR
		2   No echo of character LF
		4   No echo of characters VT, HT, FF
		8   No echo of characters BEL, BS
		16 No echo of characters ESC, ENQ
		32 No echo of characters ACK, NAK, STX, SOH, EOT, ETB, ETX
		64 No echo of the editing characters selected by radSPSProfileCharDel,
														       radSPSProfileLineDel, and
														       radSPSProfileLineDisp
				128 No echo of the DEL character and of all the other characters in the range of
					ASCII 00 through 31 not mentioned above."
	::= { pktSwchProfileSEntry 21 }

pktSwchProfileParTreatS OBJECT-TYPE
    SYNTAX  INTEGER  {
       parCheck(1),
       parGen(2),
       checkAndGen(3),
       noPar(255)
    }
    MAX-ACCESS  read-write
    STATUS  current
    DESCRIPTION
	"This entry controls the generation of parity bits in the data sent to the local DTE and the
		checking of the parity bit when generated by the local DTE.  The options are (1) parity
		checking is enabled, (2) parity generation is enabled, (3) parity checking and generation are
		enabled, or (255) no parity checking nor parity generation."
    ::= { pktSwchProfileSEntry 22 }

pktSwchProfilePageWaitS OBJECT-TYPE
    SYNTAX  Integer32 (0..255)
    MAX-ACCESS  read-write
    STATUS  current
    DESCRIPTION
	"This entry specifies the number of line feed characters counted by the PAD before the
		page wait condition is entered.  If the value is zero, page wait is disabled."
   ::= { pktSwchProfileSEntry 23}

pktSwchProfileBitsPerCharS  OBJECT-TYPE
    SYNTAX Integer32 (5..8)
    MAX-ACCESS  read-write
    STATUS  current
    DESCRIPTION
	"The number of data bits per character supported by the PAD."
    ::= { pktSwchProfileSEntry 24 }

pktSwchProfileDvParityS OBJECT-TYPE
    SYNTAX  INTEGER  {
       space(1),
       mark(2),
       even(3),
       odd(4),
       none(255)
    }
    MAX-ACCESS  read-write
    STATUS  current
    DESCRIPTION
	"This entry selects the type of parity to be checked and or generated by the PAD
		 when radSPSProfileParTreat is a value other than 255.  The options are
		  (1) space parity, (2) mark parity, (3) even parity, (4) odd parity, or (255) no parity."
    ::= { pktSwchProfileSEntry 25 }

pktSwchProfileStopBitsS OBJECT-TYPE
    SYNTAX  INTEGER  {
       one(1),
       two(2),
       oneAndHalf(3)
    }
    MAX-ACCESS  read-write
    STATUS  current
    DESCRIPTION
	"This entry indicates the number of stop bits per character supported by the PAD.
		The options are either (1) one stop bit, (2) two stop bits, or (3) 1.5 stop bits."
   ::= { pktSwchProfileSEntry 26 }

pktSwchProfileSpecFlowS OBJECT-TYPE
    SYNTAX  INTEGER {
       spec(1),
       noSpec(2)
     }
    MAX-ACCESS  read-write
    STATUS  current
    DESCRIPTION
	"This entry is used to define additional flow control possiblilites.
		 The options are either  (1) Flow control by means of the terminal DTR line
		 or (2) No special flow control."
   ::= { pktSwchProfileSEntry 27  }

pktSwchProfileCountFwdS OBJECT-TYPE
    SYNTAX  Integer32 (0..255)
    MAX-ACCESS  read-write
    STATUS  current
    DESCRIPTION
	"This entry can be used to instruct the PAD to complete the assembly of a packet
		and to forward it after the specifed number of characters has been received.
		If the value is zero, count forwarding is disabled."
   ::= { pktSwchProfileSEntry 28}

pktSwchProfileEscDelayS OBJECT-TYPE
    SYNTAX  Integer32 (0..255)
    MAX-ACCESS  read-write
    STATUS  current
    DESCRIPTION
"This entry can be used to instruct the PAD whether to delay the forwarding of
a data packet when an escape character is detected in the data stream and to
determine the required delay.  The packet forwarding is delayed until the specified
number of characters is received after the escape character.  A value of zero indicates
no special handling( at the moment up to 10 chars are accepted)."
   ::= { pktSwchProfileSEntry 29}

pktSwchProfileCharBreakS OBJECT-TYPE
    SYNTAX  Integer32 (0..127)
    MAX-ACCESS  read-write
    STATUS  current
    DESCRIPTION
	"This entry specifies the decimal value of the character that will be interpreted
		as an additional break signal by the PAD.  A value of zero indicates no break character."
   ::= { pktSwchProfileSEntry 30}

pktSwchProfileCharSuppressS OBJECT-TYPE
    SYNTAX  Integer32 (0..127)
    MAX-ACCESS  read-write
    STATUS  current
    DESCRIPTION
	"This entry specifies the decimal value of the character that will toggle
		echo suppression in the PAD.  A value of zero indicates that echo suppression
		 is only controlled by radSPSProfileEcho."
   ::= { pktSwchProfileSEntry 31}

pktSwchProfileCharSubsS OBJECT-TYPE
    SYNTAX  Integer32 (0..127)
    MAX-ACCESS  read-write
    STATUS  current
    DESCRIPTION
	"This entry specifies the decimal value of the character that will be echoed
		instead of the character received from the user's DTE.  A zero value indicates that
		 no character is echoed."
   ::= { pktSwchProfileSEntry 32}

pktSwchProfileFormFeedPadS OBJECT-TYPE
    SYNTAX  Integer32 (0..127)
    MAX-ACCESS  read-write
    STATUS  current
    DESCRIPTION
	"This entry specifies the number of padding (NUL) characters that will be
		automatically sent after the form feed character."
   ::= { pktSwchProfileSEntry 33}

pktSwchProfileInactivityS OBJECT-TYPE
    SYNTAX  Integer32 (0..255)
    MAX-ACCESS  read-write
    STATUS  current
    DESCRIPTION
	"This entry specifies the number of minutes after which the PAD will forward
		the accumulated data and clear the call.  A zero value indicates no disconnection
		on inactivity."
   ::= { pktSwchProfileSEntry 34 }

pktSwchProfileOptionsS OBJECT-TYPE
    SYNTAX  Integer32 (0..255)
    MAX-ACCESS  read-write
    STATUS  current
    DESCRIPTION
	"This entry defines several options to control the profile.  The value is a sum of values
		(powers of two), where each value in the sum represents an option .
	The values that may be included in the sum and their meanings are:
		0   No options
		1   Remote set of local X.3 parameters through X.29 is disabled
		2   Add sub address to call request
		4   Don't use protocol ID in user data field.
		8   SPRINT NUI format
		16  More bit is set when the edit buffer is full
        32  Extended error message
        64  Discard  connect extended service signal
        128 enable connect by typing the address w/out a command"
   ::= { pktSwchProfileSEntry 35 }

pktSwchProfileClrTimerS OBJECT-TYPE
    SYNTAX  Integer32 (0..255)
    MAX-ACCESS  read-write
    STATUS  current
    DESCRIPTION
	"This entry specifies the number of minutes after which a call is cleared.
		  If the parameter value is 0, there is no disconnection timer."
   ::= { pktSwchProfileSEntry 36 }

pktSwchProfileSubAddInCUDS OBJECT-TYPE
    SYNTAX  Integer32 (0..5)
    MAX-ACCESS  read-write
    STATUS  current
    DESCRIPTION
	"This entry defines the number of digits for the subaddress in CUD."
    ::= { pktSwchProfileSEntry 37 }

pktSwchProfileStatusS OBJECT-TYPE
    SYNTAX  INTEGER {
       valid(1),
       createRequest(2),
       underCreation(3),
       invalid(4)
     }
    MAX-ACCESS  read-write
    STATUS  current
    DESCRIPTION
	"The status of this profile.  The choices are those defined in the SNMPv2 Textual Conventions
		 for RowStatus.  This will allow easy replacement of the INTEGER syntax with the RowStatus
		 textual convention SYNTAX."
  ::= { pktSwchProfileSEntry 38 }

-- pktSwchProfileATable defines the Active profiles that the Packet Switch devices can use to configure a channel


pktSwchProfileATable    OBJECT-TYPE
    SYNTAX  SEQUENCE  OF PktSwchProfileAEntry
    MAX-ACCESS  not-accessible
    STATUS  current
    DESCRIPTION
	"The Profile Table defines the profiles that the PS can use to configure
	a channel."
    ::=  { pktSwchProfile 2 }

pktSwchProfileAEntry OBJECT-TYPE
    SYNTAX  PktSwchProfileAEntry
    MAX-ACCESS  not-accessible
    STATUS  current
    DESCRIPTION
	"Defines the contents of each line in the Profile Table."
    INDEX   { pktSwchProfileNumberA }
    ::=  { pktSwchProfileATable 1  }

PktSwchProfileAEntry ::= SEQUENCE {
    pktSwchProfileNumberA
     Integer32,
    pktSwchProfileRecallCharA
     Integer32,
    pktSwchProfileEchoA
     INTEGER,
    pktSwchProfileDataForwCharA
     Integer32,
    pktSwchProfileIdleTimerA
     Integer32,
    pktSwchProfileDevFlowContA
     INTEGER,
    pktSwchProfileServSigA
     INTEGER,
    pktSwchProfileBreakA
     Integer32,
    pktSwchProfileDiscOutA
     INTEGER,
    pktSwchProfileCRPaddingA
     Integer32,
    pktSwchProfileLineFoldA
     Integer32,
    pktSwchProfileSpeedA
     INTEGER,
    pktSwchProfilePadFlowContA
     INTEGER,
    pktSwchProfileLineFeedInsertA
     INTEGER,
    pktSwchProfileLineFeedPadA
     Integer32,
    pktSwchProfileEditingA
     INTEGER,
    pktSwchProfileCharDelA
     Integer32,
	pktSwchProfileLineDelA
     Integer32,
    pktSwchProfileLineDispA
     Integer32,
    pktSwchProfileEditServSigA
     Integer32,
    pktSwchProfileEchomaskA
     Integer32,
    pktSwchProfileParTreatA
     INTEGER,
    pktSwchProfilePageWaitA
     Integer32,
    pktSwchProfileBitsPerCharA
     Integer32,
    pktSwchProfileDvParityA
     INTEGER,
    pktSwchProfileStopBitsA
     INTEGER,
    pktSwchProfileSpecFlowA
     INTEGER,
    pktSwchProfileCountFwdA
     Integer32,
    pktSwchProfileEscDelayA
     Integer32,
    pktSwchProfileCharBreakA
     Integer32,
    pktSwchProfileCharSuppressA
     Integer32,
    pktSwchProfileCharSubsA
     Integer32,
    pktSwchProfileFormFeedPadA
     Integer32,
    pktSwchProfileInactivityA
     Integer32,
    pktSwchProfileOptionsA
     Integer32,
    pktSwchProfileClrTimerA
     Integer32,
    pktSwchProfileSubAddInCUDA
     Integer32
    }

pktSwchProfileNumberA  OBJECT-TYPE
    SYNTAX Integer32 (1..200)
    MAX-ACCESS  read-only
    STATUS  current
    DESCRIPTION
	"The number by which a profile is identified.  This is also used as the index for the profile table.
		 The maximum profile number is 200."
    ::= { pktSwchProfileAEntry 1  }

pktSwchProfileRecallCharA  OBJECT-TYPE
    SYNTAX Integer32 (0..126)
    MAX-ACCESS  read-only
    STATUS  current
    DESCRIPTION
	"The character specified by this entry is used to escape from the data transfer
		 mode and enter the PAD command mode.  The integer values have the following meanings:
			 (0)                 PAD recall is not possible
			 (1)                 The PAD recall character is DLE
			 (2)  to (126)  The PAD recall character is specified by the user by entering its ASCII
		code."
    ::= { pktSwchProfileAEntry 2  }

pktSwchProfileEchoA OBJECT-TYPE
    SYNTAX  INTEGER {
       echEn(1),
       noEch(2)
     }
    MAX-ACCESS  read-only
    STATUS  current
    DESCRIPTION
	"This determines if an echo of the input characters is retured to the DTE.
		 The options are either  'echo enabled'  or 'no echo'."
   ::= { pktSwchProfileAEntry 3  }

pktSwchProfileDataForwCharA OBJECT-TYPE
    SYNTAX  Integer32 (0..127)
    MAX-ACCESS  read-only
    STATUS  current
    DESCRIPTION
	"The value is a sum of values (powers of two), where each value in the sum represents
		a character (or characters) that is (are) used as a data forwarding character.  The data
		forwarding characters are used to instruct the PAD to complete the assembly of and to
		forward a packet containing the data accumulated up to the reception of such a character.
		The values that may be included in the sum and their meanings are:
		0   Data forwarding characters are not used
		1   Alpha-numeric characters (A to Z, a to z, 0 to 9, inclusive)
		2   Character CR
		4   Characters ESC, BEL, ENQ, ACK
		8   Characters DEL, CAN, DC2
		16 Characters EOT, ETX
		32 Characters HT, LF, VT, FF
		64 All the other characters in colums 0 and 1 of IA5 and not listed above."
   ::= { pktSwchProfileAEntry 4 }

pktSwchProfileIdleTimerA OBJECT-TYPE
    SYNTAX  Integer32 (0..255)
    MAX-ACCESS  read-only
    STATUS  current
    DESCRIPTION
	"Packets will be forwarded when the idle timer expires.  The idle time interval is specified
		 as a multiple of 50 milliseconds.  The multiple is given by the parameter value.  For example,
		 a value of 60 sets an interval of 3 seconds.  If the parameter value is 0, no forwarding occurs
		 after the idle condition."
   ::= { pktSwchProfileAEntry 5 }

pktSwchProfileDevFlowContA OBJECT-TYPE
    SYNTAX  INTEGER  {
       trans(1),
       transAndCom(2),
       noFlow(255)
    }
    MAX-ACCESS  read-only
    STATUS  current
    DESCRIPTION
	"This parameter determines whether or not the PAD uses software flow control for the
		attached device.  The options are either (1) PAD uses flow control during data transfer
		 mode, (2) PAD uses flow control both in the data transfer mode and in the command mode,
		 or (255) PAD does not use flow control."
   ::= { pktSwchProfileAEntry 6 }

pktSwchProfileServSigA OBJECT-TYPE
    SYNTAX  INTEGER  {
       serv(1),
       prompt(4),
       servAndPrompt(5),
       noSig(255)
    }
    MAX-ACCESS  read-only
    STATUS  current
    DESCRIPTION
	"This parameter is used to instruct the PAD whether to transfer PAD service signals and
		 the PAD prompt to the local DTE in standard format.  The options are (1) PAD service
		 signals are transmitted to the DTE using the standard format, (4) The PAD prompt is
		 transmitted using the standard format, (5) PAD service signals and the PAD prompt are
		 transmitted in the standard format, or (255) No PAD service signals are transmitted to the
		 DTE."
    ::= { pktSwchProfileAEntry 7 }

pktSwchProfileBreakA OBJECT-TYPE
    SYNTAX  Integer32 (0..31)
    MAX-ACCESS  read-only
    STATUS  current
    DESCRIPTION
	"The value is a sum of values (powers of two), where each value in the sum represents
		a PAD operation on receipt of the break signal from the DTE.
		The values that may be included in the sum and their meanings are:
		0   Nothing
		1   Send interrupt packet to network
		2   Send RESET packet to network
		4   Send and 'indication of break' message
		8   Escape from data transfer mode
		16 Discard output data waiting to be sent to the DTE ."
   ::= { pktSwchProfileAEntry 8 }

pktSwchProfileDiscOutA OBJECT-TYPE
    SYNTAX  INTEGER {
       discOut(1),
       normal(2)
     }
    MAX-ACCESS  read-only
    STATUS  current
    DESCRIPTION
	"This parameter instructs the PAD whether to forward the user sequences included in
		data packets to the local DTE or discard them.  The options are (1) discard output or
		 (2) normal data delivery.  If the value of radSPSProfileBreak is 21, the value of
		 pktSwchProfileDiscOut is automatically set to (1) when a break signal is received."
   ::= { pktSwchProfileAEntry 9  }

pktSwchProfileCRPaddingA OBJECT-TYPE
    SYNTAX  Integer32 (0..127)
    MAX-ACCESS  read-only
    STATUS  current
    DESCRIPTION
	"This parameter specifies the number of padding characters to be added after a carriage
		 return character is transmitted to the local DTE."
   ::= { pktSwchProfileAEntry 10}

pktSwchProfileLineFoldA OBJECT-TYPE
    SYNTAX  Integer32 (0..255)
    MAX-ACCESS  read-only
    STATUS  current
    DESCRIPTION
	"This parameter specifies the maximum number of characters to be inserted before the
		 format effector.  If the value is zero, there is no insertion of a format effector (line folding)."
    ::= { pktSwchProfileAEntry 11}

pktSwchProfileSpeedA OBJECT-TYPE
    SYNTAX  INTEGER  {
       s110bps(1),
       s300bps(2),
       s1200bps(3),
       s600bps(4),
       s75bps(5),
       s150bps(6),
       s2400bps(12),
       s4800bps(13),
       s9600bps(14),
       s19200bps(15),
       s38400bps(19),
	   s57600bps(20),
	   s115200bps(21)
    }
    MAX-ACCESS  read-only
    STATUS  current
    DESCRIPTION
	"This parameter determines the rate of data transmission to and from the DTE."
    ::= { pktSwchProfileAEntry 12 }

pktSwchProfilePadFlowContA OBJECT-TYPE
    SYNTAX  INTEGER {
       flowCont(1),
       noFlowCont(2)
     }
    MAX-ACCESS  read-only
    STATUS  current
    DESCRIPTION
	"This determines whether or not the terminal can exercise flow control over the PAD.
		 The options are either 'device can exercise flow control' or 'device cannot exercise flow
		 control."
   ::= { pktSwchProfileAEntry 13  }

pktSwchProfileLineFeedInsertA OBJECT-TYPE
    SYNTAX  INTEGER  {
       afterCR(1),
       recCR(2),
       echoCR(4),
       onePlusFour(5),
       twoPlusFour(6),
       oneTwoFour(7),
       noFeed(255)
    }
    MAX-ACCESS  read-only
    STATUS  current
    DESCRIPTION
	"This parameter indicates when there is a line feed insertion after CR.  The options are
		  (1) Insert line feed after transmission of CR to the DTE, (2) Insert line feed after receipt
		 of CR from the DTE, (4) Insert line feed after echoing a CR character to the DTE,
		 (5) Combination of (1) and (4), (6) Insert line feed after any CR to the DTE (combination of
		 (2) and (4)), (7) Combination of (1), (2), and (4), or (255) No line feed insertion."
    ::= { pktSwchProfileAEntry 14 }

pktSwchProfileLineFeedPadA OBJECT-TYPE
    SYNTAX  Integer32 (0..255)
    MAX-ACCESS  read-only
    STATUS  current
    DESCRIPTION
	"This parameter specifies the number of padding characters to be added after a line
		 feed."
   ::= { pktSwchProfileAEntry 15 }

pktSwchProfileEditingA OBJECT-TYPE
    SYNTAX  INTEGER {
       edit(1),
       noEdit(2)
     }
    MAX-ACCESS  read-only
    STATUS  current
    DESCRIPTION
	"This parameter specifies the editing capabilities available in the data transfer mode.
		Editing is always possible when the PAD is in the command mode.  The options are
		 (1) Command editing in the data trasfer mode is enabled or (2) No command editing
		 in the data transfer mode."
   ::= { pktSwchProfileAEntry 16  }

pktSwchProfileCharDelA OBJECT-TYPE
    SYNTAX  Integer32 (0..127)
    MAX-ACCESS  read-only
    STATUS  current
    DESCRIPTION
	"This parameter specifies the character delete, which is one character from IA5.  The default
		selection is 127 (character DEL)."
   ::= { pktSwchProfileAEntry 17}


pktSwchProfileLineDelA OBJECT-TYPE
    SYNTAX  Integer32 (0..127)
    MAX-ACCESS  read-only
    STATUS  current
    DESCRIPTION
	"This parameter specifies the line delete, which is one character from IA5.  The default
		selection is 24 (character CAN)."
   ::= { pktSwchProfileAEntry 18}

pktSwchProfileLineDispA OBJECT-TYPE
    SYNTAX  Integer32 (0..127)
    MAX-ACCESS  read-only
    STATUS  current
    DESCRIPTION
	"This entry specifies the line display character, which is one character
		from IA5.  The default selection is 18 (character DC2)."
   ::= { pktSwchProfileAEntry 19}

pktSwchProfileEditServSigA  OBJECT-TYPE
    SYNTAX Integer32 (0..126)
    MAX-ACCESS  read-only
    STATUS  current
    DESCRIPTION
	"This entry specifies the editing PAD service signals.
		The integer values have the following meanings:
			 (0)                 No editing PAD service signals
			 (1)                 Editing PAD service signals for printing terminals
			 (2)                 Editing PAD service signals for display terminals
			 (3)  to (126)  Editing PAD service signals using the desired character from IA5."
    ::= { pktSwchProfileAEntry 20  }

pktSwchProfileEchomaskA OBJECT-TYPE
    SYNTAX  Integer32 (0..255)
    MAX-ACCESS  read-only
    STATUS  current
    DESCRIPTION
	"The value is a sum of values (powers of two), where each value in the sum represents
		a character (or characters) that is (are) included in the echo mask.  The characters in the
		echo mask are not echoed to the DTE when PAD echo is enabled.
		The values that may be included in the sum and their meanings are:
		0   No echo mask (all the characters are echoed)
		1   No echo of character CR
		2   No echo of character LF
		4   No echo of characters VT, HT, FF
		8   No echo of characters BEL, BS
		16 No echo of characters ESC, ENQ
		32 No echo of characters ACK, NAK, STX, SOH, EOT, ETB, ETX
		64 No echo of the editing characters selected by radSPSProfileCharDel,
														       radSPSProfileLineDel, and
														       radSPSProfileLineDisp
				128 No echo of the DEL character and of all the other characters in the range of
					ASCII 00 through 31 not mentioned above."
	::= { pktSwchProfileAEntry 21 }

pktSwchProfileParTreatA OBJECT-TYPE
    SYNTAX  INTEGER  {
       parCheck(1),
       parGen(2),
       checkAndGen(3),
       noPar(255)
    }
    MAX-ACCESS  read-only
    STATUS  current
    DESCRIPTION
	"This entry controls the generation of parity bits in the data sent to the local DTE and the
		checking of the parity bit when generated by the local DTE.  The options are (1) parity
		checking is enabled, (2) parity generation is enabled, (3) parity checking and generation are
		enabled, or (255) no parity checking nor parity generation."
    ::= { pktSwchProfileAEntry 22 }

pktSwchProfilePageWaitA OBJECT-TYPE
    SYNTAX  Integer32 (0..255)
    MAX-ACCESS  read-only
    STATUS  current
    DESCRIPTION
	"This entry specifies the number of line feed characters counted by the PAD before the
		page wait condition is entered.  If the value is zero, page wait is disabled."
   ::= { pktSwchProfileAEntry 23}

pktSwchProfileBitsPerCharA  OBJECT-TYPE
    SYNTAX Integer32 (5..8)
    MAX-ACCESS  read-only
    STATUS  current
    DESCRIPTION
	"The number of data bits per character supported by the PAD."
    ::= { pktSwchProfileAEntry 24 }

pktSwchProfileDvParityA OBJECT-TYPE
    SYNTAX  INTEGER  {
       space(1),
       mark(2),
       even(3),
       odd(4),
       none(255)
    }
    MAX-ACCESS  read-only
    STATUS  current
    DESCRIPTION
	"This entry selects the type of parity to be checked and or generated by the PAD
		 when radSPSProfileParTreat is a value other than 255.  The options are
		  (1) space parity, (2) mark parity, (3) even parity, (4) odd parity, or (255) no parity."
    ::= { pktSwchProfileAEntry 25 }

pktSwchProfileStopBitsA OBJECT-TYPE
    SYNTAX  INTEGER  {
       one(1),
       two(2),
       oneAndHalf(3)
    }
    MAX-ACCESS  read-only
    STATUS  current
    DESCRIPTION
	"This entry indicates the number of stop bits per character supported by the PAD.
		The options are either (1) one stop bit, (2) two stop bits, or (3) 1.5 stop bits."
   ::= { pktSwchProfileAEntry 26 }

pktSwchProfileSpecFlowA OBJECT-TYPE
    SYNTAX  INTEGER {
       spec(1),
       noSpec(2)
     }
    MAX-ACCESS  read-only
    STATUS  current
    DESCRIPTION
	"This entry is used to define additional flow control possiblilites.
		 The options are either  (1) Flow control by means fo the terminal DTR line
		 or (2) No special flow control."
   ::= { pktSwchProfileAEntry 27  }

pktSwchProfileCountFwdA OBJECT-TYPE
    SYNTAX  Integer32 (0..255)
    MAX-ACCESS  read-only
    STATUS  current
    DESCRIPTION
	"This entry can be used to instruct the PAD to complete the assembly of a packet
		and to forward it after the specifed number of characters has been received.
		If the value is zero, count forwarding is disabled."
   ::= { pktSwchProfileAEntry 28}

pktSwchProfileEscDelayA OBJECT-TYPE
    SYNTAX  Integer32 (1..255)
    MAX-ACCESS  read-only
    STATUS  current
    DESCRIPTION
	"This entry can be used to instruct the PAD whether to delay the forwarding of
		a data packet when an escape character is detected in the data stream and to
		determine the required delay.  The packet forwarding is delayed until the specified
		number of characters is received after the escape character.  A value of zero indicates
		no special handling."
   ::= { pktSwchProfileAEntry 29}

pktSwchProfileCharBreakA OBJECT-TYPE
    SYNTAX  Integer32 (0..127)
    MAX-ACCESS  read-only
    STATUS  current
    DESCRIPTION
	"This entry specifies the decimal value of the character that will be interpreted
		as an additional break signal by the PAD.  A value of zero indicates no break character."
   ::= { pktSwchProfileAEntry 30}

pktSwchProfileCharSuppressA OBJECT-TYPE
    SYNTAX  Integer32 (0..127)
    MAX-ACCESS  read-only
    STATUS  current
    DESCRIPTION
	"This entry specifies the decimal value of the character that will toggle
		echo suppression in the PAD.  A value of zero indicates that echo suppression
		 is only controlled by radSPSProfileEcho."
   ::= { pktSwchProfileAEntry 31}

pktSwchProfileCharSubsA OBJECT-TYPE
    SYNTAX  Integer32 (0..127)
    MAX-ACCESS  read-only
    STATUS  current
    DESCRIPTION
	"This entry specifies the decimal value of the character that will be echoed
		instead of the character received from the user's DTE.  A zero value indicates that
		 no character is echoed."
   ::= { pktSwchProfileAEntry 32}

pktSwchProfileFormFeedPadA OBJECT-TYPE
    SYNTAX  Integer32 (0..127)
    MAX-ACCESS  read-only
    STATUS  current
    DESCRIPTION
	"This entry specifies the number of padding (NUL) characters that will be
		automatically sent after the form feed character."
   ::= { pktSwchProfileAEntry 33}

pktSwchProfileInactivityA OBJECT-TYPE
    SYNTAX  Integer32 (0..255)
    MAX-ACCESS  read-only
    STATUS  current
    DESCRIPTION
	"This entry specifies the number of minutes after which the PAD will forward
		the accumulated data and clear the call.  A zero value indicates no disconnection
		on inactivity."
   ::= { pktSwchProfileAEntry 34 }

pktSwchProfileOptionsA OBJECT-TYPE
    SYNTAX  Integer32 (0..255)
    MAX-ACCESS  read-only
    STATUS  current
    DESCRIPTION
	"This entry defines several options to control the profile.  The value is a sum of values
		(powers of two), where each value in the sum represents an option .
				The values that may be included in the sum and their meanings are:
		0   No options
		1   Remote set of local X.3 parameters though X.29 is disabled
		2  Add sub address to call request
		4   Don't use protocol ID in user data field.
		8   SPRINT NUI format
		16  More bit is set when the edit buffer is full
                                 32 Extended error message
                                 64 Discard  connect extended service signal
                                128 enable connect by typing the address w/out a command"
   ::= { pktSwchProfileAEntry 35 }

pktSwchProfileClrTimerA OBJECT-TYPE
    SYNTAX  Integer32 (0..255)
    MAX-ACCESS  read-only
    STATUS  current
    DESCRIPTION
	"This entry specifies the number of minutes after which a call is cleared.
		  If the parameter value is 0, there is no disconnection timer."
   ::= { pktSwchProfileAEntry 36 }

pktSwchProfileSubAddInCUDA OBJECT-TYPE
    SYNTAX  Integer32 (0..5)
    MAX-ACCESS  read-only
    STATUS  current
    DESCRIPTION
	"This entry defines the number of digits for the subaddress in CUD."
    ::= { pktSwchProfileAEntry 37 }


-- pktSwchChannel (Scratch and Active) defines the channel configurations
-- of all the channels on the PS

pktSwchChannel 	OBJECT IDENTIFIER ::= { pktSwchAsync 2 }

-- pktSwchChannelSTable defines the Scratch channel configurations of all
-- the channels on the PS

pktSwchChannelSTable    OBJECT-TYPE
    SYNTAX  SEQUENCE  OF PktSwchChannelSEntry
    MAX-ACCESS  not-accessible
    STATUS  current
    DESCRIPTION
	"The Scratch Channel Table defines the channels configured on the PS."
     ::=  { pktSwchChannel 1 }

pktSwchChannelSEntry OBJECT-TYPE
    SYNTAX  PktSwchChannelSEntry
    MAX-ACCESS  not-accessible
    STATUS  current
    DESCRIPTION
	"Defines the contents of each line in the Scratch Channel Table."
    INDEX   { pktSwchChannelIfIndexS }
    ::=  { pktSwchChannelSTable 1 }

PktSwchChannelSEntry ::= SEQUENCE {
    pktSwchChannelIfIndexS
     Integer32,
    pktSwchChannelNumberS
     Integer32,
    pktSwchChannelProfileS
     Integer32,
    pktSwchChannelOutCallProfileS
     Integer32,
    pktSwchChannelInCallProfileS
     Integer32,
    pktSwchChannelRemoteProfileS
     Integer32,
    pktSwchChannelAutocallIdS
     Integer32,
    pktSwchChannelAlterAutocallIdS
     Integer32,
    pktSwchChannelAutocallRetriesS
     Integer32,
    pktSwchChannelAutocallIntervalS
     Integer32,
    pktSwchChannelCallAliasS
     Integer32,
    pktSwchChannelSubAddress1S
     Integer32,
    pktSwchChannelSubAddress2S
     Integer32,
    pktSwchChannelNUISEntry
     Integer32,
    pktSwchChannelClearTimerS
     Integer32,
    pktSwchChannelOptionsS
     Integer32,
	pktSwchChannelClear
	 INTEGER,
	pktSwchChannelCopyTo
	 Integer32,
	pktSwchChannelCopyToWMask
	 Integer32,
	pktSwchChannelCopyMask
	 Integer32
    }

pktSwchChannelIfIndexS  OBJECT-TYPE
    SYNTAX Integer32
    MAX-ACCESS  read-only
    STATUS  current
    DESCRIPTION
	"This is used as the index for the channel table."
    ::= { pktSwchChannelSEntry 1 }

pktSwchChannelNumberS  OBJECT-TYPE
    SYNTAX Integer32 (1..1224)
    MAX-ACCESS  read-only
    STATUS  current
    DESCRIPTION
	"The number by which a channel is identified."
    ::= { pktSwchChannelSEntry 2 }

pktSwchChannelProfileS  OBJECT-TYPE
    SYNTAX Integer32 (1..200)
    MAX-ACCESS  read-write
    STATUS  current
    DESCRIPTION
	"The profile that the channel uses for command mode operations."
    ::= { pktSwchChannelSEntry 3 }

pktSwchChannelOutCallProfileS  OBJECT-TYPE
    SYNTAX Integer32 (0..200)
    MAX-ACCESS  read-write
    STATUS  current
    DESCRIPTION
	"The number of the profile that will be used during an outgoing
	 call on the channel."
    ::= { pktSwchChannelSEntry 4 }

pktSwchChannelInCallProfileS  OBJECT-TYPE
    SYNTAX Integer32 (0..200)
    MAX-ACCESS  read-write
    STATUS  current
    DESCRIPTION
	"The number of the profile that will be used during an incoming
	 call on the channel."
    ::= { pktSwchChannelSEntry 5 }

pktSwchChannelRemoteProfileS  OBJECT-TYPE
    SYNTAX Integer32 (0..200)
    MAX-ACCESS  read-write
    STATUS  current
    DESCRIPTION
	"The number of the profile that will be downloaded to the remote
	 PAD at the beginning of a new call."
    ::= { pktSwchChannelSEntry 6 }

pktSwchChannelAutocallIdS  OBJECT-TYPE
    SYNTAX Integer32 (0..200)
    MAX-ACCESS  read-write
    STATUS  current
    DESCRIPTION
	"Selects the mnemonic (call ID) to be used as the first alternative.
	 A value of zero indicates that the autocall function is disabled."
    ::= { pktSwchChannelSEntry 7 }

pktSwchChannelAlterAutocallIdS  OBJECT-TYPE
    SYNTAX Integer32 (0..200)
    MAX-ACCESS  read-write
    STATUS  current
    DESCRIPTION
	"Selects the alternate mnemonic for the autocall function.  A value of zero indicates that the
		 alternate destination is not used."
    ::= { pktSwchChannelSEntry 8 }

pktSwchChannelAutocallRetriesS  OBJECT-TYPE
    SYNTAX Integer32 (0..255)
    MAX-ACCESS  read-write
    STATUS  current
    DESCRIPTION
	"The number of autocall retries if the autocall setup request is
	 rejected with a busy cause."
    ::= { pktSwchChannelSEntry 9 }

pktSwchChannelAutocallIntervalS OBJECT-TYPE
    SYNTAX Integer32 (0..255)
    MAX-ACCESS  read-write
    STATUS  current
    DESCRIPTION
	"The interval in seconds between consecutive autocall retries."
    ::= { pktSwchChannelSEntry 10 }

pktSwchChannelCallAliasS OBJECT-TYPE
    SYNTAX Integer32 (0..200)
    MAX-ACCESS  read-write
    STATUS  current
    DESCRIPTION
	"The alias to be sent after the call is set up.  A value of zero
	 indicates that alias sending is disabled.  The aliases are
	 configured on the Alias Table."
    ::= { pktSwchChannelSEntry 11 }

pktSwchChannelSubAddress1S OBJECT-TYPE
    SYNTAX Integer32 (0..255)
    MAX-ACCESS  read-write
    STATUS  current
    DESCRIPTION
	"The first subaddress for the channel."
    ::= { pktSwchChannelSEntry 12 }

pktSwchChannelSubAddress2S OBJECT-TYPE
    SYNTAX Integer32 (0..255)
    MAX-ACCESS  read-write
    STATUS  current
    DESCRIPTION
	"The second subaddress for the channel."
    ::= { pktSwchChannelSEntry 13}

pktSwchChannelNUISEntry OBJECT-TYPE
    SYNTAX Integer32 (1..200)
    MAX-ACCESS  read-write
    STATUS  current
    DESCRIPTION
	"The number corresponding to the NUI information to be sent.
	 This number is the same as the pktSwchNuiGroupId."
    ::= { pktSwchChannelSEntry 14 }

pktSwchChannelClearTimerS OBJECT-TYPE
    SYNTAX Integer32 (0..255)
    MAX-ACCESS  read-write
    STATUS  current
    DESCRIPTION
	"Time limitation for an open session.  A value of zero indicates that
	 the Clear timer is not used."
    ::= { pktSwchChannelSEntry 15 }

pktSwchChannelOptionsS OBJECT-TYPE
    SYNTAX Integer32 (0..255)
    MAX-ACCESS  read-write
    STATUS  current
    DESCRIPTION
	"This controls the use of gneral non-correlated channel options.
	 The value is a sum of values (powers of two), where each value in
	 the sum represents an option.
	 The values that may be included in the sum and their meanings are:
		0   No options
		1   HW signal is checked
		2   Auto call after clear
		4   Auto call after 
		8   DCD is ON, only in DATA TRANSFER mode
		16  Charging Info Facility
		32  Auto call if HW signal is set
                               64  Accept calls even  if HW signal is  is OFF
                              128 A transparent channel."
::= { pktSwchChannelSEntry 16 }

pktSwchChannelClear OBJECT-TYPE
	SYNTAX INTEGER {
	                noOp(1),
	                clear(2)
	               }
	MAX-ACCESS read-write
	STATUS current
	DESCRIPTION
	"The Clearing Channel operation disconnects all sessions"
	::= { pktSwchChannelSEntry 17 }

pktSwchChannelCopyTo OBJECT-TYPE
 	SYNTAX Integer32
	MAX-ACCESS  read-write
	STATUS  current
    DESCRIPTION
	"The destination channel number, to which the Copy
	 is performed."
	::= { pktSwchChannelSEntry 18 }

pktSwchChannelCopyToWMask OBJECT-TYPE
 	SYNTAX Integer32
	MAX-ACCESS  read-write
	STATUS  current
    DESCRIPTION
	"The destination channel number, to which the Copy with Mask
	 is performed."
	::= { pktSwchChannelSEntry 19 }

pktSwchChannelCopyMask OBJECT-TYPE
 	SYNTAX Integer32 (0..16383)
	MAX-ACCESS  read-write
	STATUS  current
    DESCRIPTION
	"The selected configuration parameters to be copied from the source
	 channel to the target channels. The value is a sum of values
	 (powers of two), where each value in the sum represents a selected
	 parameter that is not copied. The values that may be included in the
	 sum and their meanings are:
	 0	  Copy all.
	 1	  Do not copy Profile.
	 2	  Do not copy OutCallProfile.
	 4	  Do not copy InCallProfile.
	 8	  Do not copy RemoteProfile.
	 16	  Do not copy AutocallId.
	 32	  Do not copy AlterCallId.
	 64	  Do not copy AutoCallRetries.
	 128  Do not copy AutoCallInterval.
	 256  Do not copy CallAlias.
	 512  Do not copy SubAddress1.
	 1024  Do not copy SubAddress2.
	 2048  Do not copy NUIEntry.
	 4096  Do not copy ClearTimer.
	 8192  Do not copy Options.
	 XXX - Any combination of the above."
	::= { pktSwchChannelSEntry 20 }


pktSwchChannelATable    OBJECT-TYPE
    SYNTAX  SEQUENCE  OF PktSwchChannelAEntry
    MAX-ACCESS  not-accessible
    STATUS  current
    DESCRIPTION
	"The Active Channel Table defines the channels configured on the PS."
     ::=  { pktSwchChannel 2 }

pktSwchChannelAEntry OBJECT-TYPE
    SYNTAX  PktSwchChannelAEntry
    MAX-ACCESS  not-accessible
    STATUS  current
    DESCRIPTION
	"Defines the contents of each line in the Active Channel
	     Table."
    INDEX   { pktSwchChannelIfIndexA }
    ::=  { pktSwchChannelATable 1 }

PktSwchChannelAEntry ::= SEQUENCE {
    pktSwchChannelIfIndexA
     Integer32,
    pktSwchChannelNumberA
     Integer32,
    pktSwchChannelProfileA
     Integer32,
    pktSwchChannelOutCallProfileA
     Integer32,
    pktSwchChannelInCallProfileA
     Integer32,
    pktSwchChannelRemoteProfileA
     Integer32,
    pktSwchChannelAutocallIdA
     Integer32,
    pktSwchChannelAlterAutocallIdA
     Integer32,
    pktSwchChannelAutocallRetriesA
     Integer32,
    pktSwchChannelAutocallIntervalA
     Integer32,
    pktSwchChannelCallAliasA
     Integer32,
    pktSwchChannelSubAddress1A
     Integer32,
    pktSwchChannelSubAddress2A
     Integer32,
    pktSwchChannelNUIAEntry
     Integer32,
    pktSwchChannelClearTimerA
     Integer32,
    pktSwchChannelOptionsA
     Integer32
    }

pktSwchChannelIfIndexA  OBJECT-TYPE
    SYNTAX Integer32
    MAX-ACCESS  read-only
    STATUS  current
    DESCRIPTION
	"This is used as the index for the channel table."
    ::= { pktSwchChannelAEntry 1 }

pktSwchChannelNumberA  OBJECT-TYPE
    SYNTAX Integer32 (1..288)
    MAX-ACCESS  read-only
    STATUS  current
    DESCRIPTION
	"The number by which a channel is identified."
    ::= { pktSwchChannelAEntry 2 }

pktSwchChannelProfileA  OBJECT-TYPE
    SYNTAX Integer32
    MAX-ACCESS  read-only
    STATUS  current
    DESCRIPTION
	"The profile that the channel uses for command mode operations."
    ::= { pktSwchChannelAEntry 3 }

pktSwchChannelOutCallProfileA  OBJECT-TYPE
    SYNTAX Integer32
    MAX-ACCESS  read-only
    STATUS  current
    DESCRIPTION
	"The number of the profile that is used during an outgoing call on the channel."
    ::= { pktSwchChannelAEntry 4 }

pktSwchChannelInCallProfileA  OBJECT-TYPE
    SYNTAX Integer32
    MAX-ACCESS  read-only
    STATUS  current
    DESCRIPTION
	"The number of the profile that is used during an incoming call on the channel."
    ::= { pktSwchChannelAEntry 5 }

pktSwchChannelRemoteProfileA  OBJECT-TYPE
    SYNTAX Integer32
    MAX-ACCESS  read-only
    STATUS  current
    DESCRIPTION
	"The number of the profile that is downloaded to the remote PAD at the beginning of
		 a new call."
    ::= { pktSwchChannelAEntry 6 }

pktSwchChannelAutocallIdA  OBJECT-TYPE
    SYNTAX Integer32
    MAX-ACCESS  read-only
    STATUS  current
    DESCRIPTION
	"Selects the mnemonic (call ID) to be used as the first alternative.  A value of zero indicates that
		 the autocall function is disabled."
    ::= { pktSwchChannelAEntry 7 }

pktSwchChannelAlterAutocallIdA  OBJECT-TYPE
    SYNTAX Integer32
    MAX-ACCESS  read-only
    STATUS  current
    DESCRIPTION
	"Selects the alternate mnemonic for the autocall function.  A value of zero indicates that the
		 alternate destination is not used."
    ::= { pktSwchChannelAEntry 8 }

pktSwchChannelAutocallRetriesA  OBJECT-TYPE
    SYNTAX Integer32
    MAX-ACCESS  read-only
    STATUS  current
    DESCRIPTION
	"The number of autocall retrues if the autocall setup request is rejected with a busy cause."
    ::= { pktSwchChannelAEntry 9 }

pktSwchChannelAutocallIntervalA OBJECT-TYPE
    SYNTAX Integer32
    MAX-ACCESS  read-only
    STATUS  current
    DESCRIPTION
	"The interval in seconds between consecutive autocall retries."
    ::= { pktSwchChannelAEntry 10 }

pktSwchChannelCallAliasA OBJECT-TYPE
    SYNTAX Integer32
    MAX-ACCESS  read-only
    STATUS  current
    DESCRIPTION
	"The alias to be sent after the call is set up.  A value of zero indicates that alias
		sending is disabled.  The aliases are configured on the Alias Table."
    ::= { pktSwchChannelAEntry 11 }

pktSwchChannelSubAddress1A OBJECT-TYPE
    SYNTAX Integer32
    MAX-ACCESS  read-only
    STATUS  current
    DESCRIPTION
	"The first subaddress for the channel."
    ::= { pktSwchChannelAEntry 12 }

pktSwchChannelSubAddress2A OBJECT-TYPE
    SYNTAX Integer32
    MAX-ACCESS  read-only
    STATUS  current
    DESCRIPTION
	"The second subaddress for the channel."
    ::= { pktSwchChannelAEntry 13}

pktSwchChannelNUIAEntry OBJECT-TYPE
    SYNTAX Integer32
    MAX-ACCESS  read-only
    STATUS  current
    DESCRIPTION
	"The number corresponding to the NUI information to be sent.  This number is the same as the
		 pktSwchNuiIndex."
    ::= { pktSwchChannelAEntry 14 }

pktSwchChannelClearTimerA OBJECT-TYPE
    SYNTAX Integer32
    MAX-ACCESS  read-only
    STATUS  current
    DESCRIPTION
	"Time limitation for an open session.  A value of zero indicates that the Clear timer is not used."
    ::= { pktSwchChannelAEntry 15 }

pktSwchChannelOptionsA OBJECT-TYPE
    SYNTAX Integer32
    MAX-ACCESS  read-only
    STATUS  current
    DESCRIPTION
	"This controls the use of general non-correlated channel options.  The value is a sum of values
		(powers of two), where each value in the sum represents an option.
		The values that may be included in the sum and their meanings are:
		0   No options
		1   RTS line checked
		2   Auto call after clear
		4   Auto call after 
		8 DCD is ON, only in DATA TRANSFER mode.
		16  Charging Info Facility
		32  Auto call if HW signal is set
                               64  Accept calls even  if HW signal is  is OFF
                              128 A transparent channel."
    ::= { pktSwchChannelAEntry 16 }


-- pktSwchCallId defines the Call IDs

pktSwchCallId OBJECT IDENTIFIER ::=  { pktSwchAsync 3 }

-- pktSwchCallIdSTable defines the Scratch Call IDs

pktSwchCallIdSTable    OBJECT-TYPE
    SYNTAX  SEQUENCE  OF PktSwchCallIdSEntry
    MAX-ACCESS  not-accessible
    STATUS  current
    DESCRIPTION
	"The Call ID Table S defines the Scratch Call IDs configured on the device."
     ::=  { pktSwchCallId 1 }

pktSwchCallIdSEntry OBJECT-TYPE
    SYNTAX  PktSwchCallIdSEntry
    MAX-ACCESS  not-accessible
    STATUS  current
    DESCRIPTION
	"Defines the contents of each line in the Scratch CallId Table."
    INDEX   { pktSwchCallIdNumberS }
    ::=  { pktSwchCallIdSTable 1 }

PktSwchCallIdSEntry ::= SEQUENCE {
    pktSwchCallIdNumberS
     Integer32,
    pktSwchCallIdMnemonicS
     DisplayString,
    pktSwchCallIdAddressS
     DisplayString,
    pktSwchCallIdStatusS
     INTEGER
    }

pktSwchCallIdNumberS OBJECT-TYPE
    SYNTAX Integer32 (1..200)
    MAX-ACCESS  read-write
    STATUS  current
    DESCRIPTION
	"The index of this entry."
    ::= { pktSwchCallIdSEntry 1 }

pktSwchCallIdMnemonicS OBJECT-TYPE
    SYNTAX DisplayString
    MAX-ACCESS  read-write
    STATUS  current
    DESCRIPTION
	"The mnemonic for this call ID."
    ::= { pktSwchCallIdSEntry 2 }

pktSwchCallIdAddressS OBJECT-TYPE
    SYNTAX DisplayString
    MAX-ACCESS  read-write
    STATUS  current
    DESCRIPTION
	"The address for this call ID."
    ::= { pktSwchCallIdSEntry 3 }

pktSwchCallIdStatusS OBJECT-TYPE
    SYNTAX  INTEGER {
       valid(1),
       createRequest(2),
       underCreation(3),
       invalid(4)
     }
    MAX-ACCESS  read-write
    STATUS  current
    DESCRIPTION
	"The status of this Call ID table entry.  The choices are those defined in the SNMPv2 Textual
		 Conventions for RowStatus.  This will allow easy replacement of the INTEGER syntax with
		 the RowStatus textual convention SYNTAX."
  ::= { pktSwchCallIdSEntry 4 }

-- pktSwchCallIdATable defines the Active Call IDs

pktSwchCallIdATable    OBJECT-TYPE
    SYNTAX  SEQUENCE  OF PktSwchCallIdAEntry
    MAX-ACCESS  not-accessible
    STATUS  current
    DESCRIPTION
	"The Call ID Table A defines the Active Call IDs configured on the device."
     ::=  { pktSwchCallId 2 }

pktSwchCallIdAEntry OBJECT-TYPE
    SYNTAX  PktSwchCallIdAEntry
    MAX-ACCESS  not-accessible
    STATUS  current
    DESCRIPTION
	"Defines the contents of each line in the Active CallId Table."
    INDEX   { pktSwchCallIdNumberA }
    ::=  { pktSwchCallIdATable 1 }

PktSwchCallIdAEntry ::= SEQUENCE {
    pktSwchCallIdNumberA
     Integer32,
    pktSwchCallIdMnemonicA
     DisplayString,
    pktSwchCallIdAddressA
     DisplayString
    }

pktSwchCallIdNumberA OBJECT-TYPE
    SYNTAX Integer32 (1..200)
    MAX-ACCESS  read-only
    STATUS  current
    DESCRIPTION
	"The index of this entry."
    ::= { pktSwchCallIdAEntry 1 }

pktSwchCallIdMnemonicA OBJECT-TYPE
    SYNTAX DisplayString
    MAX-ACCESS  read-only
    STATUS  current
    DESCRIPTION
	"The mnemonic for this call ID."
    ::= { pktSwchCallIdAEntry 2 }

pktSwchCallIdAddressA OBJECT-TYPE
    SYNTAX DisplayString
    MAX-ACCESS  read-only
    STATUS  current
    DESCRIPTION
	"The address for this call ID."
    ::= { pktSwchCallIdAEntry 3 }


-- pktSwchAlias defines the Aliases

pktSwchAlias OBJECT IDENTIFIER ::=  { pktSwchAsync 4 }

-- pktSwchAliasSTable defines the Scratch Aliases

pktSwchAliasSTable    OBJECT-TYPE
    SYNTAX  SEQUENCE  OF PktSwchAliasSEntry
    MAX-ACCESS  not-accessible
    STATUS  current
    DESCRIPTION
	"The Alias Table defines the aliases configured on the device."
     ::=  { pktSwchAlias 1 }

pktSwchAliasSEntry OBJECT-TYPE
    SYNTAX  PktSwchAliasSEntry
    MAX-ACCESS  not-accessible
    STATUS  current
    DESCRIPTION
	"Defines the contents of each line in the Alias Table."
    INDEX   { pktSwchAliasNumberS }
    ::=  { pktSwchAliasSTable 1 }

PktSwchAliasSEntry ::= SEQUENCE {
    pktSwchAliasNumberS
     Integer32,
    pktSwchAliasValueS
     DisplayString,
    pktSwchAliasStatusS
     INTEGER
    }

pktSwchAliasNumberS OBJECT-TYPE
    SYNTAX Integer32 (1..200)
    MAX-ACCESS  read-write
    STATUS  current
    DESCRIPTION
	"The index of this entry."
    ::= { pktSwchAliasSEntry 1 }

pktSwchAliasValueS OBJECT-TYPE
    SYNTAX DisplayString (SIZE (0..64))
    MAX-ACCESS  read-write
    STATUS  current
    DESCRIPTION
	"The alias is defined using up to 64 characters."
    ::= { pktSwchAliasSEntry 2 }

pktSwchAliasStatusS OBJECT-TYPE
    SYNTAX  INTEGER {
       valid(1),
       createRequest(2),
       underCreation(3),
       invalid(4)
     }
    MAX-ACCESS  read-write
    STATUS  current
    DESCRIPTION
	"The status of this Alias table entry.  The choices are those defined in the SNMPv2 Textual
		 Conventions for RowStatus.  This will allow easy replacement of the INTEGER syntax with
		 the RowStatus textual convention SYNTAX."
  ::= { pktSwchAliasSEntry 3 }


-- pktSwchAliasATable defines the Active Aliases

pktSwchAliasATable    OBJECT-TYPE
    SYNTAX  SEQUENCE  OF PktSwchAliasAEntry
    MAX-ACCESS  not-accessible
    STATUS  current
    DESCRIPTION
	"The Alias Table defines the aliases configured on the device."
     ::=  { pktSwchAlias 2 }

pktSwchAliasAEntry OBJECT-TYPE
    SYNTAX  PktSwchAliasAEntry
    MAX-ACCESS  not-accessible
    STATUS  current
    DESCRIPTION
	"Defines the contents of each line in the Alias Table."
    INDEX   { pktSwchAliasNumberA }
    ::=  { pktSwchAliasATable 1 }

PktSwchAliasAEntry ::= SEQUENCE {
    pktSwchAliasNumberA
     Integer32,
    pktSwchAliasValueA
     DisplayString
    }

pktSwchAliasNumberA OBJECT-TYPE
    SYNTAX Integer32 (1..200)
    MAX-ACCESS  read-only
    STATUS  current
    DESCRIPTION
	"The index of this entry."
    ::= { pktSwchAliasAEntry 1 }

pktSwchAliasValueA OBJECT-TYPE
    SYNTAX DisplayString (SIZE (0..64))
    MAX-ACCESS  read-only
    STATUS  current
    DESCRIPTION
	"The alias is defined using up to 64 characters."
    ::= { pktSwchAliasAEntry 2 }



-- The pktSwchAsyncStatTable contains status information and statistics
-- for the Async channels

pktSwchAsyncStatTable  OBJECT-TYPE
    SYNTAX  SEQUENCE  OF PktSwchAsyncStatEntry
    MAX-ACCESS  not-accessible
    STATUS  current
    DESCRIPTION
	"The AsyncStat Table includes status information and statistics
	 provided by the PS on the async channels."
       ::=  { pktSwchAsync 5 }

pktSwchAsyncStatEntry OBJECT-TYPE
    SYNTAX  PktSwchAsyncStatEntry
    MAX-ACCESS  not-accessible
    STATUS  current
    DESCRIPTION
	"Defines the contents of each line in the Async Stat Table."
    INDEX   { pktSwchAsyncIfIndex }
    ::=  { pktSwchAsyncStatTable 1  }

PktSwchAsyncStatEntry ::= SEQUENCE {
    pktSwchAsyncIfIndex
     Integer32,
    pktSwchAsyncChannelNumber
     Integer32,
    pktSwchAsyncConnectionStatus
     INTEGER,
    pktSwchAsyncNumLogChannels
     Integer32,
    pktSwchAsyncNumActSessions
     Integer32,
    pktSwchAsyncAutocallId
     Integer32,
    pktSwchAsyncRTSStatus
     INTEGER,
    pktSwchAsyncBuffToNet
     Integer32,
    pktSwchAsyncBuffToUser
     Integer32,
    pktSwchAsyncTxXoff
     INTEGER,
    pktSwchAsyncRxXoff
     INTEGER,
    pktSwchAsyncBuffOutstand
     Integer32,
    pktSwchAsyncChannelMode
     INTEGER

   }

pktSwchAsyncIfIndex OBJECT-TYPE
    SYNTAX Integer32
    MAX-ACCESS  read-only
    STATUS  current
    DESCRIPTION
	"An index for the table."
    ::= { pktSwchAsyncStatEntry 1 }

pktSwchAsyncChannelNumber OBJECT-TYPE
    SYNTAX Integer32
    MAX-ACCESS  read-only
    STATUS  current
    DESCRIPTION
	"The channel to which this entry applies.  This value is the
	 same as the pktSwchChannelNumber."
    ::= { pktSwchAsyncStatEntry 2 }

pktSwchAsyncConnectionStatus OBJECT-TYPE
    SYNTAX INTEGER {
	  engaged(1),
	  free   (2)
	  }
    MAX-ACCESS  read-only
    STATUS  current
    DESCRIPTION
	"The connection status of the channel is either FREE or ENG (engaged)."
    ::= { pktSwchAsyncStatEntry 3}

pktSwchAsyncNumLogChannels OBJECT-TYPE
    SYNTAX Integer32
    MAX-ACCESS  read-only
    STATUS  current
    DESCRIPTION
	"The number of active logical channels used by the asynchronous channel."
    ::= { pktSwchAsyncStatEntry 4 }

pktSwchAsyncNumActSessions OBJECT-TYPE
    SYNTAX Integer32
    MAX-ACCESS  read-only
    STATUS  current
    DESCRIPTION
	"The number of active sessions opened by this asynchronous channel."
    ::= { pktSwchAsyncStatEntry 5 }

pktSwchAsyncAutocallId OBJECT-TYPE
    SYNTAX Integer32
    MAX-ACCESS  read-only
    STATUS  current
    DESCRIPTION
	"Indicates whether the channel has been configured to use the autocall function and
		 what is the call  ID.  NONE means that the channel is not configured for autocall."
    ::= { pktSwchAsyncStatEntry 6}

pktSwchAsyncRTSStatus OBJECT-TYPE
    SYNTAX INTEGER {
	  unused(1),
	  off   (2),
	  on    (3)
	  }
    MAX-ACCESS  read-only
    STATUS  current
    DESCRIPTION
	"Shows the status of the RTS line of the asynchronous channel.
	 OFF indicates that the RTS line is not active, ON indicates that
	 it is active, and UNUSED indicates that the channel PAD is
	 programmed to disregard the state of the RTS line."
    ::= { pktSwchAsyncStatEntry 7 }

pktSwchAsyncBuffToNet OBJECT-TYPE
    SYNTAX Integer32
    MAX-ACCESS  read-only
    STATUS  current
    DESCRIPTION
	"The number of data buffers currently used by the transmit direction of the channel."
    ::= { pktSwchAsyncStatEntry 8 }

pktSwchAsyncBuffToUser OBJECT-TYPE
    SYNTAX Integer32
    MAX-ACCESS  read-only
    STATUS  current
    DESCRIPTION
	"The number of data buffers currently used by the receive direction of the channel."
    ::= { pktSwchAsyncStatEntry 9}

pktSwchAsyncTxXoff OBJECT-TYPE
    SYNTAX INTEGER {
      no (1),
      yes(2)
      }
    MAX-ACCESS  read-only
    STATUS  current
    DESCRIPTION
	"The current state of software flow control in the transmit direction.
	 NO indicates that traffic flow is enabled.  YES indicates that traffic
	 flow from the user's DTE to the device channel has been interrupted
	 by sending the X-OFF character to the DTE."
    ::= { pktSwchAsyncStatEntry 10 }


pktSwchAsyncRxXoff OBJECT-TYPE
    SYNTAX  INTEGER {
      no (1),
      yes(2)
      }
    MAX-ACCESS  read-only
    STATUS  current
    DESCRIPTION
	"The current state of software flow control in the receive direction.
	 NO indicates that traffic flow is enabled.  YES indicates that traffic
	 flow to the user's DTE from the device channel has been interrupted
	 by means of the X-OFF character."
    ::= { pktSwchAsyncStatEntry 11 }

pktSwchAsyncBuffOutstand OBJECT-TYPE
    SYNTAX Integer32
    MAX-ACCESS  read-only
    STATUS  current
    DESCRIPTION
	"Indicates the number of buffers which were sent to the async user
	 but weren't yet freed."
    ::= { pktSwchAsyncStatEntry 12 }

pktSwchAsyncChannelMode OBJECT-TYPE
    SYNTAX INTEGER {
	  none        (1),
	  activeLink  (2),
	  x28command  (3),
	  dataTransfer(4)
	  }
    MAX-ACCESS  read-only
    STATUS  current
    DESCRIPTION
	"The channel mode is either X28 COMMAND or DATA TRANSFER."
    ::= { pktSwchAsyncStatEntry 13 }


-- The pktSwchAsyncRunProTable contains status information and statistics for the Async channels

pktSwchAsyncRunProTable  OBJECT-TYPE
    SYNTAX  SEQUENCE  OF PktSwchAsyncRunProEntry
    MAX-ACCESS  not-accessible
    STATUS  current
    DESCRIPTION
	"The AsyncRunPro Table includes status information and statistics provided by the PS
		on the async channels."
       ::=  { pktSwchAsync 6 }

pktSwchAsyncRunProEntry OBJECT-TYPE
    SYNTAX  PktSwchAsyncRunProEntry
    MAX-ACCESS  not-accessible
    STATUS  current
    DESCRIPTION
	"Defines the contents of each line in the Async RunPro Table."
    INDEX   { pktSwchAsyncRunProIfIndex }
    ::=  { pktSwchAsyncRunProTable 1  }


PktSwchAsyncRunProEntry ::= SEQUENCE {
     pktSwchAsyncRunProIfIndex
     Integer32,
    pktSwchAsyncRunProChannelNumber
     Integer32,
	pktSwchAsyncRunProRecallChar
	 Integer32,
	pktSwchAsyncRunProEcho
	 INTEGER,
	pktSwchAsyncRunProDataForwChar
	 Integer32,
	pktSwchAsyncRunProIdleTimer
	 Integer32,
	pktSwchAsyncRunProDevFlowCont
	 INTEGER,
	pktSwchAsyncRunProServSig
	 INTEGER,
	pktSwchAsyncRunProBreak
	 Integer32,
	pktSwchAsyncRunProDiscOut
	 INTEGER,
	pktSwchAsyncRunProCRPPadding
	 Integer32,
	pktSwchAsyncRunProLineFold
	 Integer32,
	pktSwchAsyncRunProSpeed
	 INTEGER,
	pktSwchAsyncRunProPadFlowCont
	 INTEGER,
	pktSwchAsyncRunProLineFeedInsert
	 INTEGER,
	pktSwchAsyncRunProLineFeedPad
	 Integer32,
	pktSwchAsyncRunProEditing
	 INTEGER,
	pktSwchAsyncRunProCharDel
	 Integer32,
	pktSwchAsyncRunProLineDel
	 Integer32,
	pktSwchAsyncRunProLineDisp
	 Integer32,
	pktSwchAsyncRunProEditServSig
	 Integer32,
	pktSwchAsyncRunProEchomask
	 Integer32,
	pktSwchAsyncRunProParTreat
	 INTEGER,
	pktSwchAsyncRunProPageWait
	 Integer32
    }

pktSwchAsyncRunProIfIndex OBJECT-TYPE
    SYNTAX Integer32
    MAX-ACCESS  read-only
    STATUS  current
    DESCRIPTION
	"An index for the table."
    ::= { pktSwchAsyncRunProEntry 1 }


pktSwchAsyncRunProChannelNumber OBJECT-TYPE
    SYNTAX Integer32
    MAX-ACCESS  read-only
    STATUS  current
    DESCRIPTION
	"The channel to which this entry applies.  This value is the same as the pktSwchChannelNumber."
    ::= { pktSwchAsyncRunProEntry 2 }




pktSwchAsyncRunProRecallChar  OBJECT-TYPE
    SYNTAX Integer32 (0..126)
    MAX-ACCESS  read-only
    STATUS  current
    DESCRIPTION
	"The character specified by this entry is used to escape from the data transfer
		 mode and enter the PAD command mode.  The integer values have the following meanings:
			 (0)                 PAD recall is not possible
			 (1)                 The PAD recall character is DLE
			 (2)  to (126)  The PAD recall character is specified by the user by entering its ASCII
		code."
    ::= { pktSwchAsyncRunProEntry 3  }

pktSwchAsyncRunProEcho OBJECT-TYPE
    SYNTAX  INTEGER {
       echEn(1),
       noEch(2)
     }
    MAX-ACCESS  read-only
    STATUS  current
    DESCRIPTION
	"This determines if an echo of the input characters is retured to the DTE.
		 The options are either  'echo enabled'  or 'no echo'."
   ::= { pktSwchAsyncRunProEntry 4  }

pktSwchAsyncRunProDataForwChar OBJECT-TYPE
    SYNTAX  Integer32 (0..127)
    MAX-ACCESS  read-only
    STATUS  current
    DESCRIPTION
	"The value is a sum of values (powers of two), where each value in the sum represents
		a character (or characters) that is (are) used as a data forwarding character.  The data
		forwarding characters are used to instruct the PAD to complete the assembly of and to
		forward a packet containing the data accumulated up to the reception of such a character.
		The values that may be included in the sum and their meanings are:
		0   Data forwarding characters are not used
		1   Alpha-numeric characters (A to Z, a to z, 0 to 9, inclusive)
		2   Character CR
		4   Characters ESC, BEL, ENQ, ACK
		8   Characters DEL, CAN, DC2
		16 Characters EOT, ETX
		32 Characters HT, LF, VT, FF
		64 All the other characters in colums 0 and 1 of IA5 and not listed above."
   ::= { pktSwchAsyncRunProEntry 5 }

pktSwchAsyncRunProIdleTimer OBJECT-TYPE
    SYNTAX  Integer32 (0..255)
    MAX-ACCESS  read-only
    STATUS  current
    DESCRIPTION
	"Packets will be forwarded when the idle timer expires.  The idle time interval is specified
		 as a multiple of 50 milliseconds.  The multiple is given by the parameter value.  For example,
		 a value of 60 sets an interval of 3 seconds.  If the parameter value is 0, no forwarding occurs
		 after the idle condition."
   ::= { pktSwchAsyncRunProEntry 6 }

pktSwchAsyncRunProDevFlowCont OBJECT-TYPE
    SYNTAX  INTEGER  {
       trans(1),
       transAndCom(2),
       noFlow(255)
    }
    MAX-ACCESS  read-only
    STATUS  current
    DESCRIPTION
	"This parameter determines whether or not the PAD uses software flow control for the
		attached device.  The options are either (1) PAD uses flow control during data transfer
		 mode, (2) PAD uses flow control both in the data transfer mode and in the command mode,
		 or (255) PAD does not use flow control."
   ::= { pktSwchAsyncRunProEntry 7 }

pktSwchAsyncRunProServSig OBJECT-TYPE
    SYNTAX  INTEGER  {
       serv(1),
       prompt(4),
       servAndPrompt(5),
       noSig(255)
    }
    MAX-ACCESS  read-only
    STATUS  current
    DESCRIPTION
	"This parameter is used to instruct the PAD whether to transfer PAD service signals and
		 the PAD prompt to the local DTE in standard format.  The options are (1) PAD service
		 signals are transmitted to the DTE using the standard format, (4) The PAD prompt is
		 transmitted using the standard format, (5) PAD service signals and the PAD prompt are
		 transmitted in the standard format, or (255) No PAD service signals are transmitted to the
		 DTE."
    ::= { pktSwchAsyncRunProEntry 8 }

pktSwchAsyncRunProBreak OBJECT-TYPE
    SYNTAX  Integer32 (0..31)
    MAX-ACCESS  read-only
    STATUS  current
    DESCRIPTION
	"The value is a sum of values (powers of two), where each value in the sum represents
		a PAD operation on receipt of the break signal from the DTE.
		The values that may be included in the sum and their meanings are:
		0   Nothing
		1   Send interrupt packet to network
		2   Send RESET packet to network
		4   Send and 'indication of break' message
		8   Escape from data transfer mode
		16 Discard output data waiting to be sent to the DTE ."
   ::= { pktSwchAsyncRunProEntry 9 }

pktSwchAsyncRunProDiscOut OBJECT-TYPE
    SYNTAX  INTEGER {
       discOut(1),
       normal(2)
     }
    MAX-ACCESS  read-only
    STATUS  current
    DESCRIPTION
	"This parameter instructs the PAD whether to forward the user sequences included in
		data packets to the local DTE or discard them.  The options are (1) discard output or
		 (2) normal data delivery.  If the value of radSPSProfileBreak is 21, the value of
		 pktSwchAsyncRunProDiscOut is automatically set to (1) when a break signal is received."
   ::= { pktSwchAsyncRunProEntry 10  }

pktSwchAsyncRunProCRPPadding OBJECT-TYPE
    SYNTAX  Integer32 (0..127)
    MAX-ACCESS  read-only
    STATUS  current
    DESCRIPTION
	"This parameter specifies the number of padding characters to be added after a carriage
		 return character is transmitted to the local DTE."
   ::= { pktSwchAsyncRunProEntry 11}

pktSwchAsyncRunProLineFold OBJECT-TYPE
    SYNTAX  Integer32 (0..255)
    MAX-ACCESS  read-only
    STATUS  current
    DESCRIPTION
	"This parameter specifies the maximum number of characters to be inserted before the
		 format effector.  If the value is zero, there is no insertion of a format effector (line folding)."
    ::= { pktSwchAsyncRunProEntry 12}

pktSwchAsyncRunProSpeed OBJECT-TYPE
    SYNTAX  INTEGER  {
       s110bps(1),
       s300bps(2),
       s1200bps(3),
       s600bps(4),
       s75bps(5),
       s150bps(6),
       s2400bps(12),
       s4800bps(13),
       s9600bps(14),
       s19200bps(15),
       s38400bps(19),
	   s57600bps(20),
	   s115200bps(21)
    }
    MAX-ACCESS  read-only
    STATUS  current
    DESCRIPTION
	"This parameter determines the rate of data transmission to and from the DTE."
    ::= { pktSwchAsyncRunProEntry 13 }

pktSwchAsyncRunProPadFlowCont OBJECT-TYPE
    SYNTAX  INTEGER {
       flowCont(1),
       noFlowCont(2)
     }
    MAX-ACCESS  read-only
    STATUS  current
    DESCRIPTION
	"This determines whether or not the terminal can exercise flow control over the PAD.
		 The options are either 'device can exercise flow control' or 'device cannot exercise flow
		 control."
   ::= { pktSwchAsyncRunProEntry 14  }

pktSwchAsyncRunProLineFeedInsert OBJECT-TYPE
    SYNTAX  INTEGER  {
       afterCR(1),
       recCR(2),
       echoCR(4),
       onePlusFour(5),
       twoPlusFour(6),
       oneTwoFour(7),
       noFeed(255)
    }
    MAX-ACCESS  read-only
    STATUS  current
    DESCRIPTION
	"This parameter indicates when there is a line feed insertion after CR.  The options are
		  (1) Insert line feed after transmission of CR to the DTE, (2) Insert line feed after receipt
		 of CR from the DTE, (4) Insert line feed after echoing a CR character to the DTE,
		 (5) Combination of (1) and (4), (6) Insert line feed after any CR to the DTE (combination of
		 (2) and (4)), (7) Combination of (1), (2), and (4), or (255) No line feed insertion."
    ::= { pktSwchAsyncRunProEntry 15 }

pktSwchAsyncRunProLineFeedPad OBJECT-TYPE
    SYNTAX  Integer32 (0..255)
    MAX-ACCESS  read-only
    STATUS  current
    DESCRIPTION
	"This parameter specifies the number of padding characters to be added after a line
		 feed."
   ::= { pktSwchAsyncRunProEntry 16 }

pktSwchAsyncRunProEditing OBJECT-TYPE
    SYNTAX  INTEGER {
       edit(1),
       noEdit(2)
     }
    MAX-ACCESS  read-only
    STATUS  current
    DESCRIPTION
	"This parameter specifies the editing capabilities available in the data transfer mode.
		Editing is always possible when the PAD is in the command mode.  The options are
		 (1) Command editing in the data trasfer mode is enabled or (2) No command editing
		 in the data transfer mode."
   ::= { pktSwchAsyncRunProEntry 17  }

pktSwchAsyncRunProCharDel OBJECT-TYPE
    SYNTAX  Integer32 (0..127)
    MAX-ACCESS  read-only
    STATUS  current
    DESCRIPTION
	"This parameter specifies the character delete, which is one character from IA5.  The default
		selection is 127 (character DEL)."
   ::= { pktSwchAsyncRunProEntry 18}

pktSwchAsyncRunProLineDel OBJECT-TYPE
    SYNTAX  Integer32 (0..127)
    MAX-ACCESS  read-only
    STATUS  current
    DESCRIPTION
	"This parameter specifies the line delete, which is one character from IA5.  The default
		selection is 24 (character CAN)."
   ::= { pktSwchAsyncRunProEntry 19}

pktSwchAsyncRunProLineDisp OBJECT-TYPE
    SYNTAX  Integer32 (0..127)
    MAX-ACCESS  read-only
    STATUS  current
    DESCRIPTION
	"This entry specifies the line display character, which is one character
		from IA5.  The default selection is 18 (character DC2)."
   ::= { pktSwchAsyncRunProEntry 20}

pktSwchAsyncRunProEditServSig  OBJECT-TYPE
    SYNTAX Integer32 (0..126)
    MAX-ACCESS  read-only
    STATUS  current
    DESCRIPTION
	"This entry specifies the editing PAD service signals.
		The integer values have the following meanings:
			 (0)                 No editing PAD service signals
			 (1)                 Editing PAD service signals for printing terminals
			 (2)                 Editing PAD service signals for display terminals
			 (3)  to (126)  Editing PAD service signals using the desired character from IA5."
    ::= { pktSwchAsyncRunProEntry 21  }

pktSwchAsyncRunProEchomask OBJECT-TYPE
    SYNTAX  Integer32 (0..255)
    MAX-ACCESS  read-only
    STATUS  current
    DESCRIPTION
	"The value is a sum of values (powers of two), where each value in the sum represents
		a character (or characters) that is (are) included in the echo mask.  The characters in the
		echo mask are not echoed to the DTE when PAD echo is enabled.
		The values that may be included in the sum and their meanings are:
		0   No echo mask (all the characters are echoed)
		1   No echo of character CR
		2   No echo of character LF
		4   No echo of characters VT, HT, FF
		8   No echo of characters BEL, BS
		16 No echo of characters ESC, ENQ
		32 No echo of characters ACK, NAK, STX, SOH, EOT, ETB, ETX
		64 No echo of the editing characters selected by radSPSProfileCharDel,
														       radSPSProfileLineDel, and
														       radSPSProfileLineDisp
				128 No echo of the DEL character and of all the other characters in the range of
					ASCII 00 through 31 not mentioned above."
	::= { pktSwchAsyncRunProEntry 22 }

pktSwchAsyncRunProParTreat OBJECT-TYPE
    SYNTAX  INTEGER  {
       parCheck(1),
       parGen(2),
       checkAndGen(3),
       noPar(255)
    }
    MAX-ACCESS  read-only
    STATUS  current
    DESCRIPTION
	"This entry controls the generation of parity bits in the data sent to the local DTE and the
		checking of the parity bit when generated by the local DTE.  The options are (1) parity
		checking is enabled, (2) parity generation is enabled, (3) parity checking and generation are
		enabled, or (255) no parity checking nor parity generation."
    ::= { pktSwchAsyncRunProEntry 23 }

pktSwchAsyncRunProPageWait OBJECT-TYPE
    SYNTAX  Integer32 (0..255)
    MAX-ACCESS  read-only
    STATUS  current
    DESCRIPTION
	"This entry specifies the number of line feed characters counted by the PAD before the
		page wait condition is entered.  If the value is zero, page wait is disabled."
   ::= { pktSwchAsyncRunProEntry 24}


-- pktSwch defines the scratch and active PhyInterface configurations of
-- the PS

pktSwchPhyInterfaceTable    OBJECT-TYPE
    SYNTAX  SEQUENCE  OF PktSwchPhyInterfaceEntry
    MAX-ACCESS  not-accessible
    STATUS  current
    DESCRIPTION
	"The Link Table defines the links configured on the PS."
     ::=  { radPS 3 }

pktSwchPhyInterfaceEntry OBJECT-TYPE
    SYNTAX  PktSwchPhyInterfaceEntry
    MAX-ACCESS  not-accessible
    STATUS  current
    DESCRIPTION
	"Defines the contents of each line in the Link Table."
    INDEX   { pktSwchPhyInterfaceIfIndex }
    ::=  { pktSwchPhyInterfaceTable 1 }

PktSwchPhyInterfaceEntry ::= SEQUENCE {
    pktSwchPhyInterfaceIfIndex
     Integer32,
    pktSwchPhyInterfaceProtocolS
     INTEGER,
    pktSwchPhyInterfaceProtocolA
     INTEGER,
    pktSwchPhyInterfaceCopyTo
     Integer32,
    pktSwchPhyInterfaceChanged
     INTEGER,
    pktSwchPhyInterfaceRxBuffInPool
     Integer32,
    pktSwchPhyInterfaceConnector
     INTEGER,
    pktSwchPhyInterfaceNeighborIp
     IpAddress,
    pktSwchPhyInterfaceProtocolStatus
     INTEGER,
    pktSwchPhyInterfaceTestCmd
     INTEGER,
    pktSwchPhyInterfaceTestTransmittedFrames
     Counter32,
    pktSwchPhyInterfaceTestReceivedFrames
     Counter32,
    pktSwchPhyInterfaceTestLostFrames
     Integer32
    }

pktSwchPhyInterfaceIfIndex  OBJECT-TYPE
    SYNTAX Integer32
    MAX-ACCESS  read-only
    STATUS  current
    DESCRIPTION
	"The ifIndex identified with this link."
    ::= { pktSwchPhyInterfaceEntry 1 }

pktSwchPhyInterfaceProtocolS  OBJECT-TYPE
    SYNTAX INTEGER {
       x25(1),
       frameRelay(2),
       hdlc(3),
       sdlc(4),
       async(5),
       stm4(6),
       stm8(7),
       stm16(8),
       stm24(9),
       mpe(10),
       bscHpad(11),
       bscTpad(12),
       slip(13),
       ethernet(14),
       ppp(15)
     }
    MAX-ACCESS  read-write
    STATUS  current
    DESCRIPTION
        "The protocol to be used on this link.

         Note for PPP:
         PPP protocol is allowed to be applied on Sync Links (1-3)
         as well as Async channels (1-24).
         In order to eliminate ambiguity in the IP destination where
         a destination of P1 can be used for example for async channel 1
         and Sync Link 1, it was decided NOT TO ALLOW configuring PPP on both
         Sync Link no. 1 and async channel 1. Same for Link 2 and
         Link 3."
    ::= { pktSwchPhyInterfaceEntry 2 }

pktSwchPhyInterfaceProtocolA  OBJECT-TYPE
    SYNTAX INTEGER {
       x25(1),
       frameRelay(2),
       hdlc(3),
       sdlc(4),
       async(5),
       stm4(6),
       stm8(7),
       stm16(8),
       stm24(9),
       mpe(10),
       bscHpad(11),
       bscTpad(12),
       slip(13),
       ethernet(14),
       ppp(15)
     }
    MAX-ACCESS  read-only
    STATUS  current
    DESCRIPTION
	"The protocol  currently used on this link."
    ::= { pktSwchPhyInterfaceEntry 3 }

pktSwchPhyInterfaceCopyTo OBJECT-TYPE
 	SYNTAX Integer32
	MAX-ACCESS  read-write
	STATUS  current
    DESCRIPTION
	"The destination interface number, to which the Copy
	 is performed."
	::= { pktSwchPhyInterfaceEntry 4 }

pktSwchPhyInterfaceChanged OBJECT-TYPE
 	SYNTAX INTEGER {
	no  (2),
	yes (3)
	}
	MAX-ACCESS  read-only
	STATUS  current
    DESCRIPTION
	"Indicates if the current running protocol is different than the defined
	 protocol"
	::= { pktSwchPhyInterfaceEntry 5 }

pktSwchPhyInterfaceRxBuffInPool  OBJECT-TYPE
    SYNTAX Integer32
	MAX-ACCESS read-only
	STATUS current
	DESCRIPTION
	"The free data buffers in the Rx pool per interface"
	::= { pktSwchPhyInterfaceEntry 6 }

pktSwchPhyInterfaceConnector  OBJECT-TYPE
    SYNTAX INTEGER {
                    v24(2),
                    v35(3),
                    x21(4),
                    rs530(5),
                    acd(6),
                    mobi(7),
                    u(8),
                    etherUtp(9),
                    noConnector(255)
				   }
	MAX-ACCESS read-only
	STATUS current
	DESCRIPTION
	"The connector type of the interface"
	::= { pktSwchPhyInterfaceEntry 7 }

pktSwchPhyInterfaceNeighborIp  OBJECT-TYPE
    SYNTAX IpAddress
	MAX-ACCESS read-only
	STATUS current
	DESCRIPTION
	"The Ip address of the device on the other side of the link."
	::= { pktSwchPhyInterfaceEntry 8 }

pktSwchPhyInterfaceProtocolStatus OBJECT-TYPE
 	SYNTAX INTEGER {
       valid(1),
       createRequest(2),
       underCreation(3),
       invalid(4)
     }
    MAX-ACCESS  read-write
    STATUS  current
    DESCRIPTION
    "The status of the Interface Protocol row in the Table."
	::= { pktSwchPhyInterfaceEntry 9 }

pktSwchPhyInterfaceTestCmd OBJECT-TYPE
    SYNTAX INTEGER {
        noOp     (1),
        v54Local (2),
        v54Remote(3)
        }
    MAX-ACCESS  read-write
    STATUS  current
    DESCRIPTION
    "START/STOP a test on the current interface.
     The available tests are:
     v54Local  - Local  Analog  Loopback (AL), L3 according to ITU-T standard.
     v54Remote - Remote Digital Loopback(RDL), L2 according to ITU-T standard.
     For stopping the test, SET the noOp (1) option. "
 ::= { pktSwchPhyInterfaceEntry 10 }

pktSwchPhyInterfaceTestTransmittedFrames OBJECT-TYPE
    SYNTAX  Counter32
    MAX-ACCESS  read-only
    STATUS  current
    DESCRIPTION
    "No. of frames which were transmitted from this interface
     during the TEST."
 ::= { pktSwchPhyInterfaceEntry 11 }

pktSwchPhyInterfaceTestReceivedFrames OBJECT-TYPE
    SYNTAX  Counter32
    MAX-ACCESS  read-only
    STATUS  current
    DESCRIPTION
    "No. of frames which were received on this interface
     during the TEST."
 ::= { pktSwchPhyInterfaceEntry 12 }

pktSwchPhyInterfaceTestLostFrames OBJECT-TYPE
    SYNTAX  Integer32
    MAX-ACCESS  read-only
    STATUS  current
    DESCRIPTION
    "Percentage of the frames which were lost during the TEST."
 ::= { pktSwchPhyInterfaceEntry 13 }


-- The PS X.25 Group contains the Lapb Table, the PLP Table

pktSwchx25      OBJECT IDENTIFIER ::= { radPS 4 }

pktSwchLapb     OBJECT IDENTIFIER ::= { pktSwchx25 1 }

-- The PS Lapb Scratch Table

pktSwchLapbSTable  OBJECT-TYPE
    SYNTAX  SEQUENCE  OF PktSwchLapbSEntry
    MAX-ACCESS  not-accessible
    STATUS  current
    DESCRIPTION
	"The Lapb Table includes statistics and configurable objects
	 provided by the PS that are not included in RFC 1381."
    ::=  { pktSwchLapb 1 }

pktSwchLapbSEntry OBJECT-TYPE
    SYNTAX  PktSwchLapbSEntry
    MAX-ACCESS  not-accessible
    STATUS  current
    DESCRIPTION
	"Defines the contents of each line in the RAD Lapb Table."
    INDEX   { pktSwchLapbLinkNumberS }
    ::=  { pktSwchLapbSTable 1  }

PktSwchLapbSEntry ::= SEQUENCE {
    pktSwchLapbLinkNumberS
     Integer32,
    pktSwchLapbInternalClockS
     INTEGER,
    pktSwchLapbLineOptionS
     Integer32,
    pktSwchLapbSegmentSizeS
     Integer32,
    pktSwchLapbXIDS
     Integer32,
    pktSwchLapbAckCounterS
     Integer32,
    pktSwchLapbAckTimerS
     Integer32
      }

pktSwchLapbLinkNumberS  OBJECT-TYPE
    SYNTAX Integer32
    MAX-ACCESS  read-only
    STATUS  current
    DESCRIPTION
	"The link number with which this entry is associated.  This value
	 corresponds to pktSwchPhyInterfaceNumber.  There is an entry for
	 each link for which the pktSwchPhyInterfaceProtocol is X.25  and one
	 entry for each link and DLCI if the pktSwchPhyInterfaceProtocol for
	 the link is Frame Relay and the DLCI is defined as using X.25."
    ::= { pktSwchLapbSEntry 1 }

pktSwchLapbInternalClockS  OBJECT-TYPE
    SYNTAX INTEGER {
       r2400bps (1),
       r4800bps (2),
       r9600bps (3),
       r14400bps(4),
       r19200bps(5),
       r38400bps(6),
	   r48Kbps  (7),
       r56Kbps  (8),
       r64Kbps  (9),
       r128Kbps (10),
       r256Kbps (11),
	   r384Kbps (12),
       r504Kbps (13),
	   r768Kbps (14),
	   r1008Kbps(15),
       r1466Kbps(16),
       r2016Kbps(17),
       external(255)
     }
    MAX-ACCESS  read-write
    STATUS  current
    DESCRIPTION
	"The internal clock speed to be used on this LAPB link.  If external clock is used, the value is
	 255."
    ::= { pktSwchLapbSEntry 2 }

pktSwchLapbLineOptionS  OBJECT-TYPE
    SYNTAX Integer32 (0..2048)
    MAX-ACCESS  read-write
    STATUS  current
    DESCRIPTION
	"The line option to be used on this link.  A value of zero indicates
	 no options.  A value between 0 and 255 inclusive specifes a time in
	 minutes after which the line will be disconnected if no session is open.
	 The following values have the associated meanings:
			       256     Dialed line
			       512     Return to leased line
			       1024   DTR is ON permanent
			       2048   DTR is OFF permanent.
		 any valid combination of the above options should be represented as
		 a sum of the corresponding values. Valid combinations are:
		 DTR ON or OFF (but not both). Dialed line options or not applicable.
		 If DTR control is on (256), then all combinations are possible
		 except 1024 and 2048 (which are not possible)."
    ::= { pktSwchLapbSEntry 3 }

pktSwchLapbSegmentSizeS  OBJECT-TYPE
    SYNTAX Integer32 (1..4096)
    MAX-ACCESS  read-write
    STATUS  current
    DESCRIPTION
	"This value is for the use of billing information.  The value can be no larger than the maximum
		packet size."
    ::= { pktSwchLapbSEntry 4 }


pktSwchLapbXIDS  OBJECT-TYPE
    SYNTAX  Integer32
    MAX-ACCESS read-write
    STATUS  current
    DESCRIPTION
	"When this parameter is different than zero, this lapb is configured
	 as a V25 bis dialed link. This is the XID entry Index which this dialed link is
	 associated with."
	::= { pktSwchLapbSEntry 5 }

pktSwchLapbAckCounterS  OBJECT-TYPE
    SYNTAX  Integer32 (1..128)
    MAX-ACCESS read-write
    STATUS  current
    DESCRIPTION
        "This object defines how many frames will be received on the link
         before the PS will send Acknowledge (RR frame).
         It is used for Piggy Back Acknowledge (ack within the info frames)
         and saves traffic on the line.
         Default value: 1 ."
    ::= { pktSwchLapbSEntry 6 }

pktSwchLapbAckTimerS  OBJECT-TYPE
    SYNTAX  Integer32 (0..255)
    MAX-ACCESS read-write
    STATUS  current
    DESCRIPTION
         "The Ack Timer defines the maximum time in seconds that the device
         will wait before sending RR acknowledgment on the received frames.
         It is used for Piggy Back Acknowledge (ack within the info frames)
         and saves traffic on the line.
         Default value: 0 ."
        ::= { pktSwchLapbSEntry 7 }

-- The PS Lapb Active Table

pktSwchLapbATable  OBJECT-TYPE
    SYNTAX  SEQUENCE  OF PktSwchLapbAEntry
    MAX-ACCESS  not-accessible
    STATUS  current
    DESCRIPTION
	"The Lapb Table includes statistics and configurable objects provided
	 by the PS that are not included in RFC 1381."
    ::=  { pktSwchLapb 2 }

pktSwchLapbAEntry OBJECT-TYPE
    SYNTAX  PktSwchLapbAEntry
    MAX-ACCESS  not-accessible
    STATUS  current
    DESCRIPTION
	"Defines the contents of each line in the RAD Lapb Table."
    INDEX   { pktSwchLapbLinkNumberA }
    ::=  { pktSwchLapbATable 1  }

PktSwchLapbAEntry ::= SEQUENCE {
    pktSwchLapbLinkNumberA
     Integer32,
    pktSwchLapbInternalClockA
     INTEGER,
    pktSwchLapbLineOptionA
     Integer32,
    pktSwchLapbSegmentSizeA
     Integer32,
 	pktSwchLapbLineProtocol
	 INTEGER,
	pktSwchLapbLowerId
	 Integer32,
	pktSwchLapbXIDA
	 Integer32,
	pktSwchLapbTransmittedIFrames
     Counter32,
	pktSwchLapbReceivedIFrames
     Counter32,
	pktSwchLapbNSError
     Counter32,
    pktSwchLapbTransmittedRRFrames
     Counter32,
    pktSwchLapbReceivedRRFrames
     Counter32,
    pktSwchLapbTransmittedRNRFrames
     Counter32,
    pktSwchLapbReceivedRNRFrames
     Counter32,
    pktSwchLapbTransmittedFRMRFrames
     Counter32,
    pktSwchLapbReceivedFRMRFrames
     Counter32,
    pktSwchLapbAckCounterA
     Integer32,
    pktSwchLapbAckTimerA
     Integer32
     }


pktSwchLapbLinkNumberA  OBJECT-TYPE
    SYNTAX Integer32
    MAX-ACCESS  read-only
    STATUS  current
    DESCRIPTION
	"The link number with which this entry is associated.  This value corresponds to
		 pktSwchPhyInterfaceNumber.  There is an entry for each link for which the pktSwchPhyInterfaceProtocol is
		 X.25  and one entry for each link and DLCI if the pktSwchPhyInterfaceProtocol for the link is Frame
		 Relay and theDLCI is defined as using X.25."
    ::= { pktSwchLapbAEntry 1 }


pktSwchLapbInternalClockA  OBJECT-TYPE
    SYNTAX INTEGER {
       r2400bps (1),
       r4800bps (2),
       r9600bps (3),
       r14400bps(4),
       r19200bps(5),
       r38400bps(6),
	   r48Kbps  (7),
       r56Kbps  (8),
       r64Kbps  (9),
       r128Kbps (10),
       r256Kbps (11),
	   r384Kbps (12),
       r504Kbps (13),
	   r768Kbps (14),
	   r1008Kbps(15),
       r1466Kbps(16),
       r2016Kbps(17),
       external(255)
     }
    MAX-ACCESS  read-only
    STATUS  current
    DESCRIPTION
	"The internal clock speed currently used on this LAPB link.
	 If external clock is used, the value is 255."
    ::= { pktSwchLapbAEntry 2 }

pktSwchLapbLineOptionA  OBJECT-TYPE
    SYNTAX Integer32 (0..2048)
    MAX-ACCESS  read-only
    STATUS  current
    DESCRIPTION
	"The line option currently used on this link.  A value of zero
	 indicates no options.  A value between 1 and 255 inclusive specifes
	 a time in minutes after which the line will be disconnected if no
	 session is open.  The following values have the associated meanings:
			       256     Dialed line
			       512     Return to leased line
			       1024   DTR is ON permanent
			       2048   DTR is OFF permanent.
		 any valid combination of the above options should be represented as
		 a sum of the corresponding values. Valid combinations are:
		 DTR ON or OFF (but not both). Dialed line options or not applicable.
		 If DTR control is on (256), then all combinations are possible
		 except 1024 and 2048 (which are not possible)."
       ::= { pktSwchLapbAEntry 3 }

pktSwchLapbSegmentSizeA  OBJECT-TYPE
    SYNTAX Integer32 (1..4096)
    MAX-ACCESS  read-only
    STATUS  current
    DESCRIPTION
	"The current value of the segment size."
    ::= { pktSwchLapbAEntry 4 }

pktSwchLapbLineProtocol  OBJECT-TYPE
    SYNTAX  INTEGER {
	unknown(1),
	x25  (2),
	fr   (3),
	isdn (4)
	}
	MAX-ACCESS read-only
	STATUS  current
    DESCRIPTION
	"This is the lower level protocol which runs under this lapb interface."
	::= { pktSwchLapbAEntry 5 }

pktSwchLapbLowerId  OBJECT-TYPE
    SYNTAX  Integer32
	MAX-ACCESS read-only
	STATUS  current
    DESCRIPTION
	"In case of X.25 over Frame-relay this is the lower level link
	 number."
	::= { pktSwchLapbAEntry 6 }


pktSwchLapbXIDA  OBJECT-TYPE
    SYNTAX  Integer32
    MAX-ACCESS read-only
	STATUS  current
    DESCRIPTION
	"When this parameter is different than zero, this lapb is configured
	 as a V25 bis dialed link. This is the XID entry which this dialed link is
	 associated with."
	::= { pktSwchLapbAEntry 7 }

pktSwchLapbTransmittedIFrames  OBJECT-TYPE
    SYNTAX Counter32
    MAX-ACCESS  read-only
    STATUS  current
    DESCRIPTION
	"The transmitted I frames on this link."
    ::= { pktSwchLapbAEntry 8 }

pktSwchLapbReceivedIFrames  OBJECT-TYPE
    SYNTAX Counter32
    MAX-ACCESS  read-only
    STATUS  current
    DESCRIPTION
	"The received I frames on this link."
    ::= { pktSwchLapbAEntry 9 }

pktSwchLapbNSError  OBJECT-TYPE
    SYNTAX Counter32
    MAX-ACCESS  read-only
    STATUS  current
    DESCRIPTION
	"The number of I frames transmitted out of sequence."
    ::= { pktSwchLapbAEntry 10 }

pktSwchLapbTransmittedRRFrames  OBJECT-TYPE
    SYNTAX Counter32
    MAX-ACCESS  read-only
    STATUS  current
    DESCRIPTION
	"The transmitted RR frames on this link."
    ::= { pktSwchLapbAEntry 11 }

pktSwchLapbReceivedRRFrames  OBJECT-TYPE
    SYNTAX Counter32
    MAX-ACCESS  read-only
    STATUS  current
    DESCRIPTION
	"The received RR frames on this link."
    ::= { pktSwchLapbAEntry 12 }

pktSwchLapbTransmittedRNRFrames  OBJECT-TYPE
    SYNTAX Counter32
    MAX-ACCESS  read-only
    STATUS  current
    DESCRIPTION
	"The transmitted RNR frames on this link."
    ::= { pktSwchLapbAEntry 13 }

pktSwchLapbReceivedRNRFrames  OBJECT-TYPE
    SYNTAX Counter32
    MAX-ACCESS  read-only
    STATUS  current
    DESCRIPTION
	"The received RNR frames on this link."
    ::= { pktSwchLapbAEntry 14 }

pktSwchLapbTransmittedFRMRFrames  OBJECT-TYPE
    SYNTAX Counter32
    MAX-ACCESS  read-only
    STATUS  current
    DESCRIPTION
	"The transmitted FRMR frames on this link."
    ::= { pktSwchLapbAEntry 15 }

pktSwchLapbReceivedFRMRFrames  OBJECT-TYPE
    SYNTAX Counter32
    MAX-ACCESS  read-only
    STATUS  current
    DESCRIPTION
	"The received FRMR frames on this link."
    ::= { pktSwchLapbAEntry 16 }

pktSwchLapbAckCounterA  OBJECT-TYPE
    SYNTAX  Integer32 (1..128)
    MAX-ACCESS read-only
    STATUS  current
    DESCRIPTION
        "This object defines how many frames will be received on the link
         before the PS will send Acknowledge (RR frame).
         It is used for Piggy Back Acknowledge (ack within the info frames)
         and saves traffic on the line.
         Default value: 1 ."
        ::= { pktSwchLapbAEntry 17 }

pktSwchLapbAckTimerA  OBJECT-TYPE
    SYNTAX  Integer32 (0..255)
    MAX-ACCESS read-only
    STATUS  current
    DESCRIPTION
         "The Ack Timer defines the maximum time in seconds that the device
         will wait before sending RR acknowledgment on the received frames.
         It is used for Piggy Back Acknowledge (ack within the info frames)
         and saves traffic on the line.
         Default value: 0 ."
        ::= { pktSwchLapbAEntry 18 }



-- PLP (Packet Layer Protocol: Scratch + Active}

pktSwchPlp  OBJECT IDENTIFIER  ::=  { pktSwchx25 2 }

-- PLP Scratch table

pktSwchPlpSTable  OBJECT-TYPE
    SYNTAX  SEQUENCE  OF PktSwchPlpSEntry
    MAX-ACCESS  not-accessible
    STATUS  current
    DESCRIPTION
	"The Scratch Plp Table includes configurable objects provided by the PS
		that are not included in RFC 1382."
    ::=  { pktSwchPlp 1 }

pktSwchPlpSEntry OBJECT-TYPE
    SYNTAX  PktSwchPlpSEntry
    MAX-ACCESS  not-accessible
    STATUS  current
    DESCRIPTION
	"Defines the contents of each line in the RAD Scratch Plp Table."
    INDEX   { pktSwchPlpLinkNumberS }
    ::=  { pktSwchPlpSTable 1  }

PktSwchPlpSEntry ::= SEQUENCE {
    pktSwchPlpLinkNumberS
     Integer32,
    pktSwchPlpInCallOptionS
     Integer32,
    pktSwchPlpOutCallOptionS
     Integer32,
    pktSwchPlpCugSubscriptionS
     INTEGER,
	pktSwchPlpNUIS
	 Integer32,
	pktSwchPlpCpyPktSize
	 Integer32,
	pktSwchPlpCpyWinSize
	 Integer32
    }

pktSwchPlpLinkNumberS  OBJECT-TYPE
    SYNTAX Integer32
    MAX-ACCESS  read-only
    STATUS  current
    DESCRIPTION
	"The ifIndex of the X.25 interface."
    ::= { pktSwchPlpSEntry 1 }

pktSwchPlpInCallOptionS  OBJECT-TYPE
    SYNTAX Integer32 (0..15)
    MAX-ACCESS  read-write
    STATUS  current
    DESCRIPTION
	"The in call options for the link.  The value is a sum of values (powers of two), where each
		 value in the sum represents an option.  The values that may be included in the sum and
		 their meanings are:
		0 No options
		1 Fast select acceptance - included in RFC 1382
		2 Reverse charge acceptance - included in RFC 1382
		4 Subaddress in Call User Data field (CUD)
				8 Protocol ID (PID) is not used."
    ::= { pktSwchPlpSEntry 2 }

pktSwchPlpOutCallOptionS  OBJECT-TYPE
    SYNTAX Integer32 (0..15)
    MAX-ACCESS  read-write
    STATUS  current
    DESCRIPTION
	"The out call options for the link. The value is a sum of values
	 (powers of two), where each value in the sum represents an
	 option. The values that may be included in the sum and their
	 meanings are:
		0 No options
		1 Don't add calling and call addressin call accept packet
		2 Network link, call request spread enabled
		4 Add source link number to called address
	  	8 Don't change calling address
	  	XX - Any combination of the values specified above."
      ::= { pktSwchPlpSEntry 3 }

pktSwchPlpCugSubscriptionS  OBJECT-TYPE
    SYNTAX INTEGER {
       cug(1),    --  CUG with preferential
       cugOa(2),   --  CUG/OA with preferential
       cugIa(3),   --  CUG/IA with preferential
       cugOaIa(4),   --  CUG/OA/IA with preferential
       noPref(5),    -- CUG/OA/IA without preferential (transparent)
       noCug(255)  -- no CUG
     }
    MAX-ACCESS  read-write
    STATUS  current
    DESCRIPTION
	"The CUG subscription for the link."
    ::= { pktSwchPlpSEntry 4 }

pktSwchPlpNUIS OBJECT-TYPE
 	SYNTAX Integer32
    MAX-ACCESS  read-write
    STATUS  current
    DESCRIPTION
    "This is the NUI group which this Plp is part of."
	::= { pktSwchPlpSEntry 5 }

pktSwchPlpCpyPktSize OBJECT-TYPE
 	SYNTAX Integer32
    MAX-ACCESS  read-write
    STATUS  current
    DESCRIPTION
    "x25 packet size."
	::= { pktSwchPlpSEntry 6 }

pktSwchPlpCpyWinSize OBJECT-TYPE
 	SYNTAX Integer32
    MAX-ACCESS  read-write
    STATUS  current
    DESCRIPTION
    "x25 window size."
	::= { pktSwchPlpSEntry 7 }


-- PLP Active table

pktSwchPlpATable  OBJECT-TYPE
    SYNTAX  SEQUENCE  OF PktSwchPlpAEntry
    MAX-ACCESS  not-accessible
    STATUS  current
    DESCRIPTION
	"The Active Plp Table includes objects provided by the PS
		that are not included in RFC 1382.  It also includes some packet
		layer statistics, some of which are defined in RFC 1382, but are
	    not supported there, as the x25StatTable in RFC 1382 is not supported."
    ::=  { pktSwchPlp 2 }

pktSwchPlpAEntry OBJECT-TYPE
    SYNTAX  PktSwchPlpAEntry
    MAX-ACCESS  not-accessible
    STATUS  current
    DESCRIPTION
	"Defines the contents of each line in the RAD Active Plp Table."
    INDEX   { pktSwchPlpLinkNumberA }
    ::=  { pktSwchPlpATable 1 }

PktSwchPlpAEntry ::= SEQUENCE {
    pktSwchPlpLinkNumberA
     Integer32,
    pktSwchPlpInCallOptionA
     Integer32,
    pktSwchPlpOutCallOptionA
     Integer32,
    pktSwchPlpCugSubscriptionA
     INTEGER,
	pktSwchPlpNUIA
	 Integer32,
	pktSwchStatOutRestarts
	 Counter32
    }

pktSwchPlpLinkNumberA  OBJECT-TYPE
    SYNTAX Integer32
    MAX-ACCESS  read-only
    STATUS  current
    DESCRIPTION
	"The link number with which this entry is associated.  This value corresponds to
		 pktSwchPhyInterfaceNumber.  There is an entry for each link for which the pktSwchPhyInterfaceProtocol is
		 X.25  and one entry for each link and DLCI if the pktSwchPhyInterfaceProtocol for the link is Frame
		 Relay and theDLCI is defined as using X.25."
    ::= { pktSwchPlpAEntry 1 }

pktSwchPlpInCallOptionA  OBJECT-TYPE
    SYNTAX Integer32 (0..15)
    MAX-ACCESS  read-only
    STATUS  current
    DESCRIPTION
	"The current in call options for the link.  The value is a sum of values (powers of two),
		 where each value in the sum represents an option.  The values that can be included in
		 the sum and their meanings are:
		0 No options
		1 Fast select acceptance - included in RFC 1382
		2 Reverse charge acceptance - included in RFC 1382
		4 Subaddress in Call User Data field (CUD)
				8 Protocol ID (PID) is not used."
    ::= { pktSwchPlpAEntry 2 }

pktSwchPlpOutCallOptionA  OBJECT-TYPE
    SYNTAX Integer32 (0..15)
    MAX-ACCESS  read-only
    STATUS  current
    DESCRIPTION
	"The out call options for the link. The value is a sum of values
	 (powers of two), where each value in the sum represents an
	 option. The values that may be included in the sum and their
	 meanings are:
		0 No options
		1 Don't add calling and call addressin call accept packet
		2 Network link, call request spread enabled
		4 Add source link number to called address
	  	8 Don't change calling address
	  	XX - Any combination of the values specified above."
    ::= { pktSwchPlpAEntry 3 }

pktSwchPlpCugSubscriptionA  OBJECT-TYPE
    SYNTAX INTEGER {
       cug(1),    --  CUG with preferential
       cugOa(2),   --  CUG/OA with preferential
       cugIa(3),   --  CUG/IA with preferential
       cugOaIa(4),   --  CUG/OA/IA with preferential
       noPref(5),    -- CUG/OA/IA without preferential (transparent)
       noCug(255)  -- no CUG
     }
    MAX-ACCESS  read-only
    STATUS  current
    DESCRIPTION
	"The current CUG subscription for the link."
    ::= { pktSwchPlpAEntry 4 }

pktSwchPlpNUIA OBJECT-TYPE
 	SYNTAX  Integer32
    MAX-ACCESS  read-only
    STATUS  current
    DESCRIPTION
    "This is the NUI group which this Plp is part of."
	::= { pktSwchPlpAEntry 5 }

pktSwchStatOutRestarts OBJECT-TYPE
    SYNTAX  Counter32
    MAX-ACCESS  read-only
    STATUS  current
    DESCRIPTION
        "The number of remotely initiated (including
         provider initiated) restarts experienced by
         the PLE excluding the restart associated
         with bringing up the PLE interface.  This
         only counts restarts received when the PLE
         already has an established connection with
         the remove PLE."
   ::= { pktSwchPlpAEntry 6 }



pktSwchPlaceHolderForFutureUse  OBJECT IDENTIFIER  ::=  { pktSwchx25 3 }


-- CUG (Scratch + Active}

pktSwchCug  OBJECT IDENTIFIER  ::=  { pktSwchx25 4 }

-- CUG Scratch table


pktSwchCugSTable  OBJECT-TYPE
    SYNTAX  SEQUENCE  OF PktSwchCugSEntry
    MAX-ACCESS  not-accessible
    STATUS  current
    DESCRIPTION
	"The Scratch Cug Table lists the Closed User Groups defined to each
	 X.25 link."
    ::=  { pktSwchCug 1 }

pktSwchCugSEntry OBJECT-TYPE
    SYNTAX  PktSwchCugSEntry
    MAX-ACCESS  not-accessible
    STATUS  current
    DESCRIPTION
	"Defines the contents of each line in the Scratch RAD Cug Table."
    INDEX   { pktSwchCugLinkNumberS,  pktSwchCugIndexS }
    ::=  { pktSwchCugSTable 1  }

PktSwchCugSEntry ::= SEQUENCE {
    pktSwchCugLinkNumberS
     Integer32,
    pktSwchCugIndexS
     Integer32,
    pktSwchCugNumberS
     Integer32,
    pktSwchCugStatus
     INTEGER
    }

pktSwchCugLinkNumberS  OBJECT-TYPE
    SYNTAX Integer32
    MAX-ACCESS  read-only
    STATUS  current
    DESCRIPTION
	"The link number with which this entry is associated.  This value
	 corresponds to pktSwchPhyInterfaceNumber.  There is an entry for
	 each link for which the pktSwchPhyInterfaceProtocol is X.25  if the
	 link has CUG options and one entry for each link and DLCI if the
	 pktSwchPhyInterfaceProtocol for the link is Frame Relay and the DLCI
	 is defined as using X.25 if the link has CUG options."
    ::= { pktSwchCugSEntry 1 }

pktSwchCugIndexS  OBJECT-TYPE
    SYNTAX Integer32                       -- how many CUGs??
    MAX-ACCESS  read-only
    STATUS  current
    DESCRIPTION
	"The index of the CUG for a specific link.  The lowest indexed CUG
	 is the preferential CUG."
    ::= { pktSwchCugSEntry 2 }

pktSwchCugNumberS  OBJECT-TYPE
    SYNTAX Integer32
    MAX-ACCESS  read-write
    STATUS  current
    DESCRIPTION
	"The CUG number for this entry."
    ::= { pktSwchCugSEntry 3 }

pktSwchCugStatus OBJECT-TYPE
    SYNTAX  INTEGER {
       valid(1),
       createRequest(2),
       underCreation(3),
       invalid(4)
     }
    MAX-ACCESS  read-write
    STATUS  current
    DESCRIPTION
	"The status of this CUG table entry.  The choices are those defined in the SNMPv2 Textual
		 Conventions for RowStatus.  This will allow easy replacement of the INTEGER syntax with
		 the RowStatus textual convention SYNTAX."
  ::= { pktSwchCugSEntry 4 }

-- CUG Active table

pktSwchCugATable  OBJECT-TYPE
    SYNTAX  SEQUENCE  OF PktSwchCugAEntry
    MAX-ACCESS  not-accessible
    STATUS  current
    DESCRIPTION
	"The Active Cug Table lists the active Closed User Groups defined
	 to each X.25 link."
    ::=  { pktSwchCug 2 }

pktSwchCugAEntry OBJECT-TYPE
    SYNTAX  PktSwchCugAEntry
    MAX-ACCESS  not-accessible
    STATUS  current
    DESCRIPTION
	"Defines the contents of each line in the Active RAD Cug Table."
    INDEX   { pktSwchCugLinkNumberA,  pktSwchCugIndexA }
    ::=  { pktSwchCugATable 1  }

PktSwchCugAEntry ::= SEQUENCE {
    pktSwchCugLinkNumberA
     Integer32,
    pktSwchCugIndexA
     Integer32,
    pktSwchCugNumberA
     Integer32
    }

pktSwchCugLinkNumberA  OBJECT-TYPE
    SYNTAX Integer32
    MAX-ACCESS  read-only
    STATUS  current
    DESCRIPTION
	"The link number with which this entry is associated.  This value corresponds to
		 pktSwchPhyInterfaceNumber.  There is an entry for each link for which the pktSwchPhyInterfaceProtocol is
		 X.25  if the link has CUG options and one entry for each link and DLCI if the
		 pktSwchPhyInterfaceProtocol for the link is Frame Relay and theDLCI is defined as using X.25
		 if the link has CUG options."
    ::= { pktSwchCugAEntry 1 }

pktSwchCugIndexA  OBJECT-TYPE
    SYNTAX Integer32
    MAX-ACCESS  read-only
    STATUS  current
    DESCRIPTION
	"The index of the CUG for a specific link.  The lowest indexed CUG is the preferential CUG."
    ::= { pktSwchCugAEntry 2 }

pktSwchCugNumberA  OBJECT-TYPE
    SYNTAX Integer32
    MAX-ACCESS  read-only
    STATUS  current
    DESCRIPTION
	"The CUG number for this entry."
    ::= { pktSwchCugAEntry 3 }


--  X.25 Channel LCN Table

pktSwchLogCh  OBJECT IDENTIFIER  ::=  { pktSwchx25 5 }

pktSwchLogChAssTable OBJECT-TYPE
SYNTAX  SEQUENCE OF PktSwchLogChAssEntry
MAX-ACCESS  not-accessible
STATUS  current
DESCRIPTION
        "These objects contain information about the
        channel number configuration in an X.25 PLE.
        These values are the configured values.
        changes in these values after the interface
        has started may not be reflected in the
        operating PLE."
REFERENCE "See ISO 8208, Section 3.7"
::= {pktSwchLogCh 1 }

pktSwchLogChAssEntry OBJECT-TYPE
        SYNTAX  PktSwchLogChAssEntry
        MAX-ACCESS  not-accessible
        STATUS  current
        DESCRIPTION
                "Entries of pktSwchLogChAssTable."
        REFERENCE "This provides the information available
                in 10733 logicalChannelAssignments."
        INDEX { pktSwchLogChAssIndex }
        ::= { pktSwchLogChAssTable 1    }

PktSwchLogChAssEntry ::= SEQUENCE {
        pktSwchLogChAssIndex
                IfIndexType,
        pktSwchLogChAssLIC
                Integer32,
        pktSwchLogChAssHIC
                Integer32,
        pktSwchLogChAssLTC
                Integer32,
        pktSwchLogChAssHTC
                Integer32,
        pktSwchLogChAssLOC
                Integer32,
        pktSwchLogChAssHOC
                Integer32
        }

pktSwchLogChAssIndex OBJECT-TYPE
        SYNTAX  IfIndexType
        MAX-ACCESS  read-only
        STATUS  current
        DESCRIPTION
                "The ifIndex value for the X.25 Interface."
        ::= { pktSwchLogChAssEntry 1 }


pktSwchLogChAssLIC OBJECT-TYPE
        SYNTAX  Integer32 (0..4095)
        MAX-ACCESS  read-only
        STATUS  current
        DESCRIPTION
                "Lowest Incoming channel."
        ::= { pktSwchLogChAssEntry 2 }

pktSwchLogChAssHIC OBJECT-TYPE
        SYNTAX  Integer32 (0..4095)
        MAX-ACCESS  read-only
        STATUS  current
        DESCRIPTION
                "Highest Incoming channel.  A value of zero
                indicates no channels in this range."
        ::= { pktSwchLogChAssEntry 3 }

pktSwchLogChAssLTC OBJECT-TYPE
        SYNTAX  Integer32 (0..4095)
        MAX-ACCESS  read-only
        STATUS  current
        DESCRIPTION
                "Lowest Two-way channel."
        ::= { pktSwchLogChAssEntry 4 }

pktSwchLogChAssHTC OBJECT-TYPE
        SYNTAX  Integer32 (0..4095)
        MAX-ACCESS  read-only
        STATUS  current
        DESCRIPTION
                "Highest Two-way channel.  A value of zero
                indicates no channels in this range."
        ::= { pktSwchLogChAssEntry 5 }

pktSwchLogChAssLOC OBJECT-TYPE
        SYNTAX  Integer32 (0..4095)
        MAX-ACCESS  read-only
        STATUS  current
        DESCRIPTION
                "Lowest outgoing channel."
        ::= { pktSwchLogChAssEntry 6 }

pktSwchLogChAssHOC OBJECT-TYPE
        SYNTAX  Integer32 (0..4095)
        MAX-ACCESS  read-only
        STATUS  current
        DESCRIPTION
                "Highest outgoing channel.  A value of zero
                indicates no channels in this range."
        ::= { pktSwchLogChAssEntry 7 }

pktSwchLogChPartnerTable OBJECT-TYPE
SYNTAX  SEQUENCE OF PktSwchLogChPartnerEntry
MAX-ACCESS  not-accessible
STATUS  current
DESCRIPTION
        "These objects contain information about the
        partner channel number configuration in an X.25 PLE.
        These values are the configured values.
        changes in these values after the interfaces
        has started may not be reflected in the
        operating PLE."
REFERENCE "See ISO 8208, Section 3.7"
::= {pktSwchLogCh 2 }

pktSwchLogChPartnerEntry  OBJECT-TYPE
        SYNTAX  PktSwchLogChPartnerEntry
        MAX-ACCESS  not-accessible
        STATUS  current
        DESCRIPTION
                "Entries of pktSwchLogChPartnerTable."
        REFERENCE "This provides the information available
                in 10733 logicalChannelPartners."
        INDEX { pktSwchLogChPartnerIfIndex, pktSwchLogChPartnerLcIndex }
        ::= { pktSwchLogChPartnerTable 1 }

PktSwchLogChPartnerEntry  ::= SEQUENCE {
        pktSwchLogChPartnerIfIndex
		IfIndexType,
		pktSwchLogChPartnerLcIndex
		Integer32,
		pktSwchLogChPartnerProtocol
		INTEGER,
		pktSwchLogChPartnerOpIfIndex
		IfIndexType,
		pktSwchLogChPartnerOpLcIndex
		Integer32
		}

pktSwchLogChPartnerIfIndex  OBJECT-TYPE
        SYNTAX  IfIndexType
        MAX-ACCESS  read-only
        STATUS  current
        DESCRIPTION
                "The ifIndex value for the Lapb Interface."
        ::= { pktSwchLogChPartnerEntry 1 }

pktSwchLogChPartnerLcIndex OBJECT-TYPE
		SYNTAX  Integer32
        MAX-ACCESS  read-only
        STATUS  current
        DESCRIPTION
                "The Index value for the LCN."
        ::= { pktSwchLogChPartnerEntry 2 }

pktSwchLogChPartnerProtocol OBJECT-TYPE
		SYNTAX  INTEGER {
		                  other(1),
                          x25(2),
                          hdlc(3),
                          sdlc(4),
                          async(5),
	                      mpe(6),
						  ip(7)
	                 	}
        MAX-ACCESS  read-only
        STATUS  current
        DESCRIPTION
                " The protocol of the partner."
        ::= { pktSwchLogChPartnerEntry 3 }

pktSwchLogChPartnerOpIfIndex  OBJECT-TYPE
        SYNTAX  IfIndexType
        MAX-ACCESS  read-only
        STATUS  current
        DESCRIPTION
                "The ifIndex value for the partner Lapb Interface."
        ::= { pktSwchLogChPartnerEntry 4 }


pktSwchLogChPartnerOpLcIndex OBJECT-TYPE
		SYNTAX  Integer32
        MAX-ACCESS  read-only
        STATUS  current
        DESCRIPTION
                "The Index value for the partner LCN."
        ::= { pktSwchLogChPartnerEntry 5 }



-- The PS HDLC Group contains  HDLC Scratch and Active Tables, which contain configuration for
-- HDLC links

pktSwchHdlc   OBJECT IDENTIFIER ::= { radPS 5 }

pktSwchHdlcSTable  OBJECT-TYPE
    SYNTAX  SEQUENCE  OF PktSwchHdlcSEntry
    MAX-ACCESS  not-accessible
    STATUS  current
    DESCRIPTION
	"The Scratch Hdlc Table contains configuration information for HDLC links"
    ::=  { pktSwchHdlc 1 }

pktSwchHdlcSEntry OBJECT-TYPE
    SYNTAX  PktSwchHdlcSEntry
    MAX-ACCESS  not-accessible
    STATUS  current
    DESCRIPTION
	"Defines the contents of each line in the RAD Hdlc Table."
    INDEX   { pktSwchHdlcLinkNumberS }
    ::=  { pktSwchHdlcSTable 1  }

PktSwchHdlcSEntry ::= SEQUENCE {
    pktSwchHdlcLinkNumberS
     Integer32,
    pktSwchHdlcDestAddrS
     DisplayString,
    pktSwchHdlcDestSubAddrS
     Integer32,
    pktSwchHdlcRedialTimeoutS
     Integer32,
    pktSwchHdlcRedialRetriesS
     Integer32,
    pktSwchHdlcInactivityS
     Integer32,
    pktSwchHdlcX25FacilitiesS
     Integer32,
    pktSwchHdlcLocalSubaddr1S
     Integer32,
    pktSwchHdlcLocalSubaddr2S
     Integer32,
    pktSwchHdlcDestDlciS
     Integer32,
    pktSwchHdlcDestPortS
     Integer32,
    pktSwchHdlcProtocolS
     INTEGER,
    pktSwchHdlcFlowContOptionsS
     Integer32,
    pktSwchHdlcBufferFlowControlS
     Integer32,
    pktSwchHdlcInternalClockS
     INTEGER,
    pktSwchHdlcNrzModeS
     Integer32
    }

pktSwchHdlcLinkNumberS  OBJECT-TYPE
    SYNTAX Integer32
    MAX-ACCESS  read-only
    STATUS  current
    DESCRIPTION
	"The link number with which this entry is associated.  This value
	 corresponds to pktSwchPhyInterfaceNumber.  There is an entry for
	 each link for which the pktSwchPhyInterfaceProtocol is HDLC."
    ::= { pktSwchHdlcSEntry 1 }

pktSwchHdlcDestAddrS  OBJECT-TYPE
    SYNTAX DisplayString
    MAX-ACCESS  read-write
    STATUS  current
    DESCRIPTION
	"The destination address.  It defines the X.25 address on the remote
	 device."
    ::= { pktSwchHdlcSEntry 2 }

pktSwchHdlcDestSubAddrS  OBJECT-TYPE
    SYNTAX Integer32 (0..99)
    MAX-ACCESS  read-write
    STATUS  current
    DESCRIPTION
	"The destination subaddress.  It defines the synchronous link subaddress
	 on the remote device."
    ::= { pktSwchHdlcSEntry 3 }

pktSwchHdlcRedialTimeoutS  OBJECT-TYPE
    SYNTAX Integer32 (0..255)   -- seconds??
    MAX-ACCESS  read-write
    STATUS  current
    DESCRIPTION
	"The time interval in seconds between two consecutive connect
	 operations retries."
    ::= { pktSwchHdlcSEntry 4 }

pktSwchHdlcRedialRetriesS  OBJECT-TYPE
    SYNTAX Integer32 (0..255)
    MAX-ACCESS  read-write
    STATUS  current
    DESCRIPTION
	"This defines how many times the call operation is repeated if the
	 call request has failed."
    ::= { pktSwchHdlcSEntry 5 }

pktSwchHdlcInactivityS  OBJECT-TYPE
    SYNTAX Integer32 (0..255)
    MAX-ACCESS  read-write
    STATUS  current
    DESCRIPTION
	"The amount of time in minutes of inactivity that will cause the
	 session to disconnect."
    ::= { pktSwchHdlcSEntry 6 }

pktSwchHdlcX25FacilitiesS  OBJECT-TYPE
    SYNTAX Integer32 (0..7)
    MAX-ACCESS  read-write
    STATUS  current
    DESCRIPTION
	"This specifies the X.25 facilities.  The value is a sum of values
	 (powers of two), where each value in the sum represents an option.
	 The values that may be included in the sum and their meanings are:
		0 No options
		1 Packet size negotiation
		2 Window size negotiation
		4 Reverse  charge."
    ::= { pktSwchHdlcSEntry 7 }

pktSwchHdlcLocalSubaddr1S  OBJECT-TYPE
    SYNTAX Integer32 (0..99)
    MAX-ACCESS  read-write
    STATUS  current
    DESCRIPTION
	"The first local subaddress."
    ::= { pktSwchHdlcSEntry 8 }

pktSwchHdlcLocalSubaddr2S  OBJECT-TYPE
    SYNTAX Integer32 (0..99)
    MAX-ACCESS  read-write
    STATUS  current
    DESCRIPTION
	"The secondary local subaddress."
    ::= { pktSwchHdlcSEntry 9 }

pktSwchHdlcDestDlciS  OBJECT-TYPE
    SYNTAX Integer32
    MAX-ACCESS  read-write
    STATUS  current
    DESCRIPTION
	"The local DLCI which is used for HDLC encapsulation over Frame Relay.
	 Range: 16...991"
    ::= { pktSwchHdlcSEntry 10 }

pktSwchHdlcDestPortS  OBJECT-TYPE
    SYNTAX Integer32
    MAX-ACCESS  read-write
    STATUS  current
    DESCRIPTION
	"The local port that is used for HDLC encapsulation over Frame Relay.
	 Range: 1...12"
    ::= { pktSwchHdlcSEntry 11 }

pktSwchHdlcProtocolS  OBJECT-TYPE
    SYNTAX INTEGER {
       hdlcOverX25(1),   -- HDLC encapsulated over X.25
       hdlcOverFrRel(2),  -- HDLC encapsulated over Frame Relay
	   hdlcOverMpe(3),   -- HDLC encapsulated over MPE
       hdlcReg(4),  -- HDLC regular protocol for inner routing
	   hdlcOverIp(5)     -- HDLC encapsulated over IP
     }
    MAX-ACCESS  read-write
    STATUS  current
    DESCRIPTION
	"The HDLC protocol type."
    ::= { pktSwchHdlcSEntry 12 }

pktSwchHdlcFlowContOptionsS  OBJECT-TYPE
    SYNTAX Integer32 (0..3)
    MAX-ACCESS  read-write
    STATUS  current
    DESCRIPTION
	"This specifies the type of flow control of the HDLC link.  The value
	 is a sum of values (powers of two), where each value in the sum
	 represents an option.  The values that may be included in the sum and
	 their meanings are:
		0 No flow control
		1 CTS flow control
		2 Clock flow control."
    ::= { pktSwchHdlcSEntry 13 }

pktSwchHdlcBufferFlowControlS  OBJECT-TYPE
    SYNTAX Integer32 (1..200)
    MAX-ACCESS  read-write
    STATUS  current
    DESCRIPTION
	"The number of buffers that will be allocated for the HDLC link. Default value is 10"
    ::= { pktSwchHdlcSEntry 14 }

pktSwchHdlcInternalClockS  OBJECT-TYPE
    SYNTAX INTEGER {
       r2400bps (1),
       r4800bps (2),
       r9600bps (3),
       r14400bps(4),
       r19200bps(5),
       r38400bps(6),
	   r48Kbps  (7),
       r56Kbps  (8),
       r64Kbps  (9),
       r128Kbps (10),
       r256Kbps (11),
	   r384Kbps (12),
       r504Kbps (13),
	   r768Kbps (14),
	   r1008Kbps(15),
       r1466Kbps(16),
       r2016Kbps(17),
       external(255)
     }
    MAX-ACCESS  read-write
    STATUS  current
    DESCRIPTION
	"The baud rate of the internal clock."
    ::= { pktSwchHdlcSEntry 15 }

pktSwchHdlcNrzModeS  OBJECT-TYPE
    SYNTAX Integer32 (0..7)
    MAX-ACCESS  read-write
    STATUS  current
    DESCRIPTION
	"The data encoding format.
     The value is a sum of values (powers of two), where each
     value in the sum represents an option.
     The values that may be included in the sum and their
     meanings are:
		0   NRZ
		1   NRZI
		2   Transmit Idles between frames and control the RTS pin
		4   Normal Operation (DCD, CTS lines under automatic control)
		XX  Any combination of the values specified above."
    ::= { pktSwchHdlcSEntry 16 }


pktSwchHdlcATable  OBJECT-TYPE
    SYNTAX  SEQUENCE  OF PktSwchHdlcAEntry
    MAX-ACCESS  not-accessible
    STATUS  current
    DESCRIPTION
	"The Active Hdlc Table contains active configuration information for HDLC links"
    ::=  { pktSwchHdlc 2 }

pktSwchHdlcAEntry OBJECT-TYPE
    SYNTAX  PktSwchHdlcAEntry
    MAX-ACCESS  not-accessible
    STATUS  current
    DESCRIPTION
	"Defines the contents of each line in the RAD Hdlc Table."
    INDEX   { pktSwchHdlcLinkNumberA }
    ::=  { pktSwchHdlcATable 1  }

PktSwchHdlcAEntry ::= SEQUENCE {
    pktSwchHdlcLinkNumberA
     Integer32,
    pktSwchHdlcDestAddrA
     DisplayString,
    pktSwchHdlcDestSubAddrA
     Integer32,
    pktSwchHdlcRedialTimeoutA
     Integer32,
    pktSwchHdlcRedialRetriesA
     Integer32,
    pktSwchHdlcInactivityA
     Integer32,
    pktSwchHdlcX25FacilitiesA
     Integer32,
    pktSwchHdlcLocalSubaddr1A
     Integer32,
    pktSwchHdlcLocalSubaddr2A
     Integer32,
    pktSwchHdlcDestDlciA
     Integer32,
    pktSwchHdlcDestPortA
     Integer32,
    pktSwchHdlcProtocolA
     INTEGER,
    pktSwchHdlcFlowContOptionsA
     Integer32,
    pktSwchHdlcBufferFlowControlA
     Integer32,
    pktSwchHdlcInternalClockA
     INTEGER,
    pktSwchHdlcNrzModeA
     Integer32,
	pktSwchHdlcConnStatus
	 INTEGER,
	pktSwchHdlcSpecialStatus
	 INTEGER,
    pktSwchHdlcCtsStatus
	 INTEGER,
	pktSwchHdlcRunningX25Lcn
	 DisplayString,
	pktSwchHdlcRunningDlci
	 DisplayString,
	pktSwchHdlcMaxBuffToNet
	 Integer32,
	pktSwchHdlcBuffToNet
	 Integer32
    }

pktSwchHdlcLinkNumberA  OBJECT-TYPE
    SYNTAX Integer32
    MAX-ACCESS  read-only
    STATUS  current
    DESCRIPTION
	"The link number with which this entry is associated.  This value corresponds to
		 pktSwchPhyInterfaceNumber.  There is an entry for each link for which the pktSwchPhyInterfaceProtocol is
		 HDLC."
    ::= { pktSwchHdlcAEntry 1 }

pktSwchHdlcDestAddrA  OBJECT-TYPE
    SYNTAX DisplayString
    MAX-ACCESS  read-only
    STATUS  current
    DESCRIPTION
	"The destination address.  It defines the X.25 address on the remote device."
    ::= { pktSwchHdlcAEntry 2 }

pktSwchHdlcDestSubAddrA  OBJECT-TYPE
    SYNTAX Integer32 (0..99)
    MAX-ACCESS  read-only
    STATUS  current
    DESCRIPTION
	"The destination subaddress.  It defines the synchronous link subaddress on the remote
		 device."
    ::= { pktSwchHdlcAEntry 3 }

pktSwchHdlcRedialTimeoutA  OBJECT-TYPE
    SYNTAX Integer32 (0..255)   -- seconds??
    MAX-ACCESS  read-only
    STATUS  current
    DESCRIPTION
	"The time interval in seconds between two consecutive connect operations retries."
    ::= { pktSwchHdlcAEntry 4 }

pktSwchHdlcRedialRetriesA  OBJECT-TYPE
    SYNTAX Integer32 (0..255)
    MAX-ACCESS  read-only
    STATUS  current
    DESCRIPTION
	"This defines how many times the call operation is repeated if the call request has failed."
    ::= { pktSwchHdlcAEntry 5 }

pktSwchHdlcInactivityA  OBJECT-TYPE
    SYNTAX Integer32 (0..255)
    MAX-ACCESS  read-only
    STATUS  current
    DESCRIPTION
	"The amount of time in minutes of inactivity that will cause the
	 session to disconnect."
    ::= { pktSwchHdlcAEntry 6 }

pktSwchHdlcX25FacilitiesA  OBJECT-TYPE
    SYNTAX Integer32 (0..7)
    MAX-ACCESS  read-only
    STATUS  current
    DESCRIPTION
	"This specifies the X.25 facilities.  The value is a sum of values (powers of two), where each
		 value in the sum represents an option.  The values that may be included in the sum and
		 their meanings are:
		0 No options
		1 Packet size negotiation
		2 Window size negotiation
		4 Reverse  charge."
    ::= { pktSwchHdlcAEntry 7 }

pktSwchHdlcLocalSubaddr1A  OBJECT-TYPE
    SYNTAX Integer32 (0..99)
    MAX-ACCESS  read-only
    STATUS  current
    DESCRIPTION
	"The first local subaddress."
    ::= { pktSwchHdlcAEntry 8 }

pktSwchHdlcLocalSubaddr2A  OBJECT-TYPE
    SYNTAX Integer32 (0..99)
    MAX-ACCESS  read-only
    STATUS  current
    DESCRIPTION
	"The secondary local subaddress."
    ::= { pktSwchHdlcAEntry 9 }

pktSwchHdlcDestDlciA  OBJECT-TYPE
    SYNTAX Integer32
    MAX-ACCESS  read-only
    STATUS  current
    DESCRIPTION
	"The local DLCI which is used for HDLC encapsulation over Frame Relay."
    ::= { pktSwchHdlcAEntry 10 }

pktSwchHdlcDestPortA  OBJECT-TYPE
    SYNTAX Integer32
    MAX-ACCESS  read-only
    STATUS  current
    DESCRIPTION
	"The local port that is used for HDCL encapsulation over Frame Relay."
    ::= { pktSwchHdlcAEntry 11 }

pktSwchHdlcProtocolA  OBJECT-TYPE
    SYNTAX INTEGER {
       hdlcOverX25(1),   -- HDLC encapsulated over X.25
       hdlcOverFrRel(2),  -- HDLC encapsulated over Frame Relay
	   hdlcOverMpe(3),   -- HDLC encapsulated over MPE
       hdlcReg(4),  -- HDLC regular protocol for inner routing
           hdlcOverIp(5)     -- It is actually IP over HDLC
     }
    MAX-ACCESS  read-only
    STATUS  current
    DESCRIPTION
	"The HDLC protocol type."
    ::= { pktSwchHdlcAEntry 12 }

pktSwchHdlcFlowContOptionsA  OBJECT-TYPE
    SYNTAX Integer32 (0..3)
    MAX-ACCESS  read-only
    STATUS  current
    DESCRIPTION
	"This specifies the type of flow control of the HDLC link.  The value is a sum of values
		 (powers of two), where each value in the sum represents an option.  The values that may
		 be included in the sum and their meanings are:
		0 No flow control
		1 CTS flow control
		2 Clock flow control."
    ::= { pktSwchHdlcAEntry 13 }

pktSwchHdlcBufferFlowControlA  OBJECT-TYPE
    SYNTAX Integer32 (1..200)
    MAX-ACCESS  read-only
    STATUS  current
    DESCRIPTION
	"The number of buffers that will be allocated for the HDLC link."
    ::= { pktSwchHdlcAEntry 14 }

pktSwchHdlcInternalClockA  OBJECT-TYPE
    SYNTAX INTEGER {
       r2400bps (1),
       r4800bps (2),
       r9600bps (3),
       r14400bps(4),
       r19200bps(5),
       r38400bps(6),
	   r48Kbps  (7),
       r56Kbps  (8),
       r64Kbps  (9),
       r128Kbps (10),
       r256Kbps (11),
	   r384Kbps (12),
       r504Kbps (13),
	   r768Kbps (14),
	   r1008Kbps(15),
       r1466Kbps(16),
       r2016Kbps(17),
       external(255)
      }
    MAX-ACCESS  read-only
    STATUS  current
    DESCRIPTION
	"The baud rate of the internal clock."
    ::= { pktSwchHdlcAEntry 15 }

pktSwchHdlcNrzModeA  OBJECT-TYPE
    SYNTAX Integer32 (0..7)
    MAX-ACCESS  read-only
    STATUS  current
    DESCRIPTION
	"The data encoding format.
     The value is a sum of values (powers of two), where each
     value in the sum represents an option.
     The values that may be included in the sum and their
     meanings are:
		0   NRZ
		1   NRZI
		2   Transmit Idles between frames and control the RTS pin
		4   Normal Operation (DCD, CTS lines under automatic control)
		XX  Any combination of the values specified above."
    ::= { pktSwchHdlcAEntry 16 }

pktSwchHdlcConnStatus  OBJECT-TYPE
    SYNTAX INTEGER {
	                disconnect(1),
					connect(2),
					pvc(3)
				   }
    MAX-ACCESS  read-only
    STATUS  current
    DESCRIPTION
	"The status of the Hdlc session."
    ::= { pktSwchHdlcAEntry 17 }

pktSwchHdlcSpecialStatus  OBJECT-TYPE
    SYNTAX INTEGER {
	                busy(1),
					overflow(2),
					noStatus(255)
				   }
    MAX-ACCESS  read-only
    STATUS  current
    DESCRIPTION
	"The status of the Hdlc link."
    ::= { pktSwchHdlcAEntry 18 }

pktSwchHdlcCtsStatus  OBJECT-TYPE
    SYNTAX INTEGER {
                    off(2),
                    on(3)
                   }
    MAX-ACCESS  read-only
    STATUS  current
    DESCRIPTION
	"The CTS status."
    ::= { pktSwchHdlcAEntry 19 }

pktSwchHdlcRunningX25Lcn  OBJECT-TYPE
    SYNTAX DisplayString
    MAX-ACCESS  read-only
    STATUS  current
    DESCRIPTION
	"The format of the string is ifIndex:LCN "
    ::= { pktSwchHdlcAEntry 20 }

pktSwchHdlcRunningDlci  OBJECT-TYPE
    SYNTAX DisplayString
    MAX-ACCESS  read-only
    STATUS  current
    DESCRIPTION
	"The format of the string is ifIndex:DLCI"
    ::= { pktSwchHdlcAEntry 21 }

pktSwchHdlcMaxBuffToNet  OBJECT-TYPE
    SYNTAX Integer32
    MAX-ACCESS  read-only
    STATUS  current
    DESCRIPTION
	"The maximum number of buffers above which Flow Control is enabled"
    ::= { pktSwchHdlcAEntry 22 }

pktSwchHdlcBuffToNet  OBJECT-TYPE
    SYNTAX Integer32
    MAX-ACCESS  read-only
    STATUS  current
    DESCRIPTION
	"The number of buffers waiting for transmission."
    ::= { pktSwchHdlcAEntry 23 }

pktSwchStmTable  OBJECT-TYPE
    SYNTAX  SEQUENCE  OF PktSwchStmEntry
    MAX-ACCESS  not-accessible
    STATUS  current
    DESCRIPTION
	"The STM table contains information for STM links"
    ::=  { radPS 7 }

pktSwchStmEntry OBJECT-TYPE
    SYNTAX  PktSwchStmEntry
    MAX-ACCESS  not-accessible
    STATUS  current
    DESCRIPTION
	"Defines the contents of each line in the RAD STM Table."
    INDEX   { pktSwchStmLinkNumber }
    ::=  { pktSwchStmTable 1  }

PktSwchStmEntry ::= SEQUENCE {
    pktSwchStmLinkNumber
     Integer32,
    pktSwchStmInternalClockS
     INTEGER,
    pktSwchStmInternalClockA
     INTEGER,
	pktSwchStmConn
	 INTEGER,
	pktSwchStmSyncLoss
	 Counter32
    }

pktSwchStmLinkNumber  OBJECT-TYPE
    SYNTAX Integer32
    MAX-ACCESS  read-only
    STATUS  current
    DESCRIPTION
	"The link number with which this entry is associated.  This value
	 corresponds to pktSwchPhyInterfaceNumber.  There is an entry for
	 each link whose pktSwchPhyInterfaceProtocol is STM 4, 8, 16, or 24."
    ::= { pktSwchStmEntry 1 }

pktSwchStmInternalClockS  OBJECT-TYPE
    SYNTAX INTEGER {
       r2400bps (1),
       r4800bps (2),
       r9600bps (3),
       r14400bps(4),
       r19200bps(5),
       r38400bps(6),
	   r48Kbps  (7),
       r56Kbps  (8),
       r64Kbps  (9),
       r128Kbps (10),
       r256Kbps (11),
	   r384Kbps (12),
       r504Kbps (13),
	   r768Kbps (14),
	   r1008Kbps(15),
       r1466Kbps(16),
       r2016Kbps(17),
       external(255)
       }
    MAX-ACCESS  read-write
    STATUS  current
    DESCRIPTION
	"The baud rate of the internal clock."
    ::= { pktSwchStmEntry 2 }

pktSwchStmInternalClockA  OBJECT-TYPE
    SYNTAX INTEGER {
       r2400bps (1),
       r4800bps (2),
       r9600bps (3),
       r14400bps(4),
       r19200bps(5),
       r38400bps(6),
	   r48Kbps  (7),
       r56Kbps  (8),
       r64Kbps  (9),
       r128Kbps (10),
       r256Kbps (11),
	   r384Kbps (12),
       r504Kbps (13),
	   r768Kbps (14),
	   r1008Kbps(15),
       r1466Kbps(16),
       r2016Kbps(17),
       external(255)
      }
    MAX-ACCESS  read-only
    STATUS  current
    DESCRIPTION
	"The current baud rate of the internal clock."
    ::= { pktSwchStmEntry 3 }

pktSwchStmConn OBJECT-TYPE
    SYNTAX   INTEGER {
                    disconnect(1),
					connect(2)
					}
    MAX-ACCESS   read-only
    STATUS   current
    DESCRIPTION
       "The connectivity status of the STM interface."
   ::= { pktSwchStmEntry 4 }

pktSwchStmSyncLoss OBJECT-TYPE
    SYNTAX   Counter32
    MAX-ACCESS   read-only
    STATUS   current
    DESCRIPTION
       "The counter for sync loss."
   ::= { pktSwchStmEntry 5 }

-- The PS Frame Relay Group

pktSwchFr  OBJECT IDENTIFIER ::= { radPS 8 }

pktSwchFrTotFunnels OBJECT-TYPE
    SYNTAX Integer32
    MAX-ACCESS  read-only
    STATUS  current
    DESCRIPTION
	"The total number of Funnels on the PS."
    ::= { pktSwchFr 1 }

pktSwchFrSTable  OBJECT-TYPE
   SYNTAX  SEQUENCE  OF PktSwchFrSEntry
   MAX-ACCESS  not-accessible
   STATUS  current
   DESCRIPTION
      "The Frame Relay Scratch Table includes the scratch values of
       configurable objects provided by the PS that are not included
       in RFC 1315."
   ::=  { pktSwchFr 2 }

 pktSwchFrSEntry OBJECT-TYPE
    SYNTAX  PktSwchFrSEntry
    MAX-ACCESS  not-accessible
    STATUS  current
    DESCRIPTION
	"Defines the contents of each line in the RAD PS Frame Relay
	 Scratch Table."
    INDEX   { pktSwchFrIfIndexS }
    ::=  { pktSwchFrSTable 1  }

 PktSwchFrSEntry ::= SEQUENCE {
    pktSwchFrIfIndexS
     Integer32,
    pktSwchFrMaintProtS
     Integer32,
    pktSwchFrMaintModeS
     INTEGER,
    pktSwchFrRxPoolRedLineS
     Integer32,
    pktSwchFrRxPoolOkS
     Integer32,
    pktSwchFrTxPoolRedLineS
     Integer32,
    pktSwchFrTxPoolOkS
     Integer32,
    pktSwchFrTxCeilingS
     Integer32,
    pktSwchFrInternalClockS
     INTEGER,
    pktSwchFrNrzModeS
     INTEGER,
    pktSwchFrDlciHeaderModeS
     INTEGER,
    pktSwchFrDcdLinkFailureS
     INTEGER,
    pktSwchFrTxIdlesS
     INTEGER,
    pktSwchFrOperationModeS
     INTEGER,
    pktSwchFrPhysInterfOptionsS
     INTEGER
       }


pktSwchFrIfIndexS OBJECT-TYPE
    SYNTAX   Integer32
    MAX-ACCESS   read-only
    STATUS   current
    DESCRIPTION
       "This is the ifIndex of the frame relay port."
   ::= { pktSwchFrSEntry 1 }

pktSwchFrMaintProtS OBJECT-TYPE
    SYNTAX   Integer32 (0..12)
    MAX-ACCESS   read-write
    STATUS   current
    DESCRIPTION
       "This defines what maintenance protocol is running over this port.
        0 - No maintenance protocol.
        1 - ANSI PVC maintenance protocol running on DLCI number 0.
        2 - LMI maintenance protocol running on DLCI number 1023.
        4 - ITU Q.933 ANNEX A maintenance protocol running on DLCI number 0.
        8 - Consolidate Link Layer Management CLLM running on DLCI number 1023.
		    8 cannot be a choice by itself, it can only be as part of the
			combination 9, 10, 12.
        XXX - The combination of 9, 10, 12."
   ::= { pktSwchFrSEntry 2 }

pktSwchFrMaintModeS OBJECT-TYPE
    SYNTAX   INTEGER {
	user(1),
	network(2),
	both(3)}
    MAX-ACCESS   read-write
    STATUS   current
    DESCRIPTION
       "This defines the mode of maintenance protocol running over this port."
   ::= { pktSwchFrSEntry 3 }

pktSwchFrRxPoolRedLineS OBJECT-TYPE
    SYNTAX   Integer32 (0..39)
    MAX-ACCESS   read-write
    STATUS   current
    DESCRIPTION
       "When the number of empty receive buffers at the port reaches this
        figure (of frames),the port receiver is congested.  This field
        value should be less than the Rx pool OK field."
   ::= { pktSwchFrSEntry 4 }

pktSwchFrRxPoolOkS OBJECT-TYPE
    SYNTAX   Integer32 (1..40)
    MAX-ACCESS   read-write
    STATUS   current
    DESCRIPTION
       "Clear the receive congestion condition when the number of empty
        receive buffers at the port reaches this figure.  This value
        (of frames) should be greater than the Rx pool red line."
   ::= { pktSwchFrSEntry 5 }

pktSwchFrTxPoolRedLineS OBJECT-TYPE
    SYNTAX   Integer32 (1..500)
    MAX-ACCESS   read-write
    STATUS   current
    DESCRIPTION
       "When the number of frames awaiting transmission reaches this figure,
        the port transmitter is congested.  This field value should be
        greater than the Tx pool OK field."
   ::= { pktSwchFrSEntry 6 }

pktSwchFrTxPoolOkS OBJECT-TYPE
    SYNTAX   Integer32 (0..499)
    MAX-ACCESS   read-write
    STATUS   current
    DESCRIPTION
       "Clear the transmit congestion condition when the number of frames
        awaiting transmission at the port reaches this figure.  This value
        (of frames) should be less than the Tx pool red line."
   ::= { pktSwchFrSEntry 7 }

pktSwchFrTxCeilingS OBJECT-TYPE
    SYNTAX   Integer32 (1..500)
    MAX-ACCESS   read-write
    STATUS   current
    DESCRIPTION
       "The maximum allowable transmit pool for this port."
   ::= { pktSwchFrSEntry 8 }

pktSwchFrInternalClockS  OBJECT-TYPE
    SYNTAX INTEGER {
       r2400bps (1),
       r4800bps (2),
       r9600bps (3),
       r14400bps(4),
       r19200bps(5),
       r38400bps(6),
	   r48Kbps  (7),
       r56Kbps  (8),
       r64Kbps  (9),
       r128Kbps (10),
       r256Kbps (11),
	   r384Kbps (12),
       r504Kbps (13),
	   r768Kbps (14),
	   r1008Kbps(15),
       r1466Kbps(16),
       r2016Kbps(17),
       external (255)
     }
    MAX-ACCESS  read-write
    STATUS  current
    DESCRIPTION
	"The baud rate of the internal clock."
    ::= { pktSwchFrSEntry 9 }

pktSwchFrNrzModeS  OBJECT-TYPE
    SYNTAX INTEGER {
       nrz(1),
       nrzi(2)
     }
    MAX-ACCESS  read-write
    STATUS  current
    DESCRIPTION
	"The data encoding format."
    ::= { pktSwchFrSEntry 10 }

pktSwchFrDlciHeaderModeS  OBJECT-TYPE
    SYNTAX INTEGER {
       two-octets(1),
       three-octets(2),
       four-octets(3),
       four-octets-nomanag(4)
     }
    MAX-ACCESS  read-write
    STATUS  current
    DESCRIPTION
        "Dlci Header length for this FR port. Option 4 means that there
         will be no management Dlci in the range of 1024 to 8388607.
         The management Dlci will be in the range of 0-15 or 991-1023.
         Default value: 1."
         ::= { pktSwchFrSEntry 11 }

pktSwchFrDcdLinkFailureS  OBJECT-TYPE
    SYNTAX INTEGER {
       no-Detect(2),
       linkFailure-Detect(3)
     }
    MAX-ACCESS  read-write
    STATUS  current
    DESCRIPTION
        "Link Failure Detection by DCD.
         If Link Failure detection by DCD is on - (3), when the DCD is
         down, the FR SW will detect it and change the FR link status
         from UP to DOWN. A trap of LINK DOWN will be sent to the NMS.
         Default: (2)."
         ::= { pktSwchFrSEntry 12 }


pktSwchFrTxIdlesS  OBJECT-TYPE
    SYNTAX INTEGER {
       no(2),
       yes(3)
     }
    MAX-ACCESS  read-write
    STATUS  current
    DESCRIPTION
        "This parameter shows whether the PS will Transmit Idles between
         frames and control the RTS pin.
         Default: no(2)."
        ::= { pktSwchFrSEntry 13 }

pktSwchFrOperationModeS  OBJECT-TYPE
    SYNTAX INTEGER {
       swControl(2),
       hwControl(3)
     }
    MAX-ACCESS  read-write
    STATUS  current
    DESCRIPTION
        "When H/W Control is configured, the SCC H/W will detect the change in the
		 DCD or CTS signals and Start or Stop transmission automatically.
		 When S/W Control is configured the S/W will decide when to start or stop
		 the transmission.
         Default: swControl(2)."
         ::= { pktSwchFrSEntry 14 }

pktSwchFrPhysInterfOptionsS  OBJECT-TYPE
    SYNTAX INTEGER {
       noOption(2),
       dds4800bps(3),
	   dds9600bps(4),
	   dds19200bps(5),
	   dds56000bos(6)
     }
    MAX-ACCESS  read-write
    STATUS  current
    DESCRIPTION
        "This is the physical interface.
		 Note that the DDS physical interface H/W does not exist in the FPS-8.
		 It is relevant for other PS devices only.
		 For FPS-8 only the default (noOption) should be used.
		 Default: (2)."
         ::= { pktSwchFrSEntry 15 }


 pktSwchFrATable  OBJECT-TYPE
    SYNTAX  SEQUENCE  OF PktSwchFrAEntry
    MAX-ACCESS  not-accessible
    STATUS  current
    DESCRIPTION
	"The Frame Relay Active Table includes statistics and the active values of configurable
                objects provided by the PS that are not included in RFC 1315."
    ::=  { pktSwchFr 3 }

 pktSwchFrAEntry OBJECT-TYPE
    SYNTAX  PktSwchFrAEntry
    MAX-ACCESS  not-accessible
    STATUS  current
    DESCRIPTION
	"Defines the contents of each line in the RAD PS Frame Relay Active Table."
    INDEX   { pktSwchFrIfIndexA }
    ::=  { pktSwchFrATable 1  }

PktSwchFrAEntry ::= SEQUENCE {
    pktSwchFrIfIndexA
     Integer32,
    pktSwchFrMaintProtA
     Integer32,
    pktSwchFrMaintModeA
     INTEGER,
    pktSwchFrRxPoolRedLineA
     Integer32,
    pktSwchFrRxPoolOkA
     Integer32,
    pktSwchFrTxPoolRedLineA
     Integer32,
    pktSwchFrTxPoolOkA
     Integer32,
    pktSwchFrTxCeilingA
     Integer32,
    pktSwchFrInternalClockA
     INTEGER,
    pktSwchFrNrzModeA
     INTEGER,
    pktSwchFrDlcmiPollingInterval
     Integer32,
    pktSwchFrDlcmiFullEnquiryInterval
     Integer32,
    pktSwchFrDlcmiErrorThreshold
     Integer32,
    pktSwchFrDlcmiMonitoredEvents
     Integer32,
    pktSwchFrDlciHeaderModeA
     INTEGER,
    pktSwchFrDcdLinkFailureA
     INTEGER,
    pktSwchFrTxIdlesA
     INTEGER,
    pktSwchFrOperationModeA
     INTEGER,
    pktSwchFrPhysInterfOptionsA
     INTEGER
    }


pktSwchFrIfIndexA OBJECT-TYPE
    SYNTAX   Integer32
    MAX-ACCESS   read-only
    STATUS   current
    DESCRIPTION
       "This is the ifIndex of the frame relay port."
   ::= { pktSwchFrAEntry 1 }

pktSwchFrMaintProtA OBJECT-TYPE
    SYNTAX   Integer32 (0..12)
    MAX-ACCESS   read-only
    STATUS   current
    DESCRIPTION
       "This defines what maintenance protocol is running over this port.
        0 - No maintenance protocol.
        1 - ANSI PVC maintenance protocol running on DLCI number 0.
        2 - LMI maintenance protocol running on DLCI number 1023.
        4 - ITU Q.933 ANNEX A maintenance protocol running on DLCI number 0.
        8 - Consolidate Link Layer Management CLLM running on DLCI number 1023.
		    8 cannot be a choice by itself, it can only be as part of the
			combination 9, 10, 12.
        XXX - The combination of 9, 10, 12."
   ::= { pktSwchFrAEntry 2 }

pktSwchFrMaintModeA OBJECT-TYPE
    SYNTAX   INTEGER {
	user(1),
	network(2),
	both(3)}
    MAX-ACCESS   read-only
    STATUS   current
    DESCRIPTION
       "This defines the mode of maintenance protocol running over this port."
   ::= { pktSwchFrAEntry 3 }

pktSwchFrRxPoolRedLineA OBJECT-TYPE
    SYNTAX   Integer32 (0..39)
    MAX-ACCESS   read-only
    STATUS   current
    DESCRIPTION
       "When the number of empty receive buffers at the port reaches this figure (of frames),
        the port receiver is congested.  This field value should be less than the Rx pool OK field."
   ::= { pktSwchFrAEntry 4 }

pktSwchFrRxPoolOkA OBJECT-TYPE
    SYNTAX   Integer32 (1..40)
    MAX-ACCESS   read-only
    STATUS   current
    DESCRIPTION
       "Clear the receive congestion condition when the number of empty receive buffers at the port
        reaches this figure.  This value (of frames) should be greater than the Rx pool red line."
   ::= { pktSwchFrAEntry 5 }

pktSwchFrTxPoolRedLineA OBJECT-TYPE
    SYNTAX   Integer32 (1..500)
    MAX-ACCESS   read-only
    STATUS   current
    DESCRIPTION
       "When the number of frames awaiting transmission reaches this figure,
        the port transmitter is congested.  This field value should be greater than the Tx pool OK field."
   ::= { pktSwchFrAEntry 6 }

pktSwchFrTxPoolOkA OBJECT-TYPE
    SYNTAX   Integer32 (0..499)
    MAX-ACCESS   read-only
    STATUS   current
    DESCRIPTION
       "Clear the transmit congestion condition when the number of frames awaiting transmission
        at the port reaches this figure.  This value (of frames) should be less than the Tx pool red line."
   ::= { pktSwchFrAEntry 7 }

pktSwchFrTxCeilingA OBJECT-TYPE
    SYNTAX   Integer32 (0..500)
    MAX-ACCESS   read-only
    STATUS   current
    DESCRIPTION
       "The maximum allowable transmit pool for this port."
   ::= { pktSwchFrAEntry 8 }

pktSwchFrInternalClockA  OBJECT-TYPE
    SYNTAX INTEGER {
       r2400bps (1),
       r4800bps (2),
       r9600bps (3),
       r14400bps(4),
       r19200bps(5),
       r38400bps(6),
	   r48Kbps  (7),
       r56Kbps  (8),
       r64Kbps  (9),
       r128Kbps (10),
       r256Kbps (11),
	   r384Kbps (12),
       r504Kbps (13),
	   r768Kbps (14),
	   r1008Kbps(15),
       r1466Kbps(16),
       r2016Kbps(17),
       external (255)
     }
    MAX-ACCESS  read-only
    STATUS  current
    DESCRIPTION
	"The baud rate of the internal clock."
    ::= { pktSwchFrAEntry 9 }

pktSwchFrNrzModeA  OBJECT-TYPE
    SYNTAX INTEGER {
       nrz(1),
       nrzi(2)
     }
    MAX-ACCESS  read-only
    STATUS  current
    DESCRIPTION
	"The data encoding format."
    ::= { pktSwchFrAEntry 10 }

pktSwchFrDlcmiPollingInterval OBJECT-TYPE
             SYNTAX   Integer32 (5..30)
             MAX-ACCESS   read-only
             STATUS   current
             DESCRIPTION
                "This is the number of seconds between succes-
                sive status enquiry messages."
            REFERENCE
               "Draft American National  Standard  T1.617-1991,
               Section D.7 Timer T391."
           DEFVAL { 10 }
    ::= { pktSwchFrAEntry 11 }

pktSwchFrDlcmiFullEnquiryInterval OBJECT-TYPE
             SYNTAX   Integer32 (1..255)
             MAX-ACCESS   read-only
             STATUS   current
             DESCRIPTION
                "Number of status enquiry intervals  that  pass
                before  issuance  of a full status enquiry mes-
                sage."
            REFERENCE
               "Draft American National  Standard  T1.617-1991,
               Section D.7 Counter32 N391."
           DEFVAL { 6 }
    ::= { pktSwchFrAEntry 12 }

pktSwchFrDlcmiErrorThreshold OBJECT-TYPE
             SYNTAX   Integer32 (1..10)
             MAX-ACCESS   read-only
             STATUS   current
             DESCRIPTION
                "This  is  the  maximum  number  of  unanswered
                Status Enquiries the equipment shall accept be-
                fore declaring the interface down."
            REFERENCE
               "Draft American National  Standard  T1.617-1991,
               Section D.5.1 Counter32 N392."
           DEFVAL { 3 }
    ::= { pktSwchFrAEntry 13 }

pktSwchFrDlcmiMonitoredEvents OBJECT-TYPE
             SYNTAX   Integer32 (1..10)
             MAX-ACCESS   read-only
             STATUS   current
             DESCRIPTION
                "This is the number of status polling intervals
                over which the error threshold is counted.  For
                example, if within 'MonitoredEvents' number  of
                events  the  station  receives 'ErrorThreshold'
                number of errors, the interface  is  marked  as
                down."
            REFERENCE
               "Draft American National  Standard  T1.617-1991,
               Section D.5.2 Counter32 N393."
           DEFVAL { 4 }
    ::= { pktSwchFrAEntry 14 }

pktSwchFrDlciHeaderModeA  OBJECT-TYPE
    SYNTAX INTEGER {
       two-octets(1),
       three-octets(2),
       four-octets(3),
       four-octets-nomanag(4)
     }
    MAX-ACCESS  read-only
    STATUS  current
    DESCRIPTION
        "Dlci Header length for this FR port. Option 4 means that there
         will be no management Dlci in the range of 1024 to 8388607.
         The management Dlci will be in the range of 0-15 or 991-1023.
         Default value: 1."
    ::= { pktSwchFrAEntry 15 }

pktSwchFrDcdLinkFailureA  OBJECT-TYPE
    SYNTAX INTEGER {
       no-Detect(2),
       linkFailure-Detect(3)
     }
    MAX-ACCESS  read-only
    STATUS  current
    DESCRIPTION
        "Link Failure Detection by DCD.
         If Link Failure detection by DCD is on - (3), when the DCD is
         down, the FR SW will detect it and change the FR link status
         from UP to DOWN. A trap of LINK DOWN will be sent to the NMS.
         Default: (2)."
         ::= { pktSwchFrAEntry 16 }

pktSwchFrTxIdlesA  OBJECT-TYPE
    SYNTAX INTEGER {
       no(2),
       yes(3)
     }
    MAX-ACCESS  read-only
    STATUS  current
    DESCRIPTION
        "This parameter shows whether the PS will Transmit Idles between
         frames and control the RTS pin.
         Default: no(2)."
        ::= { pktSwchFrAEntry 17 }

pktSwchFrOperationModeA  OBJECT-TYPE
    SYNTAX INTEGER {
       swControl(2),
       hwControl(3)
     }
    MAX-ACCESS  read-only
    STATUS  current
    DESCRIPTION
        "When H/W Control is configured, the SCC H/W will detect the change in the
		 DCD or CTS signals and Start or Stop transmission automatically.
		 When S/W Control is configured the S/W will decide when to start or stop
		 the transmission.
         Default: swControl(2)."
         ::= { pktSwchFrAEntry 18 }

pktSwchFrPhysInterfOptionsA  OBJECT-TYPE
    SYNTAX INTEGER {
       noOption(2),
       dds4800bps(3),
	   dds9600bps(4),
	   dds19200bps(5),
	   dds56000bos(6)
     }
    MAX-ACCESS  read-only
    STATUS  current
    DESCRIPTION
        "This is the physical interface.
		 Note that the DDS physical interface H/W does not exist in the FPS-8.
		 It is relevant for other PS devices only.
		 For FPS-8 only the default (noOption) should be used.
		 Default: (2)."
         ::= { pktSwchFrAEntry 19 }


pktSwchFrIfTable  OBJECT-TYPE
    SYNTAX  SEQUENCE  OF PktSwchFrIfEntry
    MAX-ACCESS  not-accessible
    STATUS  current
    DESCRIPTION
	"The Frame Relay Active Port Table includes statistics and configurable objects
                 provided by the PS  that are not included in RFC 1315."
    ::=  { pktSwchFr 4 }

pktSwchFrIfEntry OBJECT-TYPE
    SYNTAX  PktSwchFrIfEntry
    MAX-ACCESS  not-accessible
    STATUS  current
    DESCRIPTION
	"Defines the contents of each line in the RAD PS Frame Relay Port Active Table."
    INDEX   { ifIndex }
    ::=  { pktSwchFrIfTable 1  }

PktSwchFrIfEntry ::= SEQUENCE {
	pktSwchFrIfTxBytes
     Counter32,
    pktSwchFrIfRxBytes
     Counter32,
    pktSwchFrIfTxCongDiscards
     Counter32,
    pktSwchFrIfDeTxFrames
     Counter32,
    pktSwchFrIfDeRxFrames
     Counter32,
    pktSwchFrIfFecnTxFrames
     Counter32,
	pktSwchFrIfFecnRxFrames
     Counter32,
    pktSwchFrIfBecnTxFrames
     Counter32,
	pktSwchFrIfBecnRxFrames
     Counter32,
    pktSwchFrIfCommRateViolTxFrames
     Counter32,
    pktSwchFrIfCommRateViolRxFrames
     Counter32,
    pktSwchFrIfExcessRateViolTxFrames
     Counter32,
    pktSwchFrIfExcessRateViolRxFrames
     Counter32,
    pktSwchFrIfBuffersInTxPool
     Integer32,
    pktSwchFrIfFreeBuffersInRxPool
     Integer32,
    pktSwchFrIfLmiTxFrames
     Counter32,
    pktSwchFrIfLmiRxFrames
     Counter32,
    pktSwchFrIfAnsiTxFrames
     Counter32,
    pktSwchFrIfAnsiRxFrames
     Counter32,
    pktSwchFrIfCllmTxFrames
     Counter32,
    pktSwchFrIfCllmRxFrames
     Counter32,
    pktSwchFrIfTxCongestions
     Counter32,
    pktSwchFrIfRxCongestions
     Counter32,
    pktSwchFrIfTotDlciNumber
	 Integer32
     }

pktSwchFrIfTxBytes  OBJECT-TYPE
    SYNTAX Counter32
    MAX-ACCESS  read-only
    STATUS  current
    DESCRIPTION
	"The number of Tx bytes."
    ::= { pktSwchFrIfEntry 1 }

pktSwchFrIfRxBytes  OBJECT-TYPE
    SYNTAX Counter32
    MAX-ACCESS  read-only
    STATUS  current
    DESCRIPTION
	"The number of Rx bytes."
    ::= { pktSwchFrIfEntry 2 }

pktSwchFrIfTxCongDiscards  OBJECT-TYPE
    SYNTAX Counter32
    MAX-ACCESS  read-only
    STATUS  current
    DESCRIPTION
	"The number of frames discarded because of Tx congestion."
    ::= { pktSwchFrIfEntry 3 }

pktSwchFrIfDeTxFrames  OBJECT-TYPE
    SYNTAX Counter32
    MAX-ACCESS  read-only
    STATUS  current
    DESCRIPTION
	"The number of DE Tx frames."
    ::= { pktSwchFrIfEntry 4 }

pktSwchFrIfDeRxFrames  OBJECT-TYPE
    SYNTAX Counter32
    MAX-ACCESS  read-only
    STATUS  current
    DESCRIPTION
	"The number of DE Rx frames."
    ::= { pktSwchFrIfEntry 5 }

pktSwchFrIfFecnTxFrames  OBJECT-TYPE
    SYNTAX Counter32
    MAX-ACCESS  read-only
    STATUS  current
    DESCRIPTION
	"The number of FECN Tx frames."
    ::= { pktSwchFrIfEntry 6 }

pktSwchFrIfFecnRxFrames  OBJECT-TYPE
    SYNTAX Counter32
    MAX-ACCESS  read-only
    STATUS  current
    DESCRIPTION
	"The number of FECN Tx frames."
    ::= { pktSwchFrIfEntry 7 }

pktSwchFrIfBecnTxFrames  OBJECT-TYPE
    SYNTAX Counter32
    MAX-ACCESS  read-only
    STATUS  current
    DESCRIPTION
	"The number of BECN Tx frames."
    ::= { pktSwchFrIfEntry 8 }

pktSwchFrIfBecnRxFrames  OBJECT-TYPE
    SYNTAX Counter32
    MAX-ACCESS  read-only
    STATUS  current
    DESCRIPTION
	"The number of BECN Tx frames."
    ::= { pktSwchFrIfEntry 9 }

pktSwchFrIfCommRateViolTxFrames  OBJECT-TYPE
    SYNTAX Counter32
    MAX-ACCESS  read-only
    STATUS  current
    DESCRIPTION
	"The number of  Tx committed rate violations in number of frames."
    ::= { pktSwchFrIfEntry 10 }

pktSwchFrIfCommRateViolRxFrames  OBJECT-TYPE
    SYNTAX Counter32
    MAX-ACCESS  read-only
    STATUS  current
    DESCRIPTION
	"The number of  Rx committed rate violations in number of frames."
    ::= { pktSwchFrIfEntry 11 }

pktSwchFrIfExcessRateViolTxFrames  OBJECT-TYPE
    SYNTAX Counter32
    MAX-ACCESS  read-only
    STATUS  current
    DESCRIPTION
	"The number of  Tx excess rate violations in number of frames."
    ::= { pktSwchFrIfEntry 12 }

pktSwchFrIfExcessRateViolRxFrames  OBJECT-TYPE
    SYNTAX Counter32
    MAX-ACCESS  read-only
    STATUS  current
    DESCRIPTION
	"The number of  Rx excess rate violations in number of frames."
    ::= { pktSwchFrIfEntry 13 }

pktSwchFrIfBuffersInTxPool OBJECT-TYPE
    SYNTAX   Integer32
    MAX-ACCESS   read-only
    STATUS   current
    DESCRIPTION
       "The number of buffers waiting for transmission."
   ::= { pktSwchFrIfEntry 14 }

pktSwchFrIfFreeBuffersInRxPool OBJECT-TYPE
    SYNTAX   Integer32
    MAX-ACCESS   read-only
    STATUS   current
    DESCRIPTION
       "The number of free buffers in the Rx pool."
   ::= { pktSwchFrIfEntry 15 }

pktSwchFrIfLmiTxFrames OBJECT-TYPE
    SYNTAX   Counter32
    MAX-ACCESS   read-only
    STATUS   current
    DESCRIPTION
       "The number of LMI Tx Frames."
   ::= { pktSwchFrIfEntry 16 }

pktSwchFrIfLmiRxFrames OBJECT-TYPE
    SYNTAX   Counter32
    MAX-ACCESS   read-only
    STATUS   current
    DESCRIPTION
       "The number of  LMI Rx Frames."
   ::= { pktSwchFrIfEntry 17 }

pktSwchFrIfAnsiTxFrames OBJECT-TYPE
    SYNTAX   Counter32
    MAX-ACCESS   read-only
    STATUS   current
    DESCRIPTION
       "The number of  ANSI Tx Frames."
   ::= { pktSwchFrIfEntry 18 }

pktSwchFrIfAnsiRxFrames OBJECT-TYPE
    SYNTAX   Counter32
    MAX-ACCESS   read-only
    STATUS   current
    DESCRIPTION
       "The number of  ANSI Rx Frames."
   ::= { pktSwchFrIfEntry 19 }

pktSwchFrIfCllmTxFrames OBJECT-TYPE
    SYNTAX   Counter32
    MAX-ACCESS   read-only
    STATUS   current
    DESCRIPTION
       "The number of  CLLM Tx Frames."
   ::= { pktSwchFrIfEntry 20 }

pktSwchFrIfCllmRxFrames OBJECT-TYPE
    SYNTAX   Counter32
    MAX-ACCESS   read-only
    STATUS   current
    DESCRIPTION
       "The number of  CLLM Rx Frames."
   ::= { pktSwchFrIfEntry 21 }

pktSwchFrIfTxCongestions OBJECT-TYPE
    SYNTAX   Counter32
    MAX-ACCESS   read-only
    STATUS   current
    DESCRIPTION
       "The number of  Tx congestions."
   ::= { pktSwchFrIfEntry 22 }

pktSwchFrIfRxCongestions OBJECT-TYPE
    SYNTAX   Counter32
    MAX-ACCESS   read-only
    STATUS   current
    DESCRIPTION
       "The number of  Rx congestions."
   ::= { pktSwchFrIfEntry 23 }

pktSwchFrIfTotDlciNumber  OBJECT-TYPE
    SYNTAX Integer32
    MAX-ACCESS  read-only
    STATUS  current
    DESCRIPTION
	"The total number of DLCIs defined."
    ::= { pktSwchFrIfEntry 24 }


pktSwchFrCircuitSTable  OBJECT-TYPE
    SYNTAX  SEQUENCE  OF PktSwchFrCircuitSEntry
    MAX-ACCESS  not-accessible
    STATUS  current
    DESCRIPTION
	"The Frame Relay Scratch Circuit Table includes configurable objects
                 provided by the PS  that are not included in RFC 1315."
    ::=  { pktSwchFr 5 }

pktSwchFrCircuitSEntry OBJECT-TYPE
    SYNTAX  PktSwchFrCircuitSEntry
    MAX-ACCESS  not-accessible
    STATUS  current
    DESCRIPTION
	"Defines the contents of each line in the RAD PS Frame Relay
	 Circuit Scratch Table."
    INDEX   { pktSwchFrCircuitIfIndexS,pktSwchFrCircuitIndexS }
    ::=  { pktSwchFrCircuitSTable 1  }

PktSwchFrCircuitSEntry ::= SEQUENCE {
    pktSwchFrCircuitIfIndexS
     Integer32,
    pktSwchFrCircuitIndexS
     Integer32,
    pktSwchFrCircuitDestProtS
     INTEGER,
    pktSwchFrCircuitDestIdS
     DisplayString,
    pktSwchFrCircuitBackIdS
     DisplayString,
    pktSwchFrCircuitTxCirIntervalS
     Integer32,
    pktSwchFrCircuitTxCommittedS
     Integer32,
    pktSwchFrCircuitTxExcessS
     Integer32,
    pktSwchFrCircuitRxCirIntervalS
     Integer32,
    pktSwchFrCircuitRxCommittedS
     Integer32,
    pktSwchFrCircuitRxExcessS
     Integer32,
    pktSwchFrCircuitFunnelIdS
     Integer32,
    pktSwchFrCircuitStatusS
     INTEGER,
    pktSwchFrCircuitExtendedDlciS
     Integer32,
    pktSwchFrCircuitTxPriorityS
     Integer32,
    pktSwchFrCircuitIsdnRoutIdS
     Integer32
     }

pktSwchFrCircuitIfIndexS OBJECT-TYPE
    SYNTAX   Integer32
    MAX-ACCESS   read-only
    STATUS   current
    DESCRIPTION
       "This is the ifIndex of the circuit, according to RFC 1573."
   ::= { pktSwchFrCircuitSEntry 1 }

pktSwchFrCircuitIndexS OBJECT-TYPE
    SYNTAX   Integer32
    MAX-ACCESS   read-only
    STATUS   current
    DESCRIPTION
       "This Index is the DLCI of the circuit."
   ::= { pktSwchFrCircuitSEntry 2 }

pktSwchFrCircuitDestProtS OBJECT-TYPE
    SYNTAX   INTEGER {
	x25(1),
	none(2),
	hdlc(3),
	async(4),
	multiPoint(5),
	rfc1490(6)}
    MAX-ACCESS   read-write
    STATUS   current
    DESCRIPTION
       "The protocol encapsulation, if any, on this DLCI.
        The MPE protocol is a proprietary RAD protocol that enables
        a generic HDLC device to have multiple connections over X.25
        or Frame Relay."
   ::= { pktSwchFrCircuitSEntry 3 }

pktSwchFrCircuitDestIdS OBJECT-TYPE
    SYNTAX  DisplayString
    MAX-ACCESS   read-write
    STATUS   current
    DESCRIPTION
       "If the DLCI destination protocol is none or async, this field
        has a value of an existing DLCI or async channel, respectively.
        Otherwise, a value of zero is used."
   ::= { pktSwchFrCircuitSEntry 4 }

  pktSwchFrCircuitBackIdS OBJECT-TYPE
    SYNTAX  DisplayString
    MAX-ACCESS   read-write
    STATUS   current
    DESCRIPTION
       "The backup DLCI which is used when the current DLCI goes inactive.
        The destination protocol and destination id are the same as in the
        current DLCI"
   ::= { pktSwchFrCircuitSEntry 5 }

pktSwchFrCircuitTxCirIntervalS OBJECT-TYPE
    SYNTAX   Integer32 (0..10)
    MAX-ACCESS   read-write
    STATUS   current
    DESCRIPTION
       "The Tx  CIR interval in 1/10 seconds."
   ::= { pktSwchFrCircuitSEntry 6 }

pktSwchFrCircuitTxCommittedS OBJECT-TYPE
    SYNTAX   Integer32 (0..65000)
    MAX-ACCESS   read-write
    STATUS   current
    DESCRIPTION
       "The Tx committed rate in bytes per interval."
   ::= { pktSwchFrCircuitSEntry 7 }

pktSwchFrCircuitTxExcessS OBJECT-TYPE
    SYNTAX   Integer32 (0..65000)
    MAX-ACCESS   read-write
    STATUS   current
    DESCRIPTION
       "The Tx excess in bytes per interval."
   ::= { pktSwchFrCircuitSEntry 8 }

pktSwchFrCircuitRxCirIntervalS OBJECT-TYPE
    SYNTAX   Integer32 (0..10)
    MAX-ACCESS   read-write
    STATUS   current
    DESCRIPTION
       "The Rx  CIR interval in 1/10 seconds."
   ::= { pktSwchFrCircuitSEntry 9 }

pktSwchFrCircuitRxCommittedS OBJECT-TYPE
    SYNTAX   Integer32 (0..65000)
    MAX-ACCESS   read-write
    STATUS   current
    DESCRIPTION
       "The Rx committed rate in bytes per interval."
   ::= { pktSwchFrCircuitSEntry 10 }

pktSwchFrCircuitRxExcessS OBJECT-TYPE
    SYNTAX   Integer32 (0..65000)
    MAX-ACCESS   read-write
    STATUS   current
    DESCRIPTION
       "The Rx excess in bytes per interval."
   ::= { pktSwchFrCircuitSEntry 11 }

pktSwchFrCircuitFunnelIdS OBJECT-TYPE
    SYNTAX   Integer32 (1..200)
    MAX-ACCESS   read-write
    STATUS   current
    DESCRIPTION
       "The funnel ID."
   ::= { pktSwchFrCircuitSEntry 12 }

pktSwchFrCircuitStatusS OBJECT-TYPE
 	SYNTAX INTEGER {
       valid(1),
       createRequest(2),
       underCreation(3),
       invalid(4)
     }
    MAX-ACCESS  read-write
    STATUS  current
    DESCRIPTION
    "The status of the circuit row in the Table."
	::= { pktSwchFrCircuitSEntry 13 }

pktSwchFrCircuitExtendedDlciS OBJECT-TYPE
    SYNTAX   Integer32 (0..8388607)
    MAX-ACCESS   read-only
    STATUS   current
    DESCRIPTION
       "The no. of the DLCI represented in 23 bits."
   ::= { pktSwchFrCircuitSEntry 14 }

pktSwchFrCircuitTxPriorityS OBJECT-TYPE
    SYNTAX   Integer32 (1..4)
    MAX-ACCESS   read-write
    STATUS   current
    DESCRIPTION
       "DLCI TX Priority level. The levels are defined in the
        pktSwchTxPriorityTable"
    ::= { pktSwchFrCircuitSEntry 15 }

pktSwchFrCircuitIsdnRoutIdS OBJECT-TYPE
    SYNTAX   Integer32 (0..200)
    MAX-ACCESS   read-write
    STATUS   current
    DESCRIPTION
       "ISDN destination. ID in the ISDN routing table containing
        the outgoing ISDN address for this DLCI.

        Default value: 0 for no ISDN routing ID. "
    ::= { pktSwchFrCircuitSEntry 16 }


pktSwchFrCircuitATable  OBJECT-TYPE
    SYNTAX  SEQUENCE  OF PktSwchFrCircuitAEntry
    MAX-ACCESS  not-accessible
    STATUS  current
    DESCRIPTION
	"The Frame Relay Active Circuit Table includes statistics and configurable objects
                 provided by the PS  that are not included in RFC 1315."
    ::=  { pktSwchFr 6 }

pktSwchFrCircuitAEntry OBJECT-TYPE
    SYNTAX  PktSwchFrCircuitAEntry
    MAX-ACCESS  not-accessible
    STATUS  current
    DESCRIPTION
	"Defines the contents of each line in the RAD PS Frame Relay Circuit Active Table."
    INDEX   { pktSwchFrCircuitIfIndexA,pktSwchFrCircuitIndexA }
    ::=  { pktSwchFrCircuitATable 1  }

PktSwchFrCircuitAEntry ::= SEQUENCE {
    pktSwchFrCircuitIfIndexA
     Integer32,
	pktSwchFrCircuitIndexA
     Integer32,
    pktSwchFrCircuitDestProtA
     INTEGER,
    pktSwchFrCircuitDestIdA
     DisplayString,
	pktSwchFrCircuitBackIdA
     DisplayString,
    pktSwchFrCircuitTxCirIntervalA
     Integer32,
    pktSwchFrCircuitTxCommittedA
     Integer32,
    pktSwchFrCircuitTxExcessA
     Integer32,
    pktSwchFrCircuitRxCirIntervalA
     Integer32,
    pktSwchFrCircuitRxCommittedA
     Integer32,
    pktSwchFrCircuitRxExcessA
     Integer32,
    pktSwchFrCircuitFunnelIdA
     Integer32,
    pktSwchFrCircuitFunnelStat
     DisplayString,
    pktSwchFrCircuitTxCongDiscards
     Counter32,
    pktSwchFrCircuitDeTxFrames
     Counter32,
    pktSwchFrCircuitDeRxFrames
     Counter32,
    pktSwchFrCircuitFecnTxFrames
     Counter32,
    pktSwchFrCircuitBecnTxFrames
     Counter32,
    pktSwchFrCircuitCommRateViolTxFrames
     Counter32,
    pktSwchFrCircuitCommRateViolRxFrames
     Counter32,
    pktSwchFrCircuitExcessRateViolTxFrames
     Counter32,
    pktSwchFrCircuitExcessRateViolRxFrames
     Counter32,
    pktSwchFrCircuitState
     INTEGER,
    pktSwchFrCircuitExtendedDlciA
     Integer32,
    pktSwchFrCircuitTxPriorityA
     Integer32,
    pktSwchFrCircuitIsdnRoutIdA
     Integer32
     }

pktSwchFrCircuitIfIndexA OBJECT-TYPE
    SYNTAX   Integer32
    MAX-ACCESS   read-only
    STATUS   current
    DESCRIPTION
       "This is the ifIndex of the circuit, according to RFC 1573."
   ::= { pktSwchFrCircuitAEntry 1 }

pktSwchFrCircuitIndexA OBJECT-TYPE
    SYNTAX   Integer32
    MAX-ACCESS   read-only
    STATUS   current
    DESCRIPTION
       "This Index is the DLCI of the circuit."
   ::= { pktSwchFrCircuitAEntry 2 }

pktSwchFrCircuitDestProtA OBJECT-TYPE
    SYNTAX   INTEGER {
	x25(1),
	none(2),
	hdlc(3),
	async(4),
	multiPoint(5),
	rfc1490(6)}
    MAX-ACCESS   read-only
    STATUS   current
    DESCRIPTION
       "The protocol encapsulation, if any, on this DLCI.
        The MPE protocol is a proprietary RAD protocol that enables
        a generic HDLC device to have multiple connections over X.25
        or Frame Relay."
   ::= { pktSwchFrCircuitAEntry 3 }

pktSwchFrCircuitDestIdA OBJECT-TYPE
    SYNTAX  DisplayString
    MAX-ACCESS   read-only
    STATUS   current
    DESCRIPTION
       "If the DLCI destination protocol is none or async, this field
        has a value of an existing DLCI or async channel, respectively.
        Otherwise, a value of zero is used."
   ::= { pktSwchFrCircuitAEntry 4 }

pktSwchFrCircuitBackIdA OBJECT-TYPE
    SYNTAX  DisplayString
    MAX-ACCESS   read-only
    STATUS   current
    DESCRIPTION
	"The backup DLCI which is used when the current DLCI goes inactive.
        The destination protocol and destination id are the same as in the
        current DLCI"
    ::= { pktSwchFrCircuitAEntry 5 }

pktSwchFrCircuitTxCirIntervalA OBJECT-TYPE
    SYNTAX   Integer32 (0..10)
    MAX-ACCESS   read-only
    STATUS   current
    DESCRIPTION
       "The Tx  CIR interval in 1/10 seconds."
   ::= { pktSwchFrCircuitAEntry 6 }

pktSwchFrCircuitTxCommittedA OBJECT-TYPE
    SYNTAX   Integer32 (0..65000)
    MAX-ACCESS   read-only
    STATUS   current
    DESCRIPTION
       "The Tx committed rate in bytes per interval."
   ::= { pktSwchFrCircuitAEntry 7 }

pktSwchFrCircuitTxExcessA OBJECT-TYPE
    SYNTAX   Integer32 (0..65000)
    MAX-ACCESS   read-only
    STATUS   current
    DESCRIPTION
       "The Tx excess in bytes per interval."
   ::= { pktSwchFrCircuitAEntry 8 }

pktSwchFrCircuitRxCirIntervalA OBJECT-TYPE
    SYNTAX   Integer32 (0..10)
    MAX-ACCESS   read-only
    STATUS   current
    DESCRIPTION
       "The Rx  CIR interval in 1/10 seconds."
   ::= { pktSwchFrCircuitAEntry 9 }

pktSwchFrCircuitRxCommittedA OBJECT-TYPE
    SYNTAX   Integer32 (0..65000)
    MAX-ACCESS   read-only
    STATUS   current
    DESCRIPTION
       "The Rx committed rate in bytes per interval."
   ::= { pktSwchFrCircuitAEntry 10 }

pktSwchFrCircuitRxExcessA OBJECT-TYPE
    SYNTAX   Integer32 (0..65000)
    MAX-ACCESS   read-only
    STATUS   current
    DESCRIPTION
       "The Rx excess in bytes per interval."
   ::= { pktSwchFrCircuitAEntry 11 }

pktSwchFrCircuitFunnelIdA OBJECT-TYPE
    SYNTAX   Integer32 (1..200)
    MAX-ACCESS   read-only
    STATUS   current
    DESCRIPTION
       "The funnel ID."
   ::= { pktSwchFrCircuitAEntry 12 }

pktSwchFrCircuitFunnelStat OBJECT-TYPE
    SYNTAX  DisplayString
    MAX-ACCESS   read-only
    STATUS   current
    DESCRIPTION
       "The funnel status."
   ::= { pktSwchFrCircuitAEntry 13 }

pktSwchFrCircuitTxCongDiscards  OBJECT-TYPE
    SYNTAX Counter32
    MAX-ACCESS  read-only
    STATUS  current
    DESCRIPTION
	"The number of frames discarded because of Tx congestion."
    ::= { pktSwchFrCircuitAEntry 14 }

pktSwchFrCircuitDeTxFrames  OBJECT-TYPE
    SYNTAX Counter32
    MAX-ACCESS  read-only
    STATUS  current
    DESCRIPTION
	"The number of DE Tx frames."
    ::= { pktSwchFrCircuitAEntry 15 }

pktSwchFrCircuitDeRxFrames  OBJECT-TYPE
    SYNTAX Counter32
    MAX-ACCESS  read-only
    STATUS  current
    DESCRIPTION
	"The number of DE Rx frames."
    ::= { pktSwchFrCircuitAEntry 16 }

pktSwchFrCircuitFecnTxFrames  OBJECT-TYPE
    SYNTAX Counter32
    MAX-ACCESS  read-only
    STATUS  current
    DESCRIPTION
	"The number of FECN Tx frames."
    ::= { pktSwchFrCircuitAEntry 17 }

pktSwchFrCircuitBecnTxFrames  OBJECT-TYPE
    SYNTAX Counter32
    MAX-ACCESS  read-only
    STATUS  current
    DESCRIPTION
	"The number of BECN Tx frames."
    ::= { pktSwchFrCircuitAEntry 18 }

pktSwchFrCircuitCommRateViolTxFrames  OBJECT-TYPE
    SYNTAX Counter32
    MAX-ACCESS  read-only
    STATUS  current
    DESCRIPTION
	"The number of  Tx committed rate violations in number of frames."
    ::= { pktSwchFrCircuitAEntry 19 }

pktSwchFrCircuitCommRateViolRxFrames  OBJECT-TYPE
    SYNTAX Counter32
    MAX-ACCESS  read-only
    STATUS  current
    DESCRIPTION
	"The number of  Rx committed rate violations in number of frames."
    ::= { pktSwchFrCircuitAEntry 20 }

pktSwchFrCircuitExcessRateViolTxFrames  OBJECT-TYPE
    SYNTAX Counter32
    MAX-ACCESS  read-only
    STATUS  current
    DESCRIPTION
	"The number of  Tx excess rate violations in number of frames."
    ::= { pktSwchFrCircuitAEntry 21 }

pktSwchFrCircuitExcessRateViolRxFrames  OBJECT-TYPE
    SYNTAX Counter32
    MAX-ACCESS  read-only
    STATUS  current
    DESCRIPTION
	"The number of  Rx excess rate violations in number of frames."
    ::= { pktSwchFrCircuitAEntry 22 }

pktSwchFrCircuitState OBJECT-TYPE
             SYNTAX   INTEGER {
                         new (1),
                         noState (2)
                      }
             MAX-ACCESS   read-only
             STATUS   current
             DESCRIPTION
                "Indicates whether the particular virtual  cir-
                cuit  is new or not."
            ::= { pktSwchFrCircuitAEntry 23 }

pktSwchFrCircuitExtendedDlciA OBJECT-TYPE
    SYNTAX   Integer32 (0..8388607)
    MAX-ACCESS   read-only
    STATUS   current
    DESCRIPTION
       "The no. of the DLCI represented in 23 bits."
   ::= { pktSwchFrCircuitAEntry 24 }

pktSwchFrCircuitTxPriorityA OBJECT-TYPE
    SYNTAX   Integer32 (1..4)
    MAX-ACCESS   read-only
    STATUS   current
    DESCRIPTION
       "DLCI TX Priority level. The levels are defined in the
        pktSwchTxPriorityTable"
    ::= { pktSwchFrCircuitAEntry 25 }

pktSwchFrCircuitIsdnRoutIdA OBJECT-TYPE
    SYNTAX   Integer32 (0..200)
    MAX-ACCESS   read-only
    STATUS   current
    DESCRIPTION
       "ISDN destination. ID in the ISDN routing table containing
        the outgoing ISDN address for this DLCI.

        Default value: 0 for no ISDN routing ID. "
    ::= { pktSwchFrCircuitAEntry 26 }


pktSwchFrFunnelSTable  OBJECT-TYPE
    SYNTAX  SEQUENCE  OF PktSwchFrFunnelSEntry
    MAX-ACCESS  not-accessible
    STATUS  current
    DESCRIPTION
	"The Frame Relay Funnel Table defines the funnels that DLCIs may use."
    ::=  { pktSwchFr 7 }

pktSwchFrFunnelSEntry OBJECT-TYPE
    SYNTAX  PktSwchFrFunnelSEntry
    MAX-ACCESS  not-accessible
    STATUS  current
    DESCRIPTION
	"Defines the contents of each line in the RAD PS Frame Relay Funnel Table."
    INDEX   { pktSwchFrFunnelIndexS }
    ::=  { pktSwchFrFunnelSTable 1  }

PktSwchFrFunnelSEntry ::= SEQUENCE {
    pktSwchFrFunnelIndexS
     Integer32,
    pktSwchFrFunnelSizeS
     Integer32,
    pktSwchFrFunnelHighWaterFramesS
     Integer32,
    pktSwchFrFunnelHighWaterBytesS
     Integer32,
    pktSwchFrFunnelGaugeTxRateS
     Integer32,
    pktSwchFrFunnelTransWindowS
     Integer32,
    pktSwchFrFunnelStatusS
     INTEGER
    }

pktSwchFrFunnelIndexS OBJECT-TYPE
    SYNTAX   Integer32
    MAX-ACCESS   read-only
    STATUS   current
    DESCRIPTION
       "This is the index of the funnel table."
   ::= { pktSwchFrFunnelSEntry 1 }

pktSwchFrFunnelSizeS OBJECT-TYPE
    SYNTAX   Integer32 (0..256)
    MAX-ACCESS   read-write
    STATUS   current
    DESCRIPTION
       "The number of frames the funnel can store internally, where each
        frame is 512 bytes."
   ::= { pktSwchFrFunnelSEntry 2 }

pktSwchFrFunnelHighWaterFramesS OBJECT-TYPE
    SYNTAX  Integer32 (0..256)
    MAX-ACCESS   read-write
    STATUS   current
    DESCRIPTION
       "The maximum number of frames the funnel can hold before it
        expands and transmits all the data."
   ::= { pktSwchFrFunnelSEntry 3 }

pktSwchFrFunnelHighWaterBytesS OBJECT-TYPE
    SYNTAX   Integer32 (0..65000)
    MAX-ACCESS   read-write
    STATUS   current
    DESCRIPTION
       "The maximum number of bytes the funnel can hold before it expands
        and transmits all the data."
   ::= { pktSwchFrFunnelSEntry 4 }

pktSwchFrFunnelGaugeTxRateS OBJECT-TYPE
    SYNTAX   Integer32 (0..65000)
    MAX-ACCESS   read-write
    STATUS   current
    DESCRIPTION
       "The outgoing data rate in bytes per window of the funnel."
   ::= { pktSwchFrFunnelSEntry 5 }

pktSwchFrFunnelTransWindowS OBJECT-TYPE
    SYNTAX   Integer32 (0..10)
    MAX-ACCESS   read-write
    STATUS   current
    DESCRIPTION
       "The transmission rate is measured during a sliding time window.
        This parameter defines the window in 1/10 seconds."
   ::= { pktSwchFrFunnelSEntry 6 }

pktSwchFrFunnelStatusS OBJECT-TYPE
    SYNTAX  INTEGER {
      valid(1),
      createRequest(2),
      underCreation(3),
      invalid(4)
    }
    MAX-ACCESS  read-write
    STATUS  current
    DESCRIPTION
	"The status of this funnel table entry.  The choices are those defined in the SNMPv2 Textual
                 Conventions for RowStatus.  This will allow easy replacement of the INTEGER syntax with
                 the RowStatus textual convention SYNTAX."
  ::= { pktSwchFrFunnelSEntry 7 }



pktSwchFrFunnelATable  OBJECT-TYPE
    SYNTAX  SEQUENCE  OF PktSwchFrFunnelAEntry
    MAX-ACCESS  not-accessible
    STATUS  current
    DESCRIPTION
	"The Frame Relay Funnel Table defines the funnels that DLCIs may use."
    ::=  { pktSwchFr 8 }

pktSwchFrFunnelAEntry OBJECT-TYPE
    SYNTAX  PktSwchFrFunnelAEntry
    MAX-ACCESS  not-accessible
    STATUS  current
    DESCRIPTION
	"Defines the contents of each line in the RAD PS Frame Relay Funnel Table."
    INDEX   { pktSwchFrFunnelIndexA }
    ::=  { pktSwchFrFunnelATable 1  }

PktSwchFrFunnelAEntry ::= SEQUENCE {
    pktSwchFrFunnelIndexA
     Integer32,
    pktSwchFrFunnelSizeA
     Integer32,
    pktSwchFrFunnelHighWaterFramesA
     Integer32,
    pktSwchFrFunnelHighWaterBytesA
     Integer32,
    pktSwchFrFunnelGaugeTxRateA
     Integer32,
    pktSwchFrFunnelTransWindowA
     Integer32
    }

pktSwchFrFunnelIndexA OBJECT-TYPE
    SYNTAX   Integer32
    MAX-ACCESS   read-only
    STATUS   current
    DESCRIPTION
       "This is the index of the funnel table."
   ::= { pktSwchFrFunnelAEntry 1 }

pktSwchFrFunnelSizeA OBJECT-TYPE
    SYNTAX   Integer32 (0..256)
    MAX-ACCESS   read-only
    STATUS   current
    DESCRIPTION
       "The number of frames the funnel can store internally, where each frame is 512 bytes."
   ::= { pktSwchFrFunnelAEntry 2 }

pktSwchFrFunnelHighWaterFramesA OBJECT-TYPE
    SYNTAX  Integer32 (0..256)
    MAX-ACCESS   read-only
    STATUS   current
    DESCRIPTION
       "The maximum number of frames the funnel can hold before it expands and transmits all the data."
   ::= { pktSwchFrFunnelAEntry 3 }

pktSwchFrFunnelHighWaterBytesA OBJECT-TYPE
    SYNTAX   Integer32 (0..65000)
    MAX-ACCESS   read-only
    STATUS   current
    DESCRIPTION
       "The maximum number of bytes the funnel can hold before it expands and transmits all the data."
   ::= { pktSwchFrFunnelAEntry 4 }

pktSwchFrFunnelGaugeTxRateA OBJECT-TYPE
    SYNTAX   Integer32 (0..65000)
    MAX-ACCESS   read-only
    STATUS   current
    DESCRIPTION
       "The outgoing data rate in bytes per window of the funnel."
   ::= { pktSwchFrFunnelAEntry 5 }

pktSwchFrFunnelTransWindowA OBJECT-TYPE
    SYNTAX   Integer32 (0..10)
    MAX-ACCESS   read-only
    STATUS   current
    DESCRIPTION
       "The transmission rate is measured during a sliding time window.  This parameter defines the
         window in 1/10 seconds."
   ::= { pktSwchFrFunnelAEntry 6 }

pktSwchFrDlciMapTable  OBJECT-TYPE
    SYNTAX  SEQUENCE  OF PktSwchFrDlciMapEntry
    MAX-ACCESS  not-accessible
    STATUS  current
    DESCRIPTION
        "The Frame Relay Dlci mapping Table maps the Dlci numbers.
         For each long Dlci a short one is mapped.
         A long Dlci is a Dlci which contains a Dlci header of 3 or
         4 bytes instead of the regular 2 bytes.
         The long Dlci number has values from 1024 to 8,388,607."
    ::=  { pktSwchFr 9 }

pktSwchFrDlciMapEntry OBJECT-TYPE
    SYNTAX  PktSwchFrDlciMapEntry
    MAX-ACCESS  not-accessible
    STATUS  current
    DESCRIPTION
        "Defines the contents of each Dlci Map Table entry."
    INDEX   { pktSwchFrDlciMapPort, pktSwchFrDlciMapLongDlci }
    ::=  { pktSwchFrDlciMapTable 1  }

PktSwchFrDlciMapEntry ::= SEQUENCE {
    pktSwchFrDlciMapPort
     Integer32,
    pktSwchFrDlciMapLongDlci
     Integer32,
    pktSwchFrDlciMapShortDlci
     Integer32,
    pktSwchFrDlciMapStatus
     INTEGER
    }

pktSwchFrDlciMapPort OBJECT-TYPE
    SYNTAX   Integer32
    MAX-ACCESS   read-only
    STATUS   current
    DESCRIPTION
       "Frame Relay port no. : 1-8 for FPS-8, 1-4 for FPS-4,
        1-3 for APS, 1-6 for SPS-6, 1-12 for SPS-12."
   ::= { pktSwchFrDlciMapEntry 1 }


pktSwchFrDlciMapLongDlci OBJECT-TYPE
    SYNTAX   Integer32 (0..8388607)
    MAX-ACCESS   read-only
    STATUS   current
    DESCRIPTION
       "The Long Dlci number.
        For Dlci's of 4 octets, the long Dlci number has values
        from 1024 to 8,388,607.
        For Dlci's of 2 octets, the long Dlci number has values
        of 16-991."
   ::= { pktSwchFrDlciMapEntry 2 }


pktSwchFrDlciMapShortDlci OBJECT-TYPE
    SYNTAX   Integer32 (0..1023)
    MAX-ACCESS   read-only
    STATUS   current
    DESCRIPTION
       "The Short Dlci number. Legal values: 0 - 1023."
   ::= { pktSwchFrDlciMapEntry 3 }

pktSwchFrDlciMapStatus OBJECT-TYPE
 	SYNTAX INTEGER {
       valid(1),
       createRequest(2),
       underCreation(3),
       invalid(4)
     }
    MAX-ACCESS  read-write
    STATUS  current
    DESCRIPTION
    "The status of the map row in the Table.
     The only value which can be set is: createRequest.
     This value is set when a new long dlci is created."
   ::= { pktSwchFrDlciMapEntry 4 }


pktSwchMpe  OBJECT IDENTIFIER ::= { radPS 9 }

pktSwchMpeSTable  OBJECT-TYPE
    SYNTAX  SEQUENCE  OF PktSwchMpeSEntry
    MAX-ACCESS  not-accessible
    STATUS  current
    DESCRIPTION
	"The MPE Table defines Scratch configuration parameters for the MPE protocol."
    ::=  { pktSwchMpe 1 }

pktSwchMpeSEntry OBJECT-TYPE
    SYNTAX  PktSwchMpeSEntry
    MAX-ACCESS  not-accessible
    STATUS  current
    DESCRIPTION
	"Defines the contents of each line in the MPE Table."
    INDEX   { pktSwchMpeLinkNumberS }
    ::=  { pktSwchMpeSTable 1  }

PktSwchMpeSEntry ::= SEQUENCE {
    pktSwchMpeLinkNumberS
     Integer32,
    pktSwchMpeInactivityS
     Integer32,
    pktSwchMpeX25FacilitiesS
     Integer32,
    pktSwchMpeLocSubAddr1S
     Integer32,
    pktSwchMpeLocSubAddr2S
     Integer32,
    pktSwchMpeFlwCtrlDurS
     Integer32,
	pktSwchMpeFlwCtrlOptS
     Integer32,
	pktSwchMpeFlwCtrlBufS
     Integer32,
	pktSwchMpeInternalClkS
	 INTEGER
    }

pktSwchMpeLinkNumberS OBJECT-TYPE
    SYNTAX   Integer32
    MAX-ACCESS   read-write
    STATUS   current
    DESCRIPTION
       "The link number with which this entry is associated.  This value
        corresponds to pktSwchPhyInterfaceNumber.  There is an entry for
        each link for which the pktSwchPhyInterfaceProtocol is MPE."
   ::= { pktSwchMpeSEntry 1 }

pktSwchMpeInactivityS OBJECT-TYPE
    SYNTAX   Integer32 (0..255)
    MAX-ACCESS   read-write
    STATUS   current
    DESCRIPTION
       "The amount of time in minutes of inactivity that will cause the
	    session to disconnect."
   ::= { pktSwchMpeSEntry 2 }

pktSwchMpeX25FacilitiesS OBJECT-TYPE
    SYNTAX   Integer32 (0..7)
    MAX-ACCESS   read-write
    STATUS   current
    DESCRIPTION
       "This specifies the X.25 facilities.  The value is a sum of values
        (powers of two), where each value in the sum represents an option.
         The values that may be included in the sum and their meanings are:
		0 No options
		1 Packet size negotiation
		2 Window size negotiation
		4 Reverse  charge."
   ::= { pktSwchMpeSEntry 3 }

pktSwchMpeLocSubAddr1S OBJECT-TYPE
    SYNTAX   Integer32 (1..99)
    MAX-ACCESS   read-write
    STATUS   current
    DESCRIPTION
       "The first local subaddress."
   ::= { pktSwchMpeSEntry 4 }

pktSwchMpeLocSubAddr2S OBJECT-TYPE
    SYNTAX   Integer32 (1..99)
    MAX-ACCESS   read-write
    STATUS   current
    DESCRIPTION
       "The second local subaddress."
   ::= { pktSwchMpeSEntry 5 }

pktSwchMpeFlwCtrlDurS OBJECT-TYPE
    SYNTAX   Integer32 (0..200)
    MAX-ACCESS   read-write
    STATUS   current
    DESCRIPTION
       "The duration in 50 milliseconds of a hardware flow control signal. Default is 0"
   ::= { pktSwchMpeSEntry 6 }

pktSwchMpeFlwCtrlOptS OBJECT-TYPE
    SYNTAX   Integer32 (0..3)
    MAX-ACCESS   read-write
    STATUS   current
    DESCRIPTION
       "This specifies the type of flow control of the MPE link.  The value
        is a sum of values (powers of two), where each value in the sum
        represents an option.  The values that may be included in the sum
        and their meanings are:
		0 No flow control
		1 CTS flow control
		2 Clock flow control."
   ::= { pktSwchMpeSEntry 7 }

pktSwchMpeFlwCtrlBufS OBJECT-TYPE
    SYNTAX   Integer32 (0..200)
    MAX-ACCESS   read-write
    STATUS   current
    DESCRIPTION
       "The number of buffers that will be allocated for the MPE link."
   ::= { pktSwchMpeSEntry 8 }

pktSwchMpeInternalClkS  OBJECT-TYPE
    SYNTAX INTEGER {
       r2400bps (1),
       r4800bps (2),
       r9600bps (3),
       r14400bps(4),
       r19200bps(5),
       r38400bps(6),
	   r48Kbps  (7),
       r56Kbps  (8),
       r64Kbps  (9),
       r128Kbps (10),
       r256Kbps (11),
	   r384Kbps (12),
       r504Kbps (13),
	   r768Kbps (14),
	   r1008Kbps(15),
       r1466Kbps(16),
       r2016Kbps(17),
       external(255)
      }
    MAX-ACCESS  read-write
    STATUS  current
    DESCRIPTION
	"The baud rate of the internal clock."
    ::= { pktSwchMpeSEntry 9 }


pktSwchMpeATable  OBJECT-TYPE
    SYNTAX  SEQUENCE  OF PktSwchMpeAEntry
    MAX-ACCESS  not-accessible
    STATUS  current
    DESCRIPTION
	"The MPE Table defines Active configuration parameters for the MPE protocol."
    ::=  { pktSwchMpe 2 }

pktSwchMpeAEntry OBJECT-TYPE
    SYNTAX  PktSwchMpeAEntry
    MAX-ACCESS  not-accessible
    STATUS  current
    DESCRIPTION
	"Defines the contents of each line in the MPE Table."
    INDEX   { pktSwchMpeLinkNumberA }
    ::=  { pktSwchMpeATable 1  }

PktSwchMpeAEntry ::= SEQUENCE {
    pktSwchMpeLinkNumberA
     Integer32,
    pktSwchMpeInactivityA
     Integer32,
    pktSwchMpeX25FacilitiesA
     Integer32,
    pktSwchMpeLocSubAddr1A
     Integer32,
    pktSwchMpeLocSubAddr2A
     Integer32,
    pktSwchMpeFlwCtrlDurA
     Integer32,
	pktSwchMpeFlwCtrlOptA
     Integer32,
	pktSwchMpeFlwCtrlBufA
     Integer32,
	pktSwchMpeInternalClkA
	 INTEGER,
	pktSwchMpeCtsStatus
	 INTEGER
    }

pktSwchMpeLinkNumberA OBJECT-TYPE
    SYNTAX   Integer32
    MAX-ACCESS   read-only
    STATUS   current
    DESCRIPTION
       "The link number with which this entry is associated.  This value
        corresponds to pktSwchPhyInterfaceNumber.  There is an entry for
        each link for which the pktSwchPhyInterfaceProtocol is MPE."
   ::= { pktSwchMpeAEntry 1 }

pktSwchMpeInactivityA OBJECT-TYPE
    SYNTAX   Integer32 (0..255)
    MAX-ACCESS   read-only
    STATUS   current
    DESCRIPTION
       "The amount of time in minutes of inactivity that will cause the
	    session to disconnect."
   ::= { pktSwchMpeAEntry 2 }

pktSwchMpeX25FacilitiesA OBJECT-TYPE
    SYNTAX   Integer32 (0..7)
    MAX-ACCESS   read-only
    STATUS   current
    DESCRIPTION
       "This specifies the X.25 facilities.  The value is a sum of values
        (powers of two), where each value in the sum represents an option.
         The values that may be included in the sum and their meanings are:
		0 No options
		1 Packet size negotiation
		2 Window size negotiation
		4 Reverse  charge."
   ::= { pktSwchMpeAEntry 3 }

pktSwchMpeLocSubAddr1A OBJECT-TYPE
    SYNTAX   Integer32 (1..99)
    MAX-ACCESS   read-only
    STATUS   current
    DESCRIPTION
       "The first local subaddress."
   ::= { pktSwchMpeAEntry 4 }

pktSwchMpeLocSubAddr2A OBJECT-TYPE
    SYNTAX   Integer32 (1..99)
    MAX-ACCESS   read-only
    STATUS   current
    DESCRIPTION
       "The second local subaddress."
   ::= { pktSwchMpeAEntry 5 }

pktSwchMpeFlwCtrlDurA OBJECT-TYPE
    SYNTAX   Integer32 (0..200)
    MAX-ACCESS   read-only
    STATUS   current
    DESCRIPTION
       "The duration in 50 milliseconds of a hardware flow control signal."
   ::= { pktSwchMpeAEntry 6 }

pktSwchMpeFlwCtrlOptA OBJECT-TYPE
    SYNTAX   Integer32 (0..3)
    MAX-ACCESS   read-only
    STATUS   current
    DESCRIPTION
       "This specifies the type of flow control of the MPE link.  The value
        is a sum of values (powers of two), where each value in the sum
        represents an option.  The values that may be included in the sum
        and their meanings are:
		0 No flow control
		1 CTS flow control
		2 Clock flow control."
   ::= { pktSwchMpeAEntry 7 }

pktSwchMpeFlwCtrlBufA OBJECT-TYPE
    SYNTAX   Integer32 (0..200)
    MAX-ACCESS   read-only
    STATUS   current
    DESCRIPTION
       "The number of buffers that will be allocated for the MPE link."
   ::= { pktSwchMpeAEntry 8 }

pktSwchMpeInternalClkA  OBJECT-TYPE
    SYNTAX INTEGER {
       r2400bps (1),
       r4800bps (2),
       r9600bps (3),
       r14400bps(4),
       r19200bps(5),
       r38400bps(6),
	   r48Kbps  (7),
       r56Kbps  (8),
       r64Kbps  (9),
       r128Kbps (10),
       r256Kbps (11),
	   r384Kbps (12),
       r504Kbps (13),
	   r768Kbps (14),
	   r1008Kbps(15),
       r1466Kbps(16),
       r2016Kbps(17),
       external(255)
      }
    MAX-ACCESS  read-only
    STATUS  current
    DESCRIPTION
	"The baud rate of the internal clock."
    ::= { pktSwchMpeAEntry 9 }

pktSwchMpeCtsStatus  OBJECT-TYPE
    SYNTAX INTEGER {
                    off(2),
                    on(3)
                   }
    MAX-ACCESS  read-only
    STATUS  current
    DESCRIPTION
	"The CTS status."
    ::= { pktSwchMpeAEntry 10 }


pktSwchMpeAidSTable  OBJECT-TYPE
    SYNTAX  SEQUENCE  OF PktSwchMpeAidSEntry
    MAX-ACCESS  not-accessible
    STATUS  current
    DESCRIPTION
	"The AID Table defines Scratch configuration parameters for the
	 logical connections (Address Id)."
    ::=  { pktSwchMpe 3 }

pktSwchMpeAidSEntry OBJECT-TYPE
    SYNTAX  PktSwchMpeAidSEntry
    MAX-ACCESS  not-accessible
    STATUS  current
    DESCRIPTION
	"Defines the contents of each line in the MPE Table."
    INDEX   { ifIndex, pktSwchMpeAddressIdS }
    ::=  { pktSwchMpeAidSTable 1  }

PktSwchMpeAidSEntry ::= SEQUENCE {
    pktSwchMpeAddressIdS
     Integer32,
    pktSwchMpeAidMainTypeS
     INTEGER,
    pktSwchMpeAidMainIdS
     Integer32,
    pktSwchMpeAidMainSubIdS
     Integer32,
    pktSwchMpeAidBackupTypeS
     INTEGER,
    pktSwchMpeAidBackupIdS
     Integer32,
	pktSwchMpeAidBackupSubIdS
     Integer32,
	pktSwchMpeAidStatusS
	 INTEGER
    }

pktSwchMpeAddressIdS OBJECT-TYPE
    SYNTAX   Integer32
    MAX-ACCESS   read-write
    STATUS   current
    DESCRIPTION
       "The Address Id (AID) with which this entry is associated."
   ::= { pktSwchMpeAidSEntry 1 }

pktSwchMpeAidMainTypeS OBJECT-TYPE
    SYNTAX   INTEGER {
	                  x25Svc(1),
					  x25Pvc(2),
					  fr(3),
					  innerCom(4),
					  notActive(255)
					 }
    MAX-ACCESS   read-write
    STATUS   current
    DESCRIPTION
       "The protocol with which the AID is communicating."
   ::= { pktSwchMpeAidSEntry 2 }

pktSwchMpeAidMainIdS OBJECT-TYPE
    SYNTAX   Integer32 (0..200)
    MAX-ACCESS   read-write
    STATUS   current
    DESCRIPTION
       "The link number of the protocol with which the AID is communicating.
    The link number of the protocol with which the AID is communicating.

    For X.25 SVC this number is Any Autocall ID (Pre-defined) ,
    values: 1..200

    For X.25 PVC this number is a local PVC that its source link has
    already been set to the current link with a prefix of N.
    values: 1..200

    For FR this number is any Frame Relay link number (Pre-defined),
    values: 1..12

    For Inner communication this number is an HDLC or MPE link number
    (Pre-defined), values: 1..12

    For notActive this number is 0."
   ::= { pktSwchMpeAidSEntry 3 }

pktSwchMpeAidMainSubIdS OBJECT-TYPE
    SYNTAX   Integer32 (0..991)
    MAX-ACCESS   read-write
    STATUS   current
    DESCRIPTION
       "The DLCI with which the AID is communicating.
    Sub ID is used only when Type is Frame Relay or Inner Comm.
    The DLCI or destination AID with which the current AID is communicating.

    If type is: Frame Relay PVC:
    Sub ID must be an existing DLCI, 16-991.
    (The DLCI's destination protocol has to be predefined to MPE).

    If type is: Inner Communication:
    In case of an HDLC link, Sub ID must be 0.
    In case of an MPE link, Sub ID must be in AID permitted range.

    For notActive this number is 0."
   ::= { pktSwchMpeAidSEntry 4 }

pktSwchMpeAidBackupTypeS OBJECT-TYPE
    SYNTAX   INTEGER {
	                  x25Svc(1),
					  x25Pvc(2),
					  fr(3),
					  innerCom(4),
	                  notActive(255)
					 }
    MAX-ACCESS   read-write
    STATUS   current
    DESCRIPTION
       "The protocol with which the AID is communicating on the backup."
   ::= { pktSwchMpeAidSEntry 5 }

pktSwchMpeAidBackupIdS OBJECT-TYPE
    SYNTAX   Integer32 (0..200)
    MAX-ACCESS   read-write
    STATUS   current
    DESCRIPTION
       "The link number of the protocol with which the AID is communicating
        on the backup.
    The link number of the protocol with which the AID is communicating.

    For X.25 SVC this number is Any Autocall ID (Pre-defined) ,
    values: 1..200

    For X.25 PVC this number is a local PVC that its source link has
    already been set to the current link with a prefix of N.
    values: 1..200

    For FR this number is any Frame Relay link number (Pre-defined),
    values: 1..12

    For Inner communication this number is an HDLC or MPE link number
    (Pre-defined), values: 1..12

    For notActive this number is 0."
   ::= { pktSwchMpeAidSEntry 6 }

pktSwchMpeAidBackupSubIdS OBJECT-TYPE
    SYNTAX   Integer32 (0..991)
    MAX-ACCESS   read-write
    STATUS   current
    DESCRIPTION
       "The DLCI with which the AID is communicating.
    Sub ID is used only when Type is Frame Relay or Inner Comm.
    The DLCI or destination AID with which the current AID is communicating.

    If type is: Frame Relay PVC:
    Sub ID must be an existing DLCI, 16-991.
    (The DLCI's destination protocol has to be predefined to MPE).

    If type is: Inner Communication:
    In case of an HDLC link, Sub ID must be 0.
    In case of an MPE link, Sub ID must be in AID permitted range.

    For notActive this number is 0."
   ::= { pktSwchMpeAidSEntry 7 }

pktSwchMpeAidStatusS OBJECT-TYPE
    SYNTAX  INTEGER {
       valid(1),
       createRequest(2),
       underCreation(3),
       invalid(4)
     }
    MAX-ACCESS  read-write
    STATUS  current
    DESCRIPTION
	"The status of this Address Id table entry."
  ::= { pktSwchMpeAidSEntry 8 }


pktSwchMpeAidATable  OBJECT-TYPE
    SYNTAX  SEQUENCE  OF PktSwchMpeAidAEntry
    MAX-ACCESS  not-accessible
    STATUS  current
    DESCRIPTION
	"The AID Table defines Active configuration parameters for the
	 logical connections (Address Id)."
    ::=  { pktSwchMpe 4 }

pktSwchMpeAidAEntry OBJECT-TYPE
    SYNTAX  PktSwchMpeAidAEntry
    MAX-ACCESS  not-accessible
    STATUS  current
    DESCRIPTION
	"Defines the contents of each line in the MPE Table."
    INDEX   { ifIndex, pktSwchMpeAddressIdA }
    ::=  { pktSwchMpeAidATable 1  }

PktSwchMpeAidAEntry ::= SEQUENCE {
    pktSwchMpeAddressIdA
     Integer32,
    pktSwchMpeAidMainTypeA
     INTEGER,
    pktSwchMpeAidMainIdA
     Integer32,
    pktSwchMpeAidMainSubIdA
     Integer32,
    pktSwchMpeAidBackupTypeA
     INTEGER,
    pktSwchMpeAidBackupIdA
     Integer32,
	pktSwchMpeAidBackupSubIdA
     Integer32,
	pktSwchMpeAidConn
	 INTEGER,
	pktSwchMpeAidFlwCtrl
	 INTEGER
    }

pktSwchMpeAddressIdA OBJECT-TYPE
    SYNTAX   Integer32
    MAX-ACCESS   read-only
    STATUS   current
    DESCRIPTION
       "The Address Id (AID) with which this entry is associated."
   ::= { pktSwchMpeAidAEntry 1 }

pktSwchMpeAidMainTypeA OBJECT-TYPE
    SYNTAX   INTEGER {
	                  x25Svc(1),
					  x25Pvc(2),
					  fr(3),
					  innerCom(4),
	                  notActive(255)
					 }
    MAX-ACCESS   read-only
    STATUS   current
    DESCRIPTION
       "The protocol with which the AID is communicating."
   ::= { pktSwchMpeAidAEntry 2 }

pktSwchMpeAidMainIdA OBJECT-TYPE
    SYNTAX   Integer32 (0..200)
    MAX-ACCESS   read-only
    STATUS   current
    DESCRIPTION
       "The link number of the protocol with which the AID is communicating.
    The link number of the protocol with which the AID is communicating.

    For X.25 SVC this number is Any Autocall ID (Pre-defined) ,
    values: 1..200

    For X.25 PVC this number is a local PVC that its source link has
    already been set to the current link with a prefix of N.
    values: 1..200

    For FR this number is any Frame Relay link number (Pre-defined),
    values: 1..12

    For Inner communication this number is an HDLC or MPE link number
    (Pre-defined), values: 1..12

    For notActive this number is 0."
   ::= { pktSwchMpeAidAEntry 3 }

pktSwchMpeAidMainSubIdA OBJECT-TYPE
    SYNTAX   Integer32 (0..991)
    MAX-ACCESS   read-only
    STATUS   current
    DESCRIPTION
       "The DLCI with which the AID is communicating.
    Sub ID is used only when Type is Frame Relay or Inner Comm.
    The DLCI or destination AID with which the current AID is communicating.

    If type is: Frame Relay PVC:
    Sub ID must be an existing DLCI, 16-991.
    (The DLCI's destination protocol has to be predefined to MPE).

    If type is: Inner Communication:
    In case of an HDLC link, Sub ID must be 0.
    In case of an MPE link, Sub ID must be in AID permitted range.

    For notActive this number is 0."
   ::= { pktSwchMpeAidAEntry 4 }

pktSwchMpeAidBackupTypeA OBJECT-TYPE
    SYNTAX   INTEGER {
	                  x25Svc(1),
					  x25Pvc(2),
					  fr(3),
					  innerCom(4),
	                  notActive(255)
					 }
    MAX-ACCESS   read-only
    STATUS   current
    DESCRIPTION
       "The protocol with which the AID is communicating on the backup."
   ::= { pktSwchMpeAidAEntry 5 }

pktSwchMpeAidBackupIdA OBJECT-TYPE
    SYNTAX   Integer32 (0..200)
    MAX-ACCESS   read-only
    STATUS   current
    DESCRIPTION
       "The link number of the protocol with which the AID is communicating
        on the backup.
    The link number of the protocol with which the AID is communicating.

    For X.25 SVC this number is Any Autocall ID (Pre-defined) ,
    values: 1..200

    For X.25 PVC this number is a local PVC that its source link has
    already been set to the current link with a prefix of N.
    values: 1..200

    For FR this number is any Frame Relay link number (Pre-defined),
    values: 1..12

    For Inner communication this number is an HDLC or MPE link number
    (Pre-defined), values: 1..12

    For notActive this number is 0."
   ::= { pktSwchMpeAidAEntry 6 }

pktSwchMpeAidBackupSubIdA OBJECT-TYPE
    SYNTAX   Integer32 (0..991)
    MAX-ACCESS   read-only
    STATUS   current
    DESCRIPTION
       "The DLCI with which the AID is communicating.
    Sub ID is used only when Type is Frame Relay or Inner Comm.
    The DLCI or destination AID with which the current AID is communicating.

    If type is: Frame Relay PVC:
    Sub ID must be an existing DLCI, 16-991.
    (The DLCI's destination protocol has to be predefined to MPE).

    If type is: Inner Communication:
    In case of an HDLC link, Sub ID must be 0.
    In case of an MPE link, Sub ID must be in AID permitted range.

    For notActive this number is 0."
   ::= { pktSwchMpeAidAEntry 7 }

pktSwchMpeAidConn OBJECT-TYPE
    SYNTAX   INTEGER {
                    disconnect(1),
					connect(2),
					pvc(3)
					}
    MAX-ACCESS   read-only
    STATUS   current
    DESCRIPTION
       "The connectivity status of the AID."
   ::= { pktSwchMpeAidAEntry 8 }

pktSwchMpeAidFlwCtrl OBJECT-TYPE
    SYNTAX   INTEGER {
	                  inactive(1),
	                  active(2)
					 }
    MAX-ACCESS   read-only
    STATUS   current
    DESCRIPTION
       "The Flow Control status of the AID."
   ::= { pktSwchMpeAidAEntry 9 }


-- The PS Slip Group contains  Slip Scratch and Active Tables,
-- which contain configuration for Slip links

pktSwchSlip  OBJECT IDENTIFIER ::= { radPS 10 }

pktSwchSlipSTable  OBJECT-TYPE
    SYNTAX  SEQUENCE  OF PktSwchSlipSEntry
    MAX-ACCESS  not-accessible
    STATUS  current
    DESCRIPTION
    "The Scratch Slip Table contains configuration information for
     Slip links"
    ::=  { pktSwchSlip 1 }

pktSwchSlipSEntry OBJECT-TYPE
    SYNTAX  PktSwchSlipSEntry
    MAX-ACCESS  not-accessible
    STATUS  current
    DESCRIPTION
    "Defines the contents of each line in the RAD Slip Table."
    INDEX   { pktSwchSlipLinkNumberS }
    ::=  { pktSwchSlipSTable 1  }

PktSwchSlipSEntry ::= SEQUENCE {
    pktSwchSlipLinkNumberS
     Integer32,
    pktSwchSlipSpeedS
     INTEGER,
    pktSwchSlipFCOptionS
     Integer32,
    pktSwchSlipStopBitsS
     INTEGER,
    pktSwchSlipBitPerCharS
     Integer32,
    pktSwchSlipParityS
     INTEGER,
    pktSwchSlipIpAddressS
     IpAddress,
    pktSwchSlipIpMaskS
     IpAddress,
    pktSwchSlipDefEncapsTypeS
     INTEGER,
    pktSwchSlipDefDestinationS
     DisplayString
    }

pktSwchSlipLinkNumberS  OBJECT-TYPE
    SYNTAX Integer32
    MAX-ACCESS  read-only
    STATUS  current
    DESCRIPTION
    "The link number with which this entry is associated.  This value
     corresponds to pktSwchPhyInterfaceIfIndex.  There is an entry for
     each link for which the pktSwchPhyInterfaceProtocol is Slip."
    ::= { pktSwchSlipSEntry 1 }

pktSwchSlipSpeedS OBJECT-TYPE
    SYNTAX  INTEGER  {
       s110bps    (1),
       s300bps    (2),
       s1200bps   (3),
       s600bps    (4),
       s75bps     (5),
       s150bps    (6),

       s2400bps  (12),
       s4800bps  (13),
       s9600bps  (14),
       s19200bps (15),

       s38400bps (19),
       s57600bps (20),
       s115200bps(21)
    }
    MAX-ACCESS  read-write
    STATUS  current
    DESCRIPTION
    "This parameter determines the rate of data transmission to
     and from the DTE."
    ::= { pktSwchSlipSEntry 2 }

pktSwchSlipFCOptionS OBJECT-TYPE
    SYNTAX Integer32 (0..255)
    MAX-ACCESS  read-write
    STATUS  current
    DESCRIPTION  " The flow control options
              0 - No HARDWARE flow control
         1..254 - Timer value (in 50ms intervals),
                  when timer expires, flow control stops
            255 - The timer is not used"
    ::= { pktSwchSlipSEntry 3 }

pktSwchSlipStopBitsS OBJECT-TYPE
    SYNTAX  INTEGER  {
       one       (1),
       two       (2),
       oneAndHalf(3)
    }
    MAX-ACCESS  read-write
    STATUS  current
    DESCRIPTION
    "This entry indicates the number of stop bits per character
     supported by the PAD.
     The options are either (1) one stop bit, (2) two stop bits,
     or (3) 1.5 stop bits."
    ::= { pktSwchSlipSEntry 4 }

pktSwchSlipBitPerCharS  OBJECT-TYPE
    SYNTAX Integer32 (5..8)
    MAX-ACCESS  read-write
    STATUS  current
    DESCRIPTION
    "The number of data bits per character supported by the Slip
     link."
    ::= { pktSwchSlipSEntry 5 }

pktSwchSlipParityS  OBJECT-TYPE
    SYNTAX  INTEGER  {
       space(1),
       mark(2),
       even(3),
       odd(4),
       none(255)
    }
    MAX-ACCESS  read-write
    STATUS  current
    DESCRIPTION
    "This entry selects the type of parity to be checked and or
     generated by the PAD when radSPSProfileParTreat is a value
     other than 255.
     The options are (1) space parity, (2) mark parity,
     (3) even parity, (4) odd parity, or (255) no parity."
    ::= { pktSwchSlipSEntry 6 }

pktSwchSlipIpAddressS  OBJECT-TYPE
    SYNTAX IpAddress
    MAX-ACCESS  read-write
    STATUS  deprecated
    DESCRIPTION
        "The IP address connected to this Slip port. This variable is
         used when an automatic connection is done by the IP Routing."
    ::= { pktSwchSlipSEntry 7 }

pktSwchSlipIpMaskS  OBJECT-TYPE
    SYNTAX 	IpAddress
    MAX-ACCESS  read-write
    STATUS  deprecated
    DESCRIPTION
        "The IP mask. This variable is
         used when an automatic connection by the IP Routing is done."
    ::= { pktSwchSlipSEntry 8 }

pktSwchSlipDefEncapsTypeS  OBJECT-TYPE
    SYNTAX  INTEGER {
             slip       (1),
             x25SVC     (2),
             x25PVC     (3),
             frameRelay (4),
             hdlc       (5),
             none      (255)
    }
    MAX-ACCESS  read-write
    STATUS  deprecated
    DESCRIPTION
        "Destination protocol of this Slip port. This variable is used
         when a direct connection without IP Routing is done."
    ::= { pktSwchSlipSEntry 9 }

pktSwchSlipDefDestinationS  OBJECT-TYPE
    SYNTAX DisplayString
    MAX-ACCESS  read-write
    STATUS  deprecated
    DESCRIPTION
    "Default destination for this Slip port.
    This variable is used when a direct connection without
    IP Routing is done.
    Possible values:
    Default :     Not Used.
    X.25 PVC:     Port:LCN  or a pre defined PVC number
    X.25 SVC:     X.25 Addr or cid followed by a predefined Call ID number
    Frame Relay:  Port:DLCI
    HDLC:         HDLC Port Number
    SLIP:         SLIP Channel Number"
    ::= { pktSwchSlipSEntry 10 }


--  The active slip table
--

pktSwchSlipATable  OBJECT-TYPE
    SYNTAX  SEQUENCE  OF PktSwchSlipAEntry
    MAX-ACCESS  not-accessible
    STATUS  current
    DESCRIPTION
    "The Active Slip Table contains configuration information for
     Slip links"
    ::=  { pktSwchSlip 2 }


pktSwchSlipAEntry OBJECT-TYPE
    SYNTAX  PktSwchSlipAEntry
    MAX-ACCESS  not-accessible
    STATUS  current
    DESCRIPTION
    "Defines the contents of each line in the RAD Slip Table."
    INDEX   { pktSwchSlipLinkNumberA }
    ::=  { pktSwchSlipATable 1  }

PktSwchSlipAEntry ::= SEQUENCE {
    pktSwchSlipLinkNumberA
     Integer32,
    pktSwchSlipSpeedA
     INTEGER,
    pktSwchSlipFCOptionA
     Integer32,
    pktSwchSlipStopBitsA
     INTEGER,
    pktSwchSlipBitPerCharA
     Integer32,
    pktSwchSlipParityA
     INTEGER,
    pktSwchSlipIpAddressA
     IpAddress,
    pktSwchSlipIpMaskA
     IpAddress,
    pktSwchSlipDefEncapsTypeA
     INTEGER,
    pktSwchSlipDefDestinationA
     DisplayString
    }

pktSwchSlipLinkNumberA  OBJECT-TYPE
    SYNTAX Integer32
    MAX-ACCESS  read-only
    STATUS  current
    DESCRIPTION
    "The link number with which this entry is associated.  This value
     corresponds to pktSwchPhyInterfaceIfIndex.  There is an entry for
     each link for which the pktSwchPhyInterfaceProtocol is Slip."
    ::= { pktSwchSlipAEntry 1 }


pktSwchSlipSpeedA OBJECT-TYPE
    SYNTAX  INTEGER  {
       s110bps    (1),
       s300bps    (2),
       s1200bps   (3),
       s600bps    (4),
       s75bps     (5),
       s150bps    (6),

       s2400bps  (12),
       s4800bps  (13),
       s9600bps  (14),
       s19200bps (15),

       s38400bps (19),
       s57600bps (20),
       s115200bps(21)
    }
    MAX-ACCESS  read-only
    STATUS  current
    DESCRIPTION
    "This parameter determines the rate of data transmission to
     and from the DTE."
    ::= { pktSwchSlipAEntry 2 }

pktSwchSlipFCOptionA OBJECT-TYPE
    SYNTAX Integer32 (0..255)
    MAX-ACCESS  read-only
    STATUS  current
    DESCRIPTION
    " The flow control options
              0 - No HARDWARE flow control
         1..254 - Timer value (in 50ms intervals),
                  when timer expires, flow control stops
            255 - The timer is not used"
    ::= { pktSwchSlipAEntry 3 }

 pktSwchSlipStopBitsA OBJECT-TYPE
    SYNTAX  INTEGER  {
       one       (1),
       two       (2),
       oneAndHalf(3)
    }
    MAX-ACCESS  read-only
    STATUS  current
    DESCRIPTION
    "This entry indicates the number of stop bits per character
     supported by the PAD.
     The options are either (1) one stop bit, (2) two stop bits,
     or (3) 1.5 stop bits."
    ::= { pktSwchSlipAEntry 4 }

pktSwchSlipBitPerCharA  OBJECT-TYPE
    SYNTAX Integer32 (5..8)
    MAX-ACCESS  read-only
    STATUS  current
    DESCRIPTION
    "The number of data bits per character supported by the Slip
     link."
    ::= { pktSwchSlipAEntry 5 }

pktSwchSlipParityA  OBJECT-TYPE
    SYNTAX  INTEGER  {
       space(1),
       mark(2),
       even(3),
       odd(4),
       none(255)
    }
    MAX-ACCESS  read-only
    STATUS  current
    DESCRIPTION
    "This entry selects the type of parity to be checked and or
     generated by the PAD when radSPSProfileParTreat is a value
     other than 255.
     The options are (1) space parity, (2) mark parity,
     (3) even parity, (4) odd parity, or (255) no parity."
    ::= { pktSwchSlipAEntry 6 }

pktSwchSlipIpAddressA  OBJECT-TYPE
    SYNTAX IpAddress
    MAX-ACCESS  read-only
    STATUS  deprecated
    DESCRIPTION
        "The IP address connected to this Slip port."
    ::= { pktSwchSlipAEntry 7 }

pktSwchSlipIpMaskA  OBJECT-TYPE
    SYNTAX  IpAddress
    MAX-ACCESS  read-only
    STATUS  deprecated
    DESCRIPTION
        "The IP mask."
    ::= { pktSwchSlipAEntry 8 }

pktSwchSlipDefEncapsTypeA  OBJECT-TYPE
    SYNTAX  INTEGER {
             slip       (1),
             x25SVC     (2),
             x25PVC     (3),
             frameRelay (4),
             hdlc       (5),
             none      (255)
    }
    MAX-ACCESS  read-only
    STATUS  deprecated
    DESCRIPTION
        "Destination protocol of this Slip port."
    ::= { pktSwchSlipAEntry 9 }

pktSwchSlipDefDestinationA  OBJECT-TYPE
    SYNTAX DisplayString
    MAX-ACCESS  read-only
    STATUS  deprecated
    DESCRIPTION
    "Default destination for this Slip port.
    This variable is used when a direct connection without
    IP Routing is done.
    Possible values:
    Default :     Not Used.
    X.25 PVC:     Port:LCN  or a pre defined PVC number
    X.25 SVC:     X.25 Addr or cid followed by a predefined Call ID number
    Frame Relay:  Port:DLCI
    HDLC:         HDLC Port Number
    SLIP:         SLIP Channel Number"
    ::= { pktSwchSlipAEntry 10 }



pktSwchSna    OBJECT IDENTIFIER ::= { radPS 11}

pktSwchSnaSDLCLinkTableS    OBJECT-TYPE
    SYNTAX  SEQUENCE  OF PktSwchSnaSDLCLinkEntryS
    MAX-ACCESS  not-accessible
    STATUS  current
    DESCRIPTION
	"The SDLC Link Table defines the SDLC links configured on the PS."
     ::=  { pktSwchSna 1 }

pktSwchSnaSDLCLinkEntryS OBJECT-TYPE
    SYNTAX  PktSwchSnaSDLCLinkEntryS
    MAX-ACCESS  not-accessible
    STATUS  current
    DESCRIPTION
	"SDLC Link Entry defines the contents of each link in the SDLC Link Table."
    INDEX   {ifIndex }
    ::=  { pktSwchSnaSDLCLinkTableS 1 }

PktSwchSnaSDLCLinkEntryS ::= SEQUENCE {
pktSwchSnaSDLCLinkTypeS
INTEGER,
pktSwchSnaSDLCLinkPUSharedS
INTEGER,
pktSwchSnaSDLCLinkDuplexPhyS
INTEGER,
pktSwchSnaSDLCLinkflagsS
Integer32,
pktSwchSnaSDLCLinkDuplexS
INTEGER,
pktSwchSnaSDLCLinkClockS
INTEGER,
pktSwchSnaSDLCLinkNRZS
INTEGER
     }

pktSwchSnaSDLCLinkTypeS  OBJECT-TYPE
    SYNTAX INTEGER{
	primary(1),
	secondary(2)
	       }
    MAX-ACCESS  read-write
    STATUS  current
    DESCRIPTION
	"This parameter identifies whether this link operates as
         TPAD(Primary) or HPAD(Secondary) SDLC device."
    ::= { pktSwchSnaSDLCLinkEntryS 1 }

pktSwchSnaSDLCLinkPUSharedS  OBJECT-TYPE
    SYNTAX INTEGER {
       yes(1),
       no (2)
	       }
    MAX-ACCESS  read-write
    STATUS  current
    DESCRIPTION
	"This parameter defines whether the link participates with more than
	 one PU or not."
    ::= { pktSwchSnaSDLCLinkEntryS 2 }

pktSwchSnaSDLCLinkDuplexPhyS OBJECT-TYPE
    SYNTAX INTEGER {
        half (1),
        full (2)
	 }
    MAX-ACCESS  read-write
    STATUS  current
    DESCRIPTION
        "This parameter describes whether the physical level of the
        SDLC line is half or full duplex."
    ::= { pktSwchSnaSDLCLinkEntryS 3 }

pktSwchSnaSDLCLinkflagsS OBJECT-TYPE
        SYNTAX Integer32 (1..15)
	MAX-ACCESS  read-write
	STATUS  current
    DESCRIPTION
        "Number of flags between frames."
  ::= { pktSwchSnaSDLCLinkEntryS 4 }

pktSwchSnaSDLCLinkDuplexS OBJECT-TYPE
	SYNTAX INTEGER {
        twoWayAlter (1),
        twoWaySimul (2)
	}
	MAX-ACCESS  read-write
	STATUS  current
    DESCRIPTION
        " This parameter shows wether the link level is Two Way Alternate
          or Two Way Simultaneous."
	::= { pktSwchSnaSDLCLinkEntryS 5 }

pktSwchSnaSDLCLinkClockS OBJECT-TYPE
    SYNTAX INTEGER {
	r2400bps(1),
	r4800bps(2),
	r9600Bps(3),
	r14400bps(4),
	r19200bps(5),
	r38400bps(6),
	r48000bps(7),
	r56000bps(8),
	r64000bps(9),
	r128000bps(10),
	r256000bps(11),
	r384000bps(12),
	r504000bps(13),
	r768000bps(14),
	r1008000bps(15),
	r1466000bps(16),
	r2016000bps(17),
	external(255)
	}
	MAX-ACCESS read-write
	STATUS current
	DESCRIPTION
	" This parameter defines the link clock rate "
	::= { pktSwchSnaSDLCLinkEntryS 6 }

pktSwchSnaSDLCLinkNRZS OBJECT-TYPE
SYNTAX INTEGER {
        nrzFlags(1),
        nrziFlags(2),
        nrzIdle(3),
        nrziIdle(4)
		}
MAX-ACCESS read-write
STATUS current
DESCRIPTION
        " This parameter describes the following combinations of NRZ,
          NRZI with FLAGS or IDLE between frames:
          Legal values:
           1 - NRZ  with FLAGs between frames. RTS is Constant
           2 - NRZI with FLAGs between frames. RTS is Constant.
           3 - NRZ  with IDLE between frames.  RTS is Controlled.
           4 - NRZI with IDLE between frames.  RTS is Controlled."
	::={ pktSwchSnaSDLCLinkEntryS 7}


pktSwchSnaSDLCLinkTableA    OBJECT-TYPE
    SYNTAX  SEQUENCE  OF PktSwchSnaSDLCLinkEntryA
    MAX-ACCESS  not-accessible
    STATUS  current
    DESCRIPTION
	"The SDLC Link Table defines the SDLC links configured on the SPS."
     ::=  { pktSwchSna 2 }

pktSwchSnaSDLCLinkEntryA OBJECT-TYPE
    SYNTAX  PktSwchSnaSDLCLinkEntryA
    MAX-ACCESS  not-accessible
    STATUS  current
    DESCRIPTION
	"SDLC Link Entry defines the contents of each link in the SDLC Link Table."
    INDEX   {ifIndex }
    ::=  { pktSwchSnaSDLCLinkTableA 1 }

PktSwchSnaSDLCLinkEntryA ::= SEQUENCE {
pktSwchSnaSDLCLinkTypeA
INTEGER,
pktSwchSnaSDLCLinkPUSharedA
INTEGER,
pktSwchSnaSDLCLinkDuplexPhyA
INTEGER,
pktSwchSnaSDLCLinkflagsA
Integer32,
pktSwchSnaSDLCLinkDuplexA
INTEGER,
pktSwchSnaSDLCLinkClockA
INTEGER,
pktSwchSnaSDLCLinkNRZA
INTEGER,
pktSwchSnaSDLCLinkStatFrames
Counter32,
pktSwchSnaSDLCLinkStatErrors
Counter32,
pktSwchSnaSDLCLinkStatInvalidAddresses
Counter32,
pktSwchSnaSDLCLinkStatShortFrames
Counter32
     }

pktSwchSnaSDLCLinkTypeA  OBJECT-TYPE
    SYNTAX INTEGER{
	primary(1),
	secondary(2)
	     }
    MAX-ACCESS  read-only
    STATUS  current
    DESCRIPTION
	"This parameter identifies whether this link operates as
         TPAD(Primary) or HPAD(Secondary) SDLC device."
    ::= { pktSwchSnaSDLCLinkEntryA 1 }

pktSwchSnaSDLCLinkPUSharedA  OBJECT-TYPE
    SYNTAX INTEGER {
       yes(1),
       no (2)
		 }
    MAX-ACCESS  read-only
    STATUS  current
    DESCRIPTION
	"This parameter defines whether the link participates with more
	 than one PU or not."
    ::= { pktSwchSnaSDLCLinkEntryA 2 }

pktSwchSnaSDLCLinkDuplexPhyA OBJECT-TYPE
    SYNTAX INTEGER {
        half (1),
        full (2)
	 }
    MAX-ACCESS  read-only
    STATUS  current
    DESCRIPTION
        "This parameter describes whether the physical level of the
        SDLC line is half or full duplex."
    ::= { pktSwchSnaSDLCLinkEntryA 3 }

pktSwchSnaSDLCLinkflagsA OBJECT-TYPE
        SYNTAX Integer32 (1..15)
	MAX-ACCESS  read-only
	STATUS  current
    DESCRIPTION
        "Number of flags between frames."
  ::= { pktSwchSnaSDLCLinkEntryA 4 }

pktSwchSnaSDLCLinkDuplexA OBJECT-TYPE
	SYNTAX INTEGER {
        twoWayAlter (1),
        twoWaySimul (2)
	}
	MAX-ACCESS  read-only
	STATUS  current
    DESCRIPTION
        " This parameter shows wether the link level is Two Way Alternate
          or Two Way Simultaneous."
	::= { pktSwchSnaSDLCLinkEntryA 5 }

pktSwchSnaSDLCLinkClockA OBJECT-TYPE
    SYNTAX INTEGER {
	r2400bps(1),
	r4800bps(2),
	r9600Bps(3),
	r14400bps(4),
	r19200bps(5),
	r38400bps(6),
	r48000bps(7),
	r56000bps(8),
	r64000bps(9),
	r128000bps(10),
	r256000bps(11),
	r384000bps(12),
	r504000bps(13),
	r768000bps(14),
	r1008000bps(15),
	r1466000bps(16),
	r2016000bps(17),
	external(255)
	}
	MAX-ACCESS read-only
	STATUS current
	DESCRIPTION
	" This parameter defines the link clock rate."
	::= { pktSwchSnaSDLCLinkEntryA 6 }

pktSwchSnaSDLCLinkNRZA OBJECT-TYPE
SYNTAX INTEGER {
        nrzFlags(1),
        nrziFlags(2),
        nrzIdle(3),
        nrziIdle(4)
		}
MAX-ACCESS read-only
STATUS current
DESCRIPTION
        " This parameter describes the following combinations of NRZ,
          NRZI with FLAGS or IDLE between frames:
          Legal values:
           1 - NRZ  with FLAGs between frames. RTS is Constant
           2 - NRZI with FLAGs between frames. RTS is Constant.
           3 - NRZ  with IDLE between frames.  RTS is Controlled.
           4 - NRZI with IDLE between frames.  RTS is Controlled."
	::={ pktSwchSnaSDLCLinkEntryA 7}

pktSwchSnaSDLCLinkStatFrames OBJECT-TYPE
    SYNTAX  Counter32
    MAX-ACCESS  read-only
    STATUS  current
    DESCRIPTION
    "The number of frames received or transmitted via this link "
	::= { pktSwchSnaSDLCLinkEntryA 8 }

pktSwchSnaSDLCLinkStatErrors OBJECT-TYPE
    SYNTAX  Counter32
    MAX-ACCESS  read-only
    STATUS  current
    DESCRIPTION
    "The number of error frames received. "
	::= { pktSwchSnaSDLCLinkEntryA 9}

pktSwchSnaSDLCLinkStatInvalidAddresses OBJECT-TYPE
    SYNTAX  Counter32
    MAX-ACCESS  read-only
    STATUS  current
    DESCRIPTION
    "The number of frames with wrong address received by this link. "
	::= { pktSwchSnaSDLCLinkEntryA 10}

pktSwchSnaSDLCLinkStatShortFrames OBJECT-TYPE
    SYNTAX  Counter32
    MAX-ACCESS  read-only
    STATUS  current
    DESCRIPTION
    "The number of short  frames received by this link. "
	::= { pktSwchSnaSDLCLinkEntryA 11}


pktSwchSnaPUTableS    OBJECT-TYPE
    SYNTAX  SEQUENCE  OF PktSwchSnaPUEntryS
    MAX-ACCESS  not-accessible
    STATUS  current
    DESCRIPTION
	"The SDLC PU table defines the PUs configured on the PS."
     ::=  { pktSwchSna 3 }

pktSwchSnaPUEntryS OBJECT-TYPE
    SYNTAX  PktSwchSnaPUEntryS
    MAX-ACCESS  not-accessible
    STATUS  current
    DESCRIPTION
	"SDLC PU Entry defines the contents of each PU in the
	 SDLC PU Table."
    INDEX   {pktSwchSnaPUNumberS}
    ::=  { pktSwchSnaPUTableS 1 }

PktSwchSnaPUEntryS ::= SEQUENCE {
pktSwchSnaPUNumberS
Integer32,
pktSwchSnaPUXIDProcessingS
INTEGER,
pktSwchSnaPUEnableS
INTEGER,
pktSwchSnaPULinkATypeS
INTEGER,
pktSwchSnaPULinkARoleS
INTEGER,
pktSwchSnaPULinkBTypeS
INTEGER,
pktSwchSnaPULinkBRoleS
INTEGER,
pktSwchSnaPUEntryStatusS
INTEGER
}
pktSwchSnaPUNumberS OBJECT-TYPE
    SYNTAX  Integer32
    MAX-ACCESS  read-only
    STATUS  current
    DESCRIPTION
    "This parameter defines an identifier associated with the PU Entry
     which is unique within the SPS"
	::= { pktSwchSnaPUEntryS 1}

pktSwchSnaPUXIDProcessingS OBJECT-TYPE
    SYNTAX  INTEGER {
	localXid(1),
	end2EndSupNoAct(2),
	end2EndNoSupNoAct(3)
		}
    MAX-ACCESS  read-write
    STATUS  current
    DESCRIPTION
   "Exchange Identification (XID) processing. The following values are legal:
    1 - Local XID handling
    2 - End-to-End XID handling, Support for NON-Activation XID
    3 - End-to-End XID handling, NO Support for NON-Activation XID"
	::= { pktSwchSnaPUEntryS 2}

pktSwchSnaPUEnableS OBJECT-TYPE
    SYNTAX INTEGER {
	 enable(1),
	 disable(2)
		   }
    MAX-ACCESS  read-write
    STATUS  current
    DESCRIPTION
    "The PU runs or not at this specific time"
	::= { pktSwchSnaPUEntryS 3}


pktSwchSnaPULinkATypeS OBJECT-TYPE
    SYNTAX  INTEGER {
	sdlc(1),
	x25Qllc(2),
	frameRelayLLC2(3)
			}
    MAX-ACCESS  read-write
    STATUS  current
    DESCRIPTION
    "The PU link A type."
	::= { pktSwchSnaPUEntryS 4}

pktSwchSnaPULinkARoleS OBJECT-TYPE
    SYNTAX  INTEGER {
	primary(1),
	secondary(2)
	}
    MAX-ACCESS  read-write
    STATUS  current
    DESCRIPTION
    "The PU role for link A. Note that the role of an SDLC PU may
     not be changed. It is defined by the SDLC Link Type."
	::= { pktSwchSnaPUEntryS 5}

pktSwchSnaPULinkBTypeS OBJECT-TYPE
    SYNTAX  INTEGER {
	sdlc(1),
	x25Qllc(2),
	frameRelayLLC2(3)
			}
    MAX-ACCESS  read-write
    STATUS  current
    DESCRIPTION
    "The PU partner link B type"
	::= { pktSwchSnaPUEntryS 6}

pktSwchSnaPULinkBRoleS OBJECT-TYPE
    SYNTAX  INTEGER {
	primary(1),
	secondary(2)
	}
    MAX-ACCESS  read-write
    STATUS  current
    DESCRIPTION
    "The PU role for link B. Note that the role of an SDLC PU may
     not be changed. It is defined by the SDLC Link Type."
	::= { pktSwchSnaPUEntryS 7}

pktSwchSnaPUEntryStatusS OBJECT-TYPE
    SYNTAX  INTEGER {
       valid(1),
       createRequest(2),
       underCreation(3),
       invalid(4)
     }
    MAX-ACCESS  read-write
    STATUS  current
    DESCRIPTION
    "The status of this PU table entry.
     This Set request will fail if there are any conflicts between any of
     of the parameter values in any of the tables comprising this PU
     definition "
         ::= {pktSwchSnaPUEntryS 8}

pktSwchSnaPUTableA    OBJECT-TYPE
    SYNTAX  SEQUENCE  OF PktSwchSnaPUEntryA
    MAX-ACCESS  not-accessible
    STATUS  current
    DESCRIPTION
	"The SDLC PU table defines the PUs configured on the PS."
     ::=  { pktSwchSna 4 }

pktSwchSnaPUEntryA OBJECT-TYPE
    SYNTAX  PktSwchSnaPUEntryA
    MAX-ACCESS  not-accessible
    STATUS  current
    DESCRIPTION
	"SDLC PU Entry defines the contents of each PU in the
	 SDLC PU Table."
    INDEX   {pktSwchSnaPUNumberA}
    ::=  { pktSwchSnaPUTableA 1 }

PktSwchSnaPUEntryA ::= SEQUENCE {
pktSwchSnaPUNumberA
Integer32,
pktSwchSnaPUXIDProcessingA
INTEGER,
pktSwchSnaPUEnableA
INTEGER,
pktSwchSnaPULinkATypeA
INTEGER,
pktSwchSnaPULinkARoleA
INTEGER,
pktSwchSnaPULinkBTypeA
INTEGER,
pktSwchSnaPULinkBRoleA
INTEGER
}
pktSwchSnaPUNumberA OBJECT-TYPE
    SYNTAX  Integer32
    MAX-ACCESS  read-only
    STATUS  current
    DESCRIPTION
    "This parameter defines an identifier associated with the PU Entry
     which is unique within the SPS"
	::= { pktSwchSnaPUEntryA 1}

pktSwchSnaPUXIDProcessingA OBJECT-TYPE
    SYNTAX  INTEGER {
	localXid(1),
	end2EndSupNoAct(2),
	end2EndNoSupNoAct(3)
		}
    MAX-ACCESS  read-only
    STATUS  current
    DESCRIPTION
    "The PU XID Processing"
	::= { pktSwchSnaPUEntryA 2}

pktSwchSnaPUEnableA OBJECT-TYPE
    SYNTAX INTEGER {
	 enable(1),
	 disable(2)
		   }
    MAX-ACCESS  read-only
    STATUS  current
    DESCRIPTION
    "The PU runs or not at this specific time"
	::= { pktSwchSnaPUEntryA 3}


pktSwchSnaPULinkATypeA OBJECT-TYPE
    SYNTAX  INTEGER {
	sdlc(1),
	x25Qllc(2),
	frameRelayLLC2(3)
	}
    MAX-ACCESS  read-only
    STATUS  current
    DESCRIPTION
    "The PU link type"
	::= { pktSwchSnaPUEntryA 4}

pktSwchSnaPULinkARoleA OBJECT-TYPE
    SYNTAX  INTEGER {
	primary(1),
	secondary(2)
	}
    MAX-ACCESS  read-only
    STATUS  current
    DESCRIPTION
    "The PU role for link A"
	::= { pktSwchSnaPUEntryA 5}

pktSwchSnaPULinkBTypeA OBJECT-TYPE
    SYNTAX  INTEGER {
	sdlc(1),
	x25Qllc(2),
	frameRelayLLC2(3)
			}
    MAX-ACCESS  read-only
    STATUS  current
    DESCRIPTION
    "The PU partner link type"
	::= { pktSwchSnaPUEntryA 6}

pktSwchSnaPULinkBRoleA OBJECT-TYPE
    SYNTAX  INTEGER {
	primary(1),
	secondary(2)
	}
    MAX-ACCESS  read-only
    STATUS  current
    DESCRIPTION
    "The PU role for link B"
	::= { pktSwchSnaPUEntryA 7}

pktSwchSnaPUSdlcTableS    OBJECT-TYPE
    SYNTAX  SEQUENCE  OF PktSwchSnaPUSdlcEntryS
    MAX-ACCESS  not-accessible
    STATUS  current
    DESCRIPTION
	"Defines links for PUs running on SDLC link "
     ::=  { pktSwchSna 5 }

pktSwchSnaPUSdlcEntryS OBJECT-TYPE
    SYNTAX  PktSwchSnaPUSdlcEntryS
    MAX-ACCESS  not-accessible
    STATUS  current
    DESCRIPTION
	"Defines parameters of a link for a PU running on an SDLC link "
    INDEX   {pktSwchSnaPUSdlcNumberS , pktSwchSnaPUSdlcSideS }
    ::=  { pktSwchSnaPUSdlcTableS 1 }

PktSwchSnaPUSdlcEntryS ::= SEQUENCE {
pktSwchSnaPUSdlcNumberS
Integer32,
pktSwchSnaPUSdlcSideS
INTEGER,
pktSwchSnaPUSdlcAddressS
OCTET STRING,
pktSwchSnaPUSdlcIfIndexS
Integer32,
pktSwchSnaPUSdlcIdBlkS
OCTET STRING,
pktSwchSnaPUSdlcIdNumS
OCTET STRING,
pktSwchSnaPUSdlcMaxPiuSizeS
Integer32,
pktSwchSnaPUSdlcTxWindowS
Integer32,
pktSwchSnaPUSdlcGrpAddressS
OCTET STRING,
pktSwchSnaPUSdlcPollTimerS
Integer32,
pktSwchSnaPUSdlcXIDInitiationS
INTEGER,
pktSwchSnaPUSdlcEntryStatusS
INTEGER
}

pktSwchSnaPUSdlcNumberS OBJECT-TYPE
    SYNTAX  Integer32
    MAX-ACCESS  read-only
    STATUS  current
    DESCRIPTION
    "This parameter defines an identifier associated with the PU Entry
     SDLC side, which is unique within the SPS"
	::= { pktSwchSnaPUSdlcEntryS 1}

pktSwchSnaPUSdlcSideS OBJECT-TYPE
    SYNTAX  INTEGER {
	    sideA(1),
	    sideB(2)
	    }
    MAX-ACCESS  read-only
    STATUS  current
    DESCRIPTION
    "Is this side A or side B of the PU definition "
	::= { pktSwchSnaPUSdlcEntryS 2}

pktSwchSnaPUSdlcAddressS OBJECT-TYPE
    SYNTAX  OCTET STRING (SIZE(1))
    MAX-ACCESS  read-write
    STATUS  current
    DESCRIPTION
    "SNA SDLC PU address. Range: 0x00-0xFE "
	::= { pktSwchSnaPUSdlcEntryS 3}

pktSwchSnaPUSdlcIfIndexS OBJECT-TYPE
    SYNTAX  Integer32
    MAX-ACCESS  read-write
    STATUS  current
    DESCRIPTION
    "ifIndex of the SDLC link"
	::= { pktSwchSnaPUSdlcEntryS 4}

pktSwchSnaPUSdlcIdBlkS OBJECT-TYPE
    SYNTAX  OCTET STRING (SIZE(1..2))
    MAX-ACCESS  read-write
    STATUS  current
    DESCRIPTION
"Part of the IBM device ID (the full ID is defined by the IDBLK and
 the IDNUM). The Idblk is required for secondary PU with Local XID
 handling.  Up to 3 Hexadecimal digits, format: 0X XX."
       ::= {pktSwchSnaPUSdlcEntryS 5}

pktSwchSnaPUSdlcIdNumS OBJECT-TYPE
    SYNTAX  OCTET STRING (SIZE(1..3))
    MAX-ACCESS  read-write
    STATUS  current
    DESCRIPTION
"Second part of the IBM device ID (the full ID is defined by the IDBLK and
 the IDNUM). The Idnum is required for secondary PU with Local XID
 handling.  Up to 5 Hexadecimal digits, format: 0X XX XX."
       ::= {pktSwchSnaPUSdlcEntryS 6}


pktSwchSnaPUSdlcMaxPiuSizeS OBJECT-TYPE
    SYNTAX Integer32 (137..7642)
    MAX-ACCESS  read-write
    STATUS  current
    DESCRIPTION
    "Maximum Path Information Size"
	::= { pktSwchSnaPUSdlcEntryS 7}


pktSwchSnaPUSdlcTxWindowS OBJECT-TYPE
    SYNTAX  Integer32
    MAX-ACCESS  read-write
    STATUS  current
    DESCRIPTION
    "Window Size(in frames) used when sending from the SPS. Range: 1-7."
	::= { pktSwchSnaPUSdlcEntryS 8}

pktSwchSnaPUSdlcGrpAddressS OBJECT-TYPE
    SYNTAX  OCTET STRING (SIZE(1))
    MAX-ACCESS  read-write
    STATUS  current
    DESCRIPTION
    "SNA Group address used by the SPS when sending polls (TPAD ONLY).
     Range: 0x00-0xFE"
	::= { pktSwchSnaPUSdlcEntryS 9}

pktSwchSnaPUSdlcPollTimerS OBJECT-TYPE
    SYNTAX  Integer32
    MAX-ACCESS  read-write
    STATUS  current
    DESCRIPTION
    "Time in between polls in 50 millisecond increments (TPAD ONLY).
     Range: 1-65535."
	::= { pktSwchSnaPUSdlcEntryS 10}

pktSwchSnaPUSdlcXIDInitiationS OBJECT-TYPE
    SYNTAX  INTEGER{
	notInitiate(1),
	initiate(2)
	}
    MAX-ACCESS  read-write
    STATUS  current
    DESCRIPTION
 "This parameter is not applicable for PU with Local XID handling.
 Legal values:
 1 - Do not initiate an XID message.
 2 - Initiate an XID message to SDLC."
	::= { pktSwchSnaPUSdlcEntryS 11}

pktSwchSnaPUSdlcEntryStatusS OBJECT-TYPE
    SYNTAX  INTEGER {
       valid(1),
       underCreation(3)
     }
    MAX-ACCESS  read-write
    STATUS  current
    DESCRIPTION
    "The status of this PU Sdlc table entry.
     In order to save this entry, set status to valid.
     An underCreation value is set by the Agent when this entry is updated."
         ::= {pktSwchSnaPUSdlcEntryS 12}


pktSwchSnaPUSdlcTableA    OBJECT-TYPE
    SYNTAX  SEQUENCE  OF PktSwchSnaPUSdlcEntryA
    MAX-ACCESS  not-accessible
    STATUS  current
    DESCRIPTION
	"Defines links for PUs running on an SDLC link "
     ::=  { pktSwchSna 6 }

pktSwchSnaPUSdlcEntryA OBJECT-TYPE
    SYNTAX  PktSwchSnaPUSdlcEntryA
    MAX-ACCESS  not-accessible
    STATUS  current
    DESCRIPTION
	"Defines parameters of link for PU running on an SDLC link "
    INDEX   {pktSwchSnaPUSdlcNumberA , pktSwchSnaPUSdlcSideA }
    ::=  { pktSwchSnaPUSdlcTableA 1 }

PktSwchSnaPUSdlcEntryA ::= SEQUENCE {
pktSwchSnaPUSdlcNumberA
Integer32,
pktSwchSnaPUSdlcSideA
INTEGER,
pktSwchSnaPUSdlcAddressA
OCTET STRING,
pktSwchSnaPUSdlcIfIndexA
Integer32,
pktSwchSnaPUSdlcIdBlkA
OCTET STRING,
pktSwchSnaPUSdlcIdNumA
OCTET STRING,
pktSwchSnaPUSdlcMaxPiuSizeA
Integer32,
pktSwchSnaPUSdlcTxWindowA
Integer32,
pktSwchSnaPUSdlcGrpAddressA
OCTET STRING,
pktSwchSnaPUSdlcPollTimerA
Integer32,
pktSwchSnaPUSdlcXIDInitiationA
INTEGER
}
pktSwchSnaPUSdlcNumberA OBJECT-TYPE
    SYNTAX  Integer32
    MAX-ACCESS  read-only
    STATUS  current
    DESCRIPTION
    "This parameter defines an identifier associated with the PU Entry
     SDLC side, which is unique within the SPS"
	::= { pktSwchSnaPUSdlcEntryA 1}

pktSwchSnaPUSdlcSideA OBJECT-TYPE
    SYNTAX  INTEGER {
	    sideA(1),
	    sideB(2)
	    }
    MAX-ACCESS  read-only
    STATUS  current
    DESCRIPTION
    "Is this side A or side B of the PU definition "
	::= { pktSwchSnaPUSdlcEntryA 2}

pktSwchSnaPUSdlcAddressA OBJECT-TYPE
    SYNTAX  OCTET STRING (SIZE(1))
    MAX-ACCESS  read-only
    STATUS  current
    DESCRIPTION
    "SNA SDLC PU address. Range: 0x00-0xFE."
	::= { pktSwchSnaPUSdlcEntryA 3}


pktSwchSnaPUSdlcIfIndexA OBJECT-TYPE
    SYNTAX  Integer32
    MAX-ACCESS  read-only
    STATUS  current
    DESCRIPTION
    "ifIndex of the SDLC link"
	::= { pktSwchSnaPUSdlcEntryA 4}

pktSwchSnaPUSdlcIdBlkA OBJECT-TYPE
    SYNTAX  OCTET STRING (SIZE(1..2))
    MAX-ACCESS  read-only
    STATUS  current
    DESCRIPTION
"Part of the IBM device ID (the full ID is defined by the IDBLK and
 the IDNUM). The Idblk is required for secondary PU with Local XID
 handling.  Up to 3 Hexadecimal digits, format: 0X XX."
       ::= {pktSwchSnaPUSdlcEntryA 5}

pktSwchSnaPUSdlcIdNumA OBJECT-TYPE
    SYNTAX  OCTET STRING (SIZE(1..3))
    MAX-ACCESS  read-only
    STATUS  current
    DESCRIPTION
"Second part of the IBM device ID (the full ID is defined by the IDBLK and
 the IDNUM). The Idnum is required for secondary PU with Local XID
 handling.  Up to 5 Hexadecimal digits, format: 0X XX XX."
       ::= {pktSwchSnaPUSdlcEntryA 6}


pktSwchSnaPUSdlcMaxPiuSizeA OBJECT-TYPE
    SYNTAX Integer32 (137..7642)
    MAX-ACCESS  read-only
    STATUS  current
    DESCRIPTION
    "Maximum Path Information Size"
	::= {pktSwchSnaPUSdlcEntryA 7}

pktSwchSnaPUSdlcTxWindowA OBJECT-TYPE
    SYNTAX  Integer32
    MAX-ACCESS  read-only
    STATUS  current
    DESCRIPTION
    "Window Size(in frames) used when sending from the SPS.
     Range: 1-7."
	::= { pktSwchSnaPUSdlcEntryA 8}

pktSwchSnaPUSdlcGrpAddressA OBJECT-TYPE
    SYNTAX  OCTET STRING (SIZE(1))
    MAX-ACCESS  read-only
    STATUS  current
    DESCRIPTION
    "SNA Group address used by the SPS when sending polls (TPAD ONLY).
     Range: 0x00-0xFE."
	::= { pktSwchSnaPUSdlcEntryA 9}

pktSwchSnaPUSdlcPollTimerA OBJECT-TYPE
    SYNTAX  Integer32
    MAX-ACCESS  read-only
    STATUS  current
    DESCRIPTION
    "Time in between polls in 50 millisecond increments (TPAD ONLY).
     Range: 1-65535."
	::= { pktSwchSnaPUSdlcEntryA 10}

pktSwchSnaPUSdlcXIDInitiationA OBJECT-TYPE
    SYNTAX  INTEGER{
	notInitiate(1),
	initiate(2)
	}
    MAX-ACCESS  read-only
    STATUS  current
    DESCRIPTION
 "This parameter is not applicable for PU with Local XID handling.
 Legal values:
 1 - Do not initiate an XID message.
 2 - Initiate an XID message to SDLC."
	::= { pktSwchSnaPUSdlcEntryA 11}


pktSwchSnaPUSdlcStatTable    OBJECT-TYPE
    SYNTAX  SEQUENCE  OF PktSwchSnaPUSdlcStatEntry
    MAX-ACCESS  not-accessible
    STATUS  current
    DESCRIPTION
	"Shows Link Statistics for PUs running on an SDLC link "
        ::=  { pktSwchSna 7 }

pktSwchSnaPUSdlcStatEntry OBJECT-TYPE
    SYNTAX  PktSwchSnaPUSdlcStatEntry
    MAX-ACCESS  not-accessible
    STATUS  current
    DESCRIPTION
	"Shows Link Statistics for PUs running on an SDLC link "
    INDEX   {pktSwchSnaPUSdlcStatNumber , pktSwchSnaPUSdlcStatSide }
    ::=  { pktSwchSnaPUSdlcStatTable 1 }

PktSwchSnaPUSdlcStatEntry ::= SEQUENCE {
pktSwchSnaPUSdlcStatNumber
Integer32,
pktSwchSnaPUSdlcStatSide
INTEGER,
pktSwchSnaPUSdlcStatOctetsIn
Counter32,
pktSwchSnaPUSdlcStatOctetsOut
Counter32,
pktSwchSnaPUSdlcStatIFramesIn
Counter32,
pktSwchSnaPUSdlcStatIFramesOut
Counter32,
pktSwchSnaPUSdlcStatRRFramesIn
Counter32,
pktSwchSnaPUSdlcStatRRFramesOut
Counter32,
pktSwchSnaPUSdlcStatRNRFramesIn
Counter32,
pktSwchSnaPUSdlcStatRNRFramesOut
Counter32,
pktSwchSnaPUSdlcStatXIDsIn
Counter32,
pktSwchSnaPUSdlcStatXIDsOut
Counter32,
pktSwchSnaPUSdlcStatTESTsIn
Counter32,
pktSwchSnaPUSdlcStatTESTsOut
Counter32,
pktSwchSnaPUSdlcStatREJsIn
Counter32,
pktSwchSnaPUSdlcStatREJsOut
Counter32,
pktSwchSnaPUSdlcStatFRMRsIn
Counter32,
pktSwchSnaPUSdlcStatFRMRsOut
Counter32,
pktSwchSnaPUSdlcStatDISCsIn
Counter32,
pktSwchSnaPUSdlcStatDISCsOut
Counter32,
pktSwchSnaPUSdlcStatUAsIn
Counter32,
pktSwchSnaPUSdlcStatUAsOut
Counter32,
pktSwchSnaPUSdlcStatDMsIn
Counter32,
pktSwchSnaPUSdlcStatDMsOut
Counter32,
pktSwchSnaPUSdlcStatSNRMsIn
Counter32,
pktSwchSnaPUSdlcStatSNRMsOut
Counter32,
pktSwchSnaPUSdlcStatRetransmitsIn
Counter32,
pktSwchSnaPUSdlcStatRetransmitsOut
Counter32,
pktSwchSnaPUSdlcUpperState
INTEGER,
pktSwchSnaPUSdlcLowerState
INTEGER,
pktSwchSnaPUSdlcStatNRMStatus
INTEGER,
pktSwchSnaPUSdlcStatFlowCtlStatus
INTEGER
}
pktSwchSnaPUSdlcStatNumber OBJECT-TYPE
    SYNTAX  Integer32
    MAX-ACCESS  read-only
    STATUS  current
    DESCRIPTION
    "This parameter defines an identifier associated with the PU Entry
     SDLC side statistics, which is unique within the SPS"
	::= { pktSwchSnaPUSdlcStatEntry 1}

pktSwchSnaPUSdlcStatSide OBJECT-TYPE
    SYNTAX  INTEGER {
	    sideA(1),
	    sideB(2)
	    }
    MAX-ACCESS  read-only
    STATUS  current
    DESCRIPTION
    "Is this side A or side B of the PU definition "
	::= { pktSwchSnaPUSdlcStatEntry 2}

pktSwchSnaPUSdlcStatOctetsIn OBJECT-TYPE
 SYNTAX Counter32
 MAX-ACCESS  read-only
 STATUS  current
 DESCRIPTION
    ""
	::= { pktSwchSnaPUSdlcStatEntry 3}

pktSwchSnaPUSdlcStatOctetsOut OBJECT-TYPE
 SYNTAX Counter32
 MAX-ACCESS  read-only
 STATUS  current
 DESCRIPTION
    ""
	::= { pktSwchSnaPUSdlcStatEntry 4}

pktSwchSnaPUSdlcStatIFramesIn OBJECT-TYPE
 SYNTAX Counter32
 MAX-ACCESS  read-only
 STATUS  current
 DESCRIPTION
    ""
	::= { pktSwchSnaPUSdlcStatEntry 5}

pktSwchSnaPUSdlcStatIFramesOut OBJECT-TYPE
 SYNTAX Counter32
 MAX-ACCESS  read-only
 STATUS  current
 DESCRIPTION
    ""
	::= { pktSwchSnaPUSdlcStatEntry 6}

pktSwchSnaPUSdlcStatRRFramesIn OBJECT-TYPE
 SYNTAX Counter32
 MAX-ACCESS  read-only
 STATUS  current
 DESCRIPTION
    ""
	::= { pktSwchSnaPUSdlcStatEntry 7}

pktSwchSnaPUSdlcStatRRFramesOut OBJECT-TYPE
 SYNTAX Counter32
 MAX-ACCESS  read-only
 STATUS  current
 DESCRIPTION
    ""
	::= { pktSwchSnaPUSdlcStatEntry 8}

pktSwchSnaPUSdlcStatRNRFramesIn OBJECT-TYPE
 SYNTAX Counter32
 MAX-ACCESS  read-only
 STATUS  current
 DESCRIPTION
    ""
	::= { pktSwchSnaPUSdlcStatEntry 9}

pktSwchSnaPUSdlcStatRNRFramesOut OBJECT-TYPE
 SYNTAX Counter32
 MAX-ACCESS  read-only
 STATUS  current
 DESCRIPTION
    ""
	::= { pktSwchSnaPUSdlcStatEntry 10}

pktSwchSnaPUSdlcStatXIDsIn OBJECT-TYPE
 SYNTAX Counter32
 MAX-ACCESS  read-only
 STATUS  current
 DESCRIPTION
    ""
	::= { pktSwchSnaPUSdlcStatEntry 11}

pktSwchSnaPUSdlcStatXIDsOut OBJECT-TYPE
 SYNTAX Counter32
 MAX-ACCESS  read-only
 STATUS  current
 DESCRIPTION
    ""
	::= { pktSwchSnaPUSdlcStatEntry 12}

pktSwchSnaPUSdlcStatTESTsIn OBJECT-TYPE
 SYNTAX Counter32
 MAX-ACCESS  read-only
 STATUS  current
 DESCRIPTION
    ""
	::= { pktSwchSnaPUSdlcStatEntry 13}

pktSwchSnaPUSdlcStatTESTsOut OBJECT-TYPE
 SYNTAX Counter32
 MAX-ACCESS  read-only
 STATUS  current
 DESCRIPTION
    ""
	::= { pktSwchSnaPUSdlcStatEntry 14}

pktSwchSnaPUSdlcStatREJsIn OBJECT-TYPE
 SYNTAX Counter32
 MAX-ACCESS  read-only
 STATUS  current
 DESCRIPTION
    ""
	::= { pktSwchSnaPUSdlcStatEntry 15}

pktSwchSnaPUSdlcStatREJsOut OBJECT-TYPE
 SYNTAX Counter32
 MAX-ACCESS  read-only
 STATUS  current
 DESCRIPTION
    ""
	::= { pktSwchSnaPUSdlcStatEntry 16}

pktSwchSnaPUSdlcStatFRMRsIn OBJECT-TYPE
 SYNTAX Counter32
 MAX-ACCESS  read-only
 STATUS  current
 DESCRIPTION
    ""
	::= { pktSwchSnaPUSdlcStatEntry 17}

pktSwchSnaPUSdlcStatFRMRsOut OBJECT-TYPE
 SYNTAX Counter32
 MAX-ACCESS  read-only
 STATUS  current
 DESCRIPTION
    ""
	::= { pktSwchSnaPUSdlcStatEntry 18}

pktSwchSnaPUSdlcStatDISCsIn OBJECT-TYPE
 SYNTAX Counter32
 MAX-ACCESS  read-only
 STATUS  current
 DESCRIPTION
    ""
	::= { pktSwchSnaPUSdlcStatEntry 19}

pktSwchSnaPUSdlcStatDISCsOut OBJECT-TYPE
 SYNTAX Counter32
 MAX-ACCESS  read-only
 STATUS  current
 DESCRIPTION
    ""
	::= { pktSwchSnaPUSdlcStatEntry 20}

pktSwchSnaPUSdlcStatUAsIn OBJECT-TYPE
 SYNTAX Counter32
 MAX-ACCESS  read-only
 STATUS  current
 DESCRIPTION
    ""
	::= { pktSwchSnaPUSdlcStatEntry 21}

pktSwchSnaPUSdlcStatUAsOut OBJECT-TYPE
 SYNTAX Counter32
 MAX-ACCESS  read-only
 STATUS  current
 DESCRIPTION
    ""
	::= { pktSwchSnaPUSdlcStatEntry 22}

pktSwchSnaPUSdlcStatDMsIn OBJECT-TYPE
 SYNTAX Counter32
 MAX-ACCESS  read-only
 STATUS  current
 DESCRIPTION
    ""
	::= { pktSwchSnaPUSdlcStatEntry 23}

pktSwchSnaPUSdlcStatDMsOut OBJECT-TYPE
 SYNTAX Counter32
 MAX-ACCESS  read-only
 STATUS  current
 DESCRIPTION
    ""
	::= { pktSwchSnaPUSdlcStatEntry 24}

pktSwchSnaPUSdlcStatSNRMsIn OBJECT-TYPE
 SYNTAX Counter32
 MAX-ACCESS  read-only
 STATUS  current
 DESCRIPTION
    ""
	::= { pktSwchSnaPUSdlcStatEntry 25}

pktSwchSnaPUSdlcStatSNRMsOut OBJECT-TYPE
 SYNTAX Counter32
 MAX-ACCESS  read-only
 STATUS  current
 DESCRIPTION
    ""
	::= { pktSwchSnaPUSdlcStatEntry 26}

pktSwchSnaPUSdlcStatRetransmitsIn OBJECT-TYPE
 SYNTAX Counter32
 MAX-ACCESS  read-only
 STATUS  current
 DESCRIPTION
    ""
	::= { pktSwchSnaPUSdlcStatEntry 27}

pktSwchSnaPUSdlcStatRetransmitsOut OBJECT-TYPE
 SYNTAX Counter32
 MAX-ACCESS  read-only
 STATUS  current
 DESCRIPTION
    ""
	::= { pktSwchSnaPUSdlcStatEntry 28}

pktSwchSnaPUSdlcUpperState  OBJECT-TYPE
 SYNTAX INTEGER {
    unbound(1),
    bindPending(2),
    unbindPend(3),
    idle(4),
    unattached(5),
    attachPend(6),
    detachPend(7),
    udqosPending(8),
    outconPend(9),
    inconPending(10),
    connResPend(11),
    dataxfer(12),
    userResetPend(13),
    provRstPend(14),
    rstResPend(15),
    discon8Pend(16),
    discon9Pend(17),
    discon11Pend(18),
    discon12Pend(19),
    discon13Pend(20),
    subsBindPnd(21),
    noChange(22)
	}
 MAX-ACCESS read-only
 STATUS current
 DESCRIPTION
    "The internal DLPI state of the connection."
	::= { pktSwchSnaPUSdlcStatEntry 29}

pktSwchSnaPUSdlcLowerState  OBJECT-TYPE
 SYNTAX INTEGER  {
    linkClosed(1),
    disconnected(2),
    linkOpening(3),
    disconnecting(4),
    frmrSent(5),
    linkOpened(6),
    localBusy(7),
    rejection(8),
    checkpointing(9),
    cpLocalBusy(10),
    cpRejection(11),
    resetting(12),
    remoteBusy(13),
    lBusyRBusy(14),
    rejLBusy(15),
    rejRBusy(16),
    cpRejLBusy(17),
    cpClearing(18),
    cpRejClr(19),
    rejLbusyRbusy(20),
    frmrReceived(21),
    programError(22),
    noChange(23)
	}
 MAX-ACCESS read-only
 STATUS current
 DESCRIPTION
    "The internal SDLC state of the connection."
	::= { pktSwchSnaPUSdlcStatEntry 30}

pktSwchSnaPUSdlcStatNRMStatus OBJECT-TYPE
 SYNTAX INTEGER	 {sync(1),notSync(2)}
 MAX-ACCESS  read-only
 STATUS  current
 DESCRIPTION
    "This variable indicates if the link is in Normal Response Mode or not."
	::= { pktSwchSnaPUSdlcStatEntry 31}

pktSwchSnaPUSdlcStatFlowCtlStatus OBJECT-TYPE
 SYNTAX INTEGER	 {noRNR(1),txFlow(2), rxFlow(3), rxAndTx(4)}
 MAX-ACCESS  read-only
 STATUS  current
 DESCRIPTION
    "This variable indicates the flow control status of the PU interface."
	::= { pktSwchSnaPUSdlcStatEntry 32}


pktSwchSnaPUSX25QllcTableS    OBJECT-TYPE
    SYNTAX  SEQUENCE  OF PktSwchSnaPUX25QllcEntryS
    MAX-ACCESS  not-accessible
    STATUS  current
    DESCRIPTION
	"Defines links for PUs running on a QLLC link "
     ::=  {pktSwchSna 8 }

pktSwchSnaPUX25QllcEntryS OBJECT-TYPE
    SYNTAX  PktSwchSnaPUX25QllcEntryS
    MAX-ACCESS  not-accessible
    STATUS  current
    DESCRIPTION
	"Defines parameters for PU side running on SDLC link "
    INDEX   {pktSwchSnaPUX25QllcNumberS , pktSwchSnaPUX25QllcSideS }
    ::=  { pktSwchSnaPUSX25QllcTableS 1 }

PktSwchSnaPUX25QllcEntryS ::= SEQUENCE {
pktSwchSnaPUX25QllcNumberS
Integer32,
pktSwchSnaPUX25QllcSideS
INTEGER,
pktSwchSnaPUX25QllcIdBlkS
OCTET STRING,
pktSwchSnaPUX25QllcIdNumS
OCTET STRING,
pktSwchSnaPUX25QllcXIDInitS
INTEGER,
pktSwchSnaPUX25QllcMaxPiuSizeS
Integer32,
pktSwchSnaPUX25QllcStationAddressS
OCTET STRING,
pktSwchSnaPUX25QllcInPasswordS
DisplayString,
pktSwchSnaPUX25QllcSubAddressS
Integer32,
pktSwchSnaPUX25QllcAutoCallS
INTEGER,
pktSwchSnaPUX25QllcCalledAddressS
OCTET STRING,
pktSwchSnaPUX25QllcCallUserDataFacilitiesS
DisplayString,
pktSwchSnaPUX25QllcEntryStatusS
INTEGER
}

pktSwchSnaPUX25QllcNumberS OBJECT-TYPE
    SYNTAX  Integer32
    MAX-ACCESS  read-only
    STATUS  current
    DESCRIPTION
    "This parameter defines an identifier associated with the PU Entry
     X25\QLLC side, which is unique within the SPS"
	::= {pktSwchSnaPUX25QllcEntryS 1}

pktSwchSnaPUX25QllcSideS  OBJECT-TYPE
    SYNTAX  INTEGER {
	    sideA(1),
	    sideB(2)
	    }
    MAX-ACCESS  read-only
    STATUS  current
    DESCRIPTION
    "Is there side A or B of the PU connection "
	::= {pktSwchSnaPUX25QllcEntryS 2}

pktSwchSnaPUX25QllcIdBlkS OBJECT-TYPE
    SYNTAX  OCTET STRING (SIZE(1..2))
    MAX-ACCESS  read-write
    STATUS  current
    DESCRIPTION
"Part of the IBM device ID (the full ID is defined by the IDBLK and
 the IDNUM). The Idblk is required for secondary PU with Local XID
 handling.  Up to 3 Hexadecimal digits, format: 0X XX."
       ::= {pktSwchSnaPUX25QllcEntryS 3}

pktSwchSnaPUX25QllcIdNumS OBJECT-TYPE
    SYNTAX  OCTET STRING (SIZE(1..3))
    MAX-ACCESS  read-write
    STATUS  current
    DESCRIPTION
"Second part of the IBM device ID (the full ID is defined by the IDBLK and
 the IDNUM). The Idnum is required for secondary PU with Local XID
 handling.  Up to 5 Hexadecimal digits, format: 0X XX XX."
       ::= {pktSwchSnaPUX25QllcEntryS 4}

pktSwchSnaPUX25QllcXIDInitS OBJECT-TYPE
    SYNTAX  INTEGER {
	notInitiate(1),
	initiate(2)
	}
    MAX-ACCESS  read-write
    STATUS  current
    DESCRIPTION
 "This parameter is not applicable for PU with Local XID handling.
 Legal values:
 1 - Do not initiate an XID message.
 2 - Initiate an XID message to QLLC."
       ::= {pktSwchSnaPUX25QllcEntryS 5}

pktSwchSnaPUX25QllcMaxPiuSizeS OBJECT-TYPE
    SYNTAX Integer32 (137..7642)
    MAX-ACCESS  read-write
    STATUS  current
    DESCRIPTION
    "Maximum Path Information Size"
	::= { pktSwchSnaPUX25QllcEntryS 6}


pktSwchSnaPUX25QllcStationAddressS OBJECT-TYPE
    SYNTAX  OCTET STRING (SIZE(1))
    MAX-ACCESS  read-write
    STATUS  current
    DESCRIPTION
"QLLC PU Link Station Address. Range: 0x01-0xFE.
 This parameter is applicable only for PU with End-to-End XID handling,
 Support for NON-Activation XID."
       ::= {pktSwchSnaPUX25QllcEntryS 7}

pktSwchSnaPUX25QllcInPasswordS OBJECT-TYPE
    SYNTAX  DisplayString (SIZE(1..8))
    MAX-ACCESS  read-write
    STATUS  current
    DESCRIPTION
    "A field matched with the call user data in call request packets for
     purposes of security and correlation."
       ::= {pktSwchSnaPUX25QllcEntryS 8}

pktSwchSnaPUX25QllcSubAddressS OBJECT-TYPE
    SYNTAX  Integer32
    MAX-ACCESS  read-write
    STATUS  current
    DESCRIPTION
    "The X.25 Sub-address associated with the PU Entry for routing
     incoming call indications. Range: 0-99."
       ::= {pktSwchSnaPUX25QllcEntryS 9}

pktSwchSnaPUX25QllcAutoCallS OBJECT-TYPE
    SYNTAX  INTEGER {
	yes(1),
	no(2)
	}
    MAX-ACCESS  read-write
    STATUS  current
    DESCRIPTION
    "This parameter indicates whether the SPS automatically initiates
     an X.25 call request or not."
       ::= {pktSwchSnaPUX25QllcEntryS 10}

pktSwchSnaPUX25QllcCalledAddressS OBJECT-TYPE
    SYNTAX  OCTET STRING (SIZE (1..15))
    MAX-ACCESS  read-write
    STATUS  current
    DESCRIPTION
    "The destination x.25 DTE address to which the SPS calls. Used with
     AutoCall only."
       ::= {pktSwchSnaPUX25QllcEntryS 11}

pktSwchSnaPUX25QllcCallUserDataFacilitiesS OBJECT-TYPE
    SYNTAX  DisplayString (SIZE(1..60))
    MAX-ACCESS  read-write
    STATUS  current
    DESCRIPTION
    "The X.25 facilities and Call User Data which the SPS uses on
     outgoing calls. AutoCall only.
  Up to 60 Hexa-Decimal digits.
  Each pair of digits represents a BYTE.
  BYTE-0 BYTE-1 BYTE-2 ... BYTE-29 (30 Bytes maximum)

  BYTE-0 for X.25 Facilities. BYTE-1 to BYTE-29 for Call User Data.
  Facilities (BYTE-0) format: PW (Hexa-Decimal), where:
      X.25 L3 Packet Size Negotiation    : [P=1 YES] [P=0 NO].
      X.25 L3 Packet Window Negotiation  : [W=1 YES] [W=0 NO].
      Legal Values for Facilities BYTE-0 : 10, 01, 11, 00  (Hex).

    ATTENTION: a. Total number of digits in this field must be EVEN.
               b. To clear this field, enter blanks or 00."
       ::= {pktSwchSnaPUX25QllcEntryS 12}

pktSwchSnaPUX25QllcEntryStatusS OBJECT-TYPE
    SYNTAX  INTEGER {
       valid(1),
       underCreation(3)
     }
    MAX-ACCESS  read-write
    STATUS  current
    DESCRIPTION
    "The status of this PU Qllc table entry.
     In order to save this entry, set status to valid.
     An underCreation value is set by the Agent when this entry is updated."
         ::= {pktSwchSnaPUX25QllcEntryS 13}

pktSwchSnaPUX25QllcTableA    OBJECT-TYPE
    SYNTAX  SEQUENCE  OF PktSwchSnaPUX25QllcEntryA
    MAX-ACCESS  not-accessible
    STATUS  current
    DESCRIPTION
	"Defines links for PUs running on a QLLC link "
     ::=  { pktSwchSna 9 }

pktSwchSnaPUX25QllcEntryA OBJECT-TYPE
    SYNTAX  PktSwchSnaPUX25QllcEntryA
    MAX-ACCESS  not-accessible
    STATUS  current
    DESCRIPTION
	"Defines parameters for PU side running on an SDLC link "
    INDEX   {pktSwchSnaPUX25QllcNumberA , pktSwchSnaPUX25QllcSideA}
    ::=  { pktSwchSnaPUX25QllcTableA 1 }

PktSwchSnaPUX25QllcEntryA ::= SEQUENCE {
pktSwchSnaPUX25QllcNumberA
Integer32,
pktSwchSnaPUX25QllcSideA
INTEGER,
pktSwchSnaPUX25QllcIdBlkA
OCTET STRING,
pktSwchSnaPUX25QllcIdNumA
OCTET STRING,
pktSwchSnaPUX25QllcXIDInitA
INTEGER,
pktSwchSnaPUX25QllcMaxPiuSizeA
Integer32,
pktSwchSnaPUX25QllcStationAddressA
OCTET STRING,
pktSwchSnaPUX25QllcInPasswordA
DisplayString,
pktSwchSnaPUX25QllcSubAddressA
Integer32,
pktSwchSnaPUX25QllcAutoCallA
INTEGER,
pktSwchSnaPUX25QllcCalledAddressA
OCTET STRING,
pktSwchSnaPUX25QllcCallUserDataFacilitiesA
DisplayString
}

pktSwchSnaPUX25QllcNumberA OBJECT-TYPE
    SYNTAX  Integer32
    MAX-ACCESS  read-only
    STATUS  current
    DESCRIPTION
    "This parameter defines an identifier associated with the PU Entry
     X25\QLLC side, which is unique within the SPS"
	::= {pktSwchSnaPUX25QllcEntryA 1}

pktSwchSnaPUX25QllcSideA  OBJECT-TYPE
    SYNTAX  INTEGER {
	    sideA(1),
	    sideB(2)
	    }
    MAX-ACCESS  read-only
    STATUS  current
    DESCRIPTION
    "Is there side A or B of the PU connection "
	::= {pktSwchSnaPUX25QllcEntryA 2}

pktSwchSnaPUX25QllcIdBlkA OBJECT-TYPE
    SYNTAX  OCTET STRING (SIZE(1..2))
    MAX-ACCESS  read-only
    STATUS  current
    DESCRIPTION
"Part of the IBM device ID (the full ID is defined by the IDBLK and
 the IDNUM). The Idblk is required for secondary PU with Local XID
 handling.  Up to 3 Hexadecimal digits, format: 0X XX."
       ::= {pktSwchSnaPUX25QllcEntryA 3}

pktSwchSnaPUX25QllcIdNumA OBJECT-TYPE
    SYNTAX  OCTET STRING (SIZE(1..3))
    MAX-ACCESS  read-only
    STATUS  current
    DESCRIPTION
"Second part of the IBM device ID (the full ID is defined by the IDBLK and
 the IDNUM). The Idnum is required for secondary PU with Local XID
 handling.  Up to 5 Hexadecimal digits, format: 0X XX XX."
       ::= {pktSwchSnaPUX25QllcEntryA 4}

pktSwchSnaPUX25QllcXIDInitA OBJECT-TYPE
    SYNTAX  INTEGER {
	notInitiate(1),
	initiate(2)
	}
    MAX-ACCESS  read-only
    STATUS  current
    DESCRIPTION
 "This parameter is not applicable for PU with Local XID handling.
 Legal values:
 1 - Do not initiate an XID message.
 2 - Initiate an XID message to QLLC."
       ::= {pktSwchSnaPUX25QllcEntryA 5}

pktSwchSnaPUX25QllcMaxPiuSizeA OBJECT-TYPE
    SYNTAX Integer32 (137..7642)
    MAX-ACCESS  read-only
    STATUS  current
    DESCRIPTION
    "Maximum Path Information Size"
	::= { pktSwchSnaPUX25QllcEntryA 6}

pktSwchSnaPUX25QllcStationAddressA OBJECT-TYPE
    SYNTAX  OCTET STRING (SIZE(1))
    MAX-ACCESS  read-only
    STATUS  current
    DESCRIPTION
"QLLC PU Link Station Address. Range: 0x01-0xFE.
 This parameter is applicable only for PU with End-to-End XID handling,
 Support for NON-Activation XID."
       ::= {pktSwchSnaPUX25QllcEntryA 7}

pktSwchSnaPUX25QllcInPasswordA OBJECT-TYPE
    SYNTAX  DisplayString (SIZE(1..8))
    MAX-ACCESS  read-only
    STATUS  current
    DESCRIPTION
    "A field matched with the call user data in call request packets for
     purposes of security and correlation."
       ::= {pktSwchSnaPUX25QllcEntryA 8}

pktSwchSnaPUX25QllcSubAddressA OBJECT-TYPE
    SYNTAX  Integer32
    MAX-ACCESS  read-only
    STATUS  current
    DESCRIPTION
    "The X.25 Sub-address associated with the PU Entry for routing
     incoming call indications. Range: 0-99."
       ::= {pktSwchSnaPUX25QllcEntryA 9}

pktSwchSnaPUX25QllcAutoCallA OBJECT-TYPE
    SYNTAX  INTEGER{
	yes(1),
	no(2)
	}
    MAX-ACCESS  read-only
    STATUS  current
    DESCRIPTION
    "This parameter indicates whether the SPS automatically initiates
     an X.25 call request or not."
       ::= {pktSwchSnaPUX25QllcEntryA 10}

pktSwchSnaPUX25QllcCalledAddressA OBJECT-TYPE
    SYNTAX  OCTET STRING (SIZE (1..15))
    MAX-ACCESS  read-only
    STATUS  current
    DESCRIPTION
    "The destination x.25 DTE address to which the SPS calls. Used
     with AutoCall only."
       ::= {pktSwchSnaPUX25QllcEntryA 11}

pktSwchSnaPUX25QllcCallUserDataFacilitiesA OBJECT-TYPE
    SYNTAX  DisplayString (SIZE(1..60))
    MAX-ACCESS  read-only
    STATUS  current
    DESCRIPTION
    "The X.25 facilities and Call User Data which the SPS uses on
     outgoing calls. AutoCall only.
  Up to 60 Hexa-Decimal digits.
  Each pair of digits represents a BYTE.
  BYTE-0 BYTE-1 BYTE-2 ... BYTE-29 (30 Bytes maximum)

  BYTE-0 for X.25 Facilities. BYTE-1 to BYTE-29 for Call User Data.
  Facilities (BYTE-0) format: PW (Hexa-Decimal), where:
      X.25 L3 Packet Size Negotiation    : [P=1 YES] [P=0 NO].
      X.25 L3 Packet Window Negotiation  : [W=1 YES] [W=0 NO].
      Legal Values for Facilities BYTE-0 : 10, 01, 11, 00  (Hex).

    ATTENTION: a. Total number of digits in this field must be EVEN.
               b. To clear this field, enter blanks or 00."
       ::= {pktSwchSnaPUX25QllcEntryA 12}



pktSwchSnaPUX25QllcStatTable    OBJECT-TYPE
    SYNTAX  SEQUENCE  OF PktSwchSnaPUX25QllcStatEntry
    MAX-ACCESS  not-accessible
    STATUS  current
    DESCRIPTION
	"Shows link statistics for PUs running on a QLLC link "
     ::=  { pktSwchSna 10 }

pktSwchSnaPUX25QllcStatEntry OBJECT-TYPE
    SYNTAX  PktSwchSnaPUX25QllcStatEntry
    MAX-ACCESS  not-accessible
    STATUS  current
    DESCRIPTION
	"Shows link statistics for PUs running on a QLLC link "
    INDEX   {pktSwchSnaPUX25QllcStatNumber , pktSwchSnaPUX25QllcStatSide}
    ::=  { pktSwchSnaPUX25QllcStatTable 1 }

PktSwchSnaPUX25QllcStatEntry ::= SEQUENCE {
pktSwchSnaPUX25QllcStatNumber
Integer32,
pktSwchSnaPUX25QllcStatSide
INTEGER,
pktSwchSnaPUX25QllcStatlink
Integer32,
pktSwchSnaPUX25QllcStatDataPacketsIn
Counter32,
pktSwchSnaPUX25QllcStatDataPacketsOut
Counter32,
pktSwchSnaPUX25QllcStatQSMPacketsIn
Counter32,
pktSwchSnaPUX25QllcStatQSMPacketsOut
Counter32,
pktSwchSnaPUX25QllcStatQDMPacketsIn
Counter32,
pktSwchSnaPUX25QllcStatQDMPacketsOut
Counter32,
pktSwchSnaPUX25QllcStatXIDPacketsIn
Counter32,
pktSwchSnaPUX25QllcStatXIDPacketsOut
Counter32,
pktSwchSnaPUX25QllcStatQDISCPacketsIn
Counter32,
pktSwchSnaPUX25QllcStatQDISCPacketsOut
Counter32,
pktSwchSnaPUX25QllcStatCallPacketsIn
Counter32,
pktSwchSnaPUX25QllcStatCallPacketsOut
Counter32,
pktSwchSnaPUX25QllcStatClearPacketsIn
Counter32,
pktSwchSnaPUX25QllcStatClearPacketsOut
Counter32,
pktSwchSnaPUX25QllcStatCallAcceptsIn
Counter32,
pktSwchSnaPUX25QllcStatCallAcceptsOut
Counter32,
pktSwchSnaPUX25QllcStatUpperState
INTEGER,
pktSwchSnaPUX25QllcStatLowerState
INTEGER,
pktSwchSnaPUX25QllcStatNRMStatus
INTEGER,
pktSwchSnaPUX25QllcStatFlowCtlStatus
INTEGER
}

pktSwchSnaPUX25QllcStatNumber OBJECT-TYPE
    SYNTAX  Integer32
    MAX-ACCESS  read-only
    STATUS  current
    DESCRIPTION
    "This parameter defines an identifier associated with the PU Entry
     X25\QLLC side, which is unique within the SPS"
	::= {pktSwchSnaPUX25QllcStatEntry 1}

pktSwchSnaPUX25QllcStatSide  OBJECT-TYPE
    SYNTAX  INTEGER {
	    sideA(1),
	    sideB(2)
	    }
    MAX-ACCESS  read-only
    STATUS  current
    DESCRIPTION
    "Is there side A or B of the PU connection "
	::= {pktSwchSnaPUX25QllcStatEntry 2}

pktSwchSnaPUX25QllcStatlink OBJECT-TYPE
    SYNTAX  Integer32
    MAX-ACCESS  read-only
    STATUS  current
    DESCRIPTION
    "The Link on which the Qllc conversation is conducted. If there is
     no conversation the variable will be 0."
       ::= {pktSwchSnaPUX25QllcStatEntry 3}

pktSwchSnaPUX25QllcStatDataPacketsIn OBJECT-TYPE
 SYNTAX Counter32
 MAX-ACCESS  read-only
 STATUS  current
 DESCRIPTION
    ""
	::= { pktSwchSnaPUX25QllcStatEntry 4 }

pktSwchSnaPUX25QllcStatDataPacketsOut OBJECT-TYPE
 SYNTAX Counter32
 MAX-ACCESS  read-only
 STATUS  current
 DESCRIPTION
    ""
	::= { pktSwchSnaPUX25QllcStatEntry 5 }

pktSwchSnaPUX25QllcStatQSMPacketsIn OBJECT-TYPE
 SYNTAX Counter32
 MAX-ACCESS  read-only
 STATUS  current
 DESCRIPTION
    ""
	::= { pktSwchSnaPUX25QllcStatEntry 6 }

pktSwchSnaPUX25QllcStatQSMPacketsOut OBJECT-TYPE
 SYNTAX Counter32
 MAX-ACCESS  read-only
 STATUS  current
 DESCRIPTION
    ""
	::= { pktSwchSnaPUX25QllcStatEntry 7 }

pktSwchSnaPUX25QllcStatQDMPacketsIn OBJECT-TYPE
 SYNTAX Counter32
 MAX-ACCESS  read-only
 STATUS  current
 DESCRIPTION
    ""
	::= { pktSwchSnaPUX25QllcStatEntry 8 }

pktSwchSnaPUX25QllcStatQDMPacketsOut OBJECT-TYPE
 SYNTAX Counter32
 MAX-ACCESS  read-only
 STATUS  current
 DESCRIPTION
    ""
	::= { pktSwchSnaPUX25QllcStatEntry 9 }

pktSwchSnaPUX25QllcStatXIDPacketsIn OBJECT-TYPE
 SYNTAX Counter32
 MAX-ACCESS  read-only
 STATUS  current
 DESCRIPTION
    ""
	::= { pktSwchSnaPUX25QllcStatEntry 10 }

pktSwchSnaPUX25QllcStatXIDPacketsOut OBJECT-TYPE
 SYNTAX Counter32
 MAX-ACCESS  read-only
 STATUS  current
 DESCRIPTION
    ""
	::= { pktSwchSnaPUX25QllcStatEntry 11 }

pktSwchSnaPUX25QllcStatQDISCPacketsIn OBJECT-TYPE
 SYNTAX Counter32
 MAX-ACCESS  read-only
 STATUS  current
 DESCRIPTION
    ""
	::= { pktSwchSnaPUX25QllcStatEntry 12 }

pktSwchSnaPUX25QllcStatQDISCPacketsOut OBJECT-TYPE
 SYNTAX Counter32
 MAX-ACCESS  read-only
 STATUS  current
 DESCRIPTION
    ""
	::= { pktSwchSnaPUX25QllcStatEntry 13 }

pktSwchSnaPUX25QllcStatCallPacketsIn OBJECT-TYPE
 SYNTAX Counter32
 MAX-ACCESS  read-only
 STATUS  current
 DESCRIPTION
    ""
	::= { pktSwchSnaPUX25QllcStatEntry 14 }

pktSwchSnaPUX25QllcStatCallPacketsOut OBJECT-TYPE
 SYNTAX Counter32
 MAX-ACCESS  read-only
 STATUS  current
 DESCRIPTION
    ""
	::= { pktSwchSnaPUX25QllcStatEntry 15 }

pktSwchSnaPUX25QllcStatClearPacketsIn OBJECT-TYPE
 SYNTAX Counter32
 MAX-ACCESS  read-only
 STATUS  current
 DESCRIPTION
    ""
	::= { pktSwchSnaPUX25QllcStatEntry 16 }

pktSwchSnaPUX25QllcStatClearPacketsOut OBJECT-TYPE
 SYNTAX Counter32
 MAX-ACCESS  read-only
 STATUS  current
 DESCRIPTION
    ""
	::= { pktSwchSnaPUX25QllcStatEntry 17 }

pktSwchSnaPUX25QllcStatCallAcceptsIn OBJECT-TYPE
 SYNTAX Counter32
 MAX-ACCESS  read-only
 STATUS  current
 DESCRIPTION
    ""
	::= { pktSwchSnaPUX25QllcStatEntry 18 }

pktSwchSnaPUX25QllcStatCallAcceptsOut OBJECT-TYPE
 SYNTAX Counter32
 MAX-ACCESS  read-only
 STATUS  current
 DESCRIPTION
    ""
	::= { pktSwchSnaPUX25QllcStatEntry 19 }

pktSwchSnaPUX25QllcStatUpperState OBJECT-TYPE
 SYNTAX INTEGER {
    unbound(1),
    bindPending(2),
    unbindPend(3),
    idle(4),
    unattached(5),
    attachPend(6),
    detachPend(7),
    udqosPending(8),
    outconPend(9),
    inconPending(10),
    connResPend(11),
    dataxfer(12),
    userResetPend(13),
    provRstPend(14),
    rstResPend(15),
    discon8Pend(16),
    discon9Pend(17),
    discon11Pend(18),
    discon12Pend(19),
    discon13Pend(20),
    subsBindPnd(21),
    noChange(22)
   }
 MAX-ACCESS read-only
 STATUS current
 DESCRIPTION
    "The internal DLPI state of the connection."
	::= { pktSwchSnaPUX25QllcStatEntry 20 }

pktSwchSnaPUX25QllcStatLowerState OBJECT-TYPE
 SYNTAX INTEGER {
    linkClosed(1),
    disconnected(2),
    linkOpening(3),
    disconnecting(4),
    frmrSent(5),
    linkOpened(6),
    localBusy(7),
    rejection(8),
    checkpointing(9),
    cpLocalBusy(10),
    cpRejection(11),
    resetting(12),
    remoteBusy(13),
    lBusyRBusy(14),
    rejLBusy(15),
    rejRBusy(16),
    cpRejLBusy(17),
    cpClearing(18),
    cpRejClr(19),
    rejLbusyRbusy(20),
    frmrReceived(21),
    programError(22),
    noChange(23)
	}
 MAX-ACCESS read-only
 STATUS current
 DESCRIPTION
    "The internal QLLC state of the connection."
	::= { pktSwchSnaPUX25QllcStatEntry 21 }

pktSwchSnaPUX25QllcStatNRMStatus OBJECT-TYPE
 SYNTAX INTEGER	 {sync(1),notSync(2)}
 MAX-ACCESS  read-only
 STATUS  current
 DESCRIPTION
    "This variable indicates if the link is in Normal Response Mode or not."
	::= { pktSwchSnaPUX25QllcStatEntry 22 }

pktSwchSnaPUX25QllcStatFlowCtlStatus OBJECT-TYPE
 SYNTAX INTEGER	 {noRNR(1),txFlow(2), rxFlow(3), rxAndTx(4)}
 MAX-ACCESS  read-only
 STATUS  current
 DESCRIPTION
    "This variable indicates the flow control status of the PU interface."
	::= { pktSwchSnaPUX25QllcStatEntry 23 }


pktSwchSnaPULlc2FrTableS    OBJECT-TYPE
    SYNTAX  SEQUENCE  OF PktSwchSnaPULlc2FrEntryS
    MAX-ACCESS  not-accessible
    STATUS  current
    DESCRIPTION
	"Defines LLC2/Frame Relay/RFC1490 Protocol Interface of SPS SNA PU entity. "
     ::=  { pktSwchSna 11 }

pktSwchSnaPULlc2FrEntryS OBJECT-TYPE
    SYNTAX  PktSwchSnaPULlc2FrEntryS
    MAX-ACCESS  not-accessible
    STATUS  current
    DESCRIPTION
	"Defines parameters for PU LLC2 Protocol Interface over Frame Relay Protocol using RFC 1490."
    INDEX   {pktSwchSnaPULlc2FrNumberS , pktSwchSnaPULlc2FrSideS}
    ::=  { pktSwchSnaPULlc2FrTableS 1 }

PktSwchSnaPULlc2FrEntryS ::= SEQUENCE {
pktSwchSnaPULlc2FrNumberS
Integer32,
pktSwchSnaPULlc2FrSideS
INTEGER,
pktSwchSnaPULlc2FrEncapsTypeS
INTEGER,
pktSwchSnaPULlc2FrDestMACS
OCTET STRING,
pktSwchSnaPULlc2FrSrcSAPS
OCTET STRING,
pktSwchSnaPULlc2FrDestSAPS
OCTET STRING,
pktSwchSnaPULlc2FrXIDIdBlkS
OCTET STRING,
pktSwchSnaPULlc2FrXIDIdNumS
OCTET STRING,
pktSwchSnaPULlc2FrMaxPiuSizeS
Integer32,
pktSwchSnaPULlc2FrTxWindowS
Integer32,
pktSwchSnaPULlc2FrLinkS
Integer32,
pktSwchSnaPULlc2FrDLCIS
Integer32,
pktSwchSnaPULlc2FrXIDInitiationS
INTEGER,
pktSwchSnaPULlc2FrN2CountS
Integer32,
pktSwchSnaPULlc2FrT1TimerS
Integer32,
pktSwchSnaPULlc2FrTiTimerS
Integer32,
pktSwchSnaPULlc2FrEntryStatusS
INTEGER
}

pktSwchSnaPULlc2FrNumberS OBJECT-TYPE
    SYNTAX Integer32
    MAX-ACCESS  read-only
    STATUS  current
    DESCRIPTION
    "Unique Identifier for this PU. The value in this field is used as a common Key in both this table and the Main PU table. "
    ::= {pktSwchSnaPULlc2FrEntryS 1 }

pktSwchSnaPULlc2FrSideS OBJECT-TYPE
    SYNTAX INTEGER {
	    sideA(1),
	    sideB(2)
	    }
    MAX-ACCESS  read-only
    STATUS  current
    DESCRIPTION
    "Indicates for each side (SIDE-A and SIDE-B) if the Protocol Interface for that side has been defined or not. "
    ::= {pktSwchSnaPULlc2FrEntryS 2}

pktSwchSnaPULlc2FrEncapsTypeS OBJECT-TYPE
    SYNTAX INTEGER	 {ban(1),bnn(2),tren(3)}
    MAX-ACCESS  read-write
    STATUS  current
    DESCRIPTION
"Indicates if the LLC2/RFC1490 Protocol Interface uses the BNN, BAN
 or TREN method of Frame Encapsulation."
    ::= {pktSwchSnaPULlc2FrEntryS 3}

pktSwchSnaPULlc2FrDestMACS OBJECT-TYPE
    SYNTAX OCTET STRING (SIZE(6))
    MAX-ACCESS  read-write
    STATUS  current
    DESCRIPTION
"The LLC2 Destination MAC Address."
    ::= {pktSwchSnaPULlc2FrEntryS 4}

pktSwchSnaPULlc2FrSrcSAPS OBJECT-TYPE
    SYNTAX OCTET STRING (SIZE(1))
    MAX-ACCESS  read-write
    STATUS  current
    DESCRIPTION
"The LLC2 Source SAP Address. 2 Hex digits"
::= {pktSwchSnaPULlc2FrEntryS 5}

pktSwchSnaPULlc2FrDestSAPS OBJECT-TYPE
    SYNTAX OCTET STRING (SIZE(1))
    MAX-ACCESS  read-write
    STATUS  current
    DESCRIPTION
"The LLC2 Destination SAP."
    ::= {pktSwchSnaPULlc2FrEntryS 6}

pktSwchSnaPULlc2FrXIDIdBlkS OBJECT-TYPE
    SYNTAX OCTET STRING (SIZE(1..2))
    MAX-ACCESS  read-write
    STATUS  current
    DESCRIPTION
"Part of the IBM device ID (the full ID is defined by the IDBLK and
 the IDNUM). The IDBLK is required for PU with Local XID handling
 or PU with End-to-End XID handling, NO Support for NON-Activation XID.
 Up to 3 Hexadecimal digits, format: 0X XX."
    ::= {pktSwchSnaPULlc2FrEntryS 7}

pktSwchSnaPULlc2FrXIDIdNumS OBJECT-TYPE
    SYNTAX OCTET STRING (SIZE(1..3))
    MAX-ACCESS  read-write
    STATUS  current
    DESCRIPTION
"Second part of the IBM device ID (the full ID is defined by the IDBLK and
 the IDNUM). The IDNUM is required for PU with Local XID handling
 or PU with End-to-End XID handling, NO Support for NON-Activation XID.
 Up to 5 Hexadecimal digits, format: 0X XX XX."
::= {pktSwchSnaPULlc2FrEntryS 8}

pktSwchSnaPULlc2FrMaxPiuSizeS OBJECT-TYPE
    SYNTAX Integer32 (137..7642)
    MAX-ACCESS  read-write
    STATUS  current
    DESCRIPTION
    "Maximum Path Information Size"
	::= { pktSwchSnaPULlc2FrEntryS 9}

pktSwchSnaPULlc2FrTxWindowS OBJECT-TYPE
    SYNTAX Integer32
    MAX-ACCESS  read-write
    STATUS  current
    DESCRIPTION
"The LLC2 Link Window Size."
    ::= {pktSwchSnaPULlc2FrEntryS 10}

pktSwchSnaPULlc2FrLinkS OBJECT-TYPE
    SYNTAX Integer32
    MAX-ACCESS  read-write
    STATUS  current
    DESCRIPTION
"The SPS Frame Relay Link Number which this LLC2 Protocol Interface is associated with."
    ::= {pktSwchSnaPULlc2FrEntryS 11}

pktSwchSnaPULlc2FrDLCIS OBJECT-TYPE
    SYNTAX Integer32
    MAX-ACCESS  read-write
    STATUS  current
    DESCRIPTION
"The SPS Frame Relay DLCI Number which this LLC2 Protocol Interface is associated with."
    ::= {pktSwchSnaPULlc2FrEntryS 12}

pktSwchSnaPULlc2FrXIDInitiationS OBJECT-TYPE
    SYNTAX  INTEGER{
	notInitiate(1),
	initiate(2)
	}
    MAX-ACCESS  read-write
    STATUS  current
    DESCRIPTION
 "This parameter is not applicable for PU with Local XID handling.
 Legal values:
 1 - Do not initiate an XID message.
 2 - Initiate an XID message to LLC2."
	::= { pktSwchSnaPULlc2FrEntryS 13}

pktSwchSnaPULlc2FrN2CountS OBJECT-TYPE
    SYNTAX  Integer32 (1..99999)
    MAX-ACCESS  read-write
    STATUS  current
    DESCRIPTION
    "N2 Count"
	::= { pktSwchSnaPULlc2FrEntryS 14}

pktSwchSnaPULlc2FrT1TimerS OBJECT-TYPE
    SYNTAX  Integer32  (1..99999)
    MAX-ACCESS  read-write
    STATUS  current
    DESCRIPTION
    "T1 Timer in 1/10 of a second."
	::= { pktSwchSnaPULlc2FrEntryS 15}

pktSwchSnaPULlc2FrTiTimerS OBJECT-TYPE
    SYNTAX  Integer32  (1..99999)
    MAX-ACCESS  read-write
    STATUS  current
    DESCRIPTION
    "TI Timer in seconds"
	::= { pktSwchSnaPULlc2FrEntryS 16}

pktSwchSnaPULlc2FrEntryStatusS OBJECT-TYPE
    SYNTAX  INTEGER {
       valid(1),
       underCreation(3)
     }
    MAX-ACCESS  read-write
    STATUS  current
    DESCRIPTION
    "The status of this PU Llc2 table entry.
     In order to save this entry, set status to valid.
     An underCreation value is set by the Agent when this entry is updated."
         ::= {pktSwchSnaPULlc2FrEntryS 17}


pktSwchSnaPULlc2FrTableA    OBJECT-TYPE
    SYNTAX  SEQUENCE  OF PktSwchSnaPULlc2FrEntryA
    MAX-ACCESS  not-accessible
    STATUS  current
    DESCRIPTION
	"Defines links for PUs running on an LLC2 link "
     ::=  { pktSwchSna 12 }

pktSwchSnaPULlc2FrEntryA OBJECT-TYPE
    SYNTAX  PktSwchSnaPULlc2FrEntryA
    MAX-ACCESS  not-accessible
    STATUS  current
    DESCRIPTION
	"Defines parameters for PU LLC2 Protocol Interface over Frame Relay Protocol using RFC 1490."
    INDEX   {pktSwchSnaPULlc2FrNumberA , pktSwchSnaPULlc2FrSideA}
    ::=  { pktSwchSnaPULlc2FrTableA 1 }

PktSwchSnaPULlc2FrEntryA ::= SEQUENCE {
pktSwchSnaPULlc2FrNumberA
Integer32,
pktSwchSnaPULlc2FrSideA
INTEGER,
pktSwchSnaPULlc2FrEncapsTypeA
INTEGER,
pktSwchSnaPULlc2FrDestMACA
OCTET STRING,
pktSwchSnaPULlc2FrSrcSAPA
OCTET STRING,
pktSwchSnaPULlc2FrDestSAPA
OCTET STRING,
pktSwchSnaPULlc2FrXIDIdBlkA
OCTET STRING,
pktSwchSnaPULlc2FrXIDIdNumA
OCTET STRING,
pktSwchSnaPULlc2FrMaxPiuSizeA
Integer32,
pktSwchSnaPULlc2FrTxWindowA
Integer32,
pktSwchSnaPULlc2FrLinkA
Integer32,
pktSwchSnaPULlc2FrDLCIA
Integer32,
pktSwchSnaPULlc2FrXIDInitiationA
INTEGER,
pktSwchSnaPULlc2FrN2CountA
Integer32,
pktSwchSnaPULlc2FrT1TimerA
Integer32,
pktSwchSnaPULlc2FrTiTimerA
Integer32
}
pktSwchSnaPULlc2FrNumberA OBJECT-TYPE
    SYNTAX Integer32
    MAX-ACCESS  read-only
    STATUS  current
    DESCRIPTION
"Unique Identifier for this PU. The value in this field is used as a common Key in both this table and the Main PU table. "
    ::= {pktSwchSnaPULlc2FrEntryA 1 }

pktSwchSnaPULlc2FrSideA OBJECT-TYPE
    SYNTAX INTEGER {
	    sideA(1),
	    sideB(2)
	    }
    MAX-ACCESS  read-only
    STATUS  current
    DESCRIPTION
"Indicates for each side (SIDE-A and SIDE-B) if the Protocol Interface for that side has been defined or not. "
    ::= {pktSwchSnaPULlc2FrEntryA 2}

pktSwchSnaPULlc2FrEncapsTypeA OBJECT-TYPE
    SYNTAX INTEGER	 {ban(1),bnn(2),tren(3)}
    MAX-ACCESS  read-only
    STATUS  current
    DESCRIPTION
"Indicates if the LLC2/RFC1490 Protocol Interface uses the BNN, BAN
 or TREN method of Frame Encapsulation."
    ::= {pktSwchSnaPULlc2FrEntryA 3}

pktSwchSnaPULlc2FrDestMACA OBJECT-TYPE
    SYNTAX OCTET STRING (SIZE(6))
    MAX-ACCESS  read-only
    STATUS  current
    DESCRIPTION
"The LLC2 Destination MAC Address."
    ::= {pktSwchSnaPULlc2FrEntryA 4}

pktSwchSnaPULlc2FrSrcSAPA OBJECT-TYPE
    SYNTAX OCTET STRING (SIZE(1))
    MAX-ACCESS  read-only
    STATUS  current
    DESCRIPTION
"The LLC2 Source SAP Address."
    ::= {pktSwchSnaPULlc2FrEntryA 5}

pktSwchSnaPULlc2FrDestSAPA OBJECT-TYPE
    SYNTAX OCTET STRING (SIZE(1))
    MAX-ACCESS  read-only
    STATUS  current
    DESCRIPTION
"The LLC2 Destination SAP."
    ::= {pktSwchSnaPULlc2FrEntryA 6}

pktSwchSnaPULlc2FrXIDIdBlkA OBJECT-TYPE
    SYNTAX OCTET STRING (SIZE(1..2))
    MAX-ACCESS  read-only
    STATUS  current
    DESCRIPTION
"Part of the IBM device ID (the full ID is defined by the IDBLK and
 the IDNUM). The IDBLK is required for PU with Local XID handling
 or PU with End-to-End XID handling, NO Support for NON-Activation XID.
 Up to 3 Hexadecimal digits, format: 0X XX."
    ::= {pktSwchSnaPULlc2FrEntryA 7}

pktSwchSnaPULlc2FrXIDIdNumA OBJECT-TYPE
    SYNTAX OCTET STRING (SIZE(1..3))
    MAX-ACCESS  read-only
    STATUS  current
    DESCRIPTION
"Second part of the IBM device ID (the full ID is defined by the IDBLK and
 the IDNUM). The IDNUM is required for PU with Local XID handling
 or PU with End-to-End XID handling, NO Support for NON-Activation XID.
 Up to 5 Hexadecimal digits, format: 0X XX XX."
    ::= {pktSwchSnaPULlc2FrEntryA 8}

pktSwchSnaPULlc2FrMaxPiuSizeA OBJECT-TYPE
    SYNTAX Integer32 (137..7642)
    MAX-ACCESS  read-only
    STATUS  current
    DESCRIPTION
    "Maximum Path Information Size"
	::= {pktSwchSnaPULlc2FrEntryA 9}

pktSwchSnaPULlc2FrTxWindowA OBJECT-TYPE
    SYNTAX Integer32
    MAX-ACCESS  read-only
    STATUS  current
    DESCRIPTION
"The LLC2 Link Window Size."
    ::= {pktSwchSnaPULlc2FrEntryA 10}

pktSwchSnaPULlc2FrLinkA OBJECT-TYPE
    SYNTAX Integer32
    MAX-ACCESS  read-only
    STATUS  current
    DESCRIPTION
"The SPS Frame Relay Link Number which this LLC2 Protocol Interface is associated with."
    ::= {pktSwchSnaPULlc2FrEntryA 11}

pktSwchSnaPULlc2FrDLCIA OBJECT-TYPE
    SYNTAX Integer32
    MAX-ACCESS  read-only
    STATUS  current
    DESCRIPTION
"The SPS Frame Relay DLCI Number which this LLC2 Protocol Interface is associated with."
    ::= {pktSwchSnaPULlc2FrEntryA 12}

pktSwchSnaPULlc2FrXIDInitiationA OBJECT-TYPE
    SYNTAX  INTEGER{
	notInitiate(1),
	initiate(2)
	}
    MAX-ACCESS  read-only
    STATUS  current
    DESCRIPTION
 "This parameter is not applicable for PU with Local XID handling.
 Legal values:
 1 - Do not initiate an XID message.
 2 - Initiate an XID message to LLC2."
	::= { pktSwchSnaPULlc2FrEntryA 13}

pktSwchSnaPULlc2FrN2CountA OBJECT-TYPE
    SYNTAX  Integer32 (1..99999)
    MAX-ACCESS  read-only
    STATUS  current
    DESCRIPTION
    "N2 Count"
	::= { pktSwchSnaPULlc2FrEntryA 14}

pktSwchSnaPULlc2FrT1TimerA OBJECT-TYPE
    SYNTAX  Integer32  (1..99999)
    MAX-ACCESS  read-only
    STATUS  current
    DESCRIPTION
    "T1 Timer in 1/10 of a second."
	::= { pktSwchSnaPULlc2FrEntryA 15}

pktSwchSnaPULlc2FrTiTimerA OBJECT-TYPE
    SYNTAX  Integer32  (1..99999)
    MAX-ACCESS  read-only
    STATUS  current
    DESCRIPTION
    "TI Timer in seconds"
	::= { pktSwchSnaPULlc2FrEntryA 16}


pktSwchSnaPULlc2FrStatTable   OBJECT-TYPE
    SYNTAX  SEQUENCE  OF PktSwchSnaPULlc2FrStatEntry
    MAX-ACCESS  not-accessible
    STATUS  current
    DESCRIPTION
	"Shows link statistics for PUs running on an LLC2 link "
     ::=  { pktSwchSna 13 }

pktSwchSnaPULlc2FrStatEntry OBJECT-TYPE
    SYNTAX  PktSwchSnaPULlc2FrStatEntry
    MAX-ACCESS  not-accessible
    STATUS  current
    DESCRIPTION
	"Shows statistics for PU LLC2 Protocol Interface over Frame Relay Protocol using RFC 1490."
    INDEX   {pktSwchSnaPULlc2FrStatNumber ,
             pktSwchSnaPULlc2FrStatSide} ::= { pktSwchSnaPULlc2FrStatTable 1 }

PktSwchSnaPULlc2FrStatEntry ::= SEQUENCE {
pktSwchSnaPULlc2FrStatNumber
Integer32,
pktSwchSnaPULlc2FrStatSide
INTEGER,
pktSwchSnaPULlc2FrStatOctetsIn
Counter32,
pktSwchSnaPULlc2FrStatOctetsOut
Counter32,
pktSwchSnaPULlc2FrStatIFramesIn
Counter32,
pktSwchSnaPULlc2FrStatIFramesOut
Counter32,
pktSwchSnaPULlc2FrStatRRFramesIn
Counter32,
pktSwchSnaPULlc2FrStatRRFramesOut
Counter32,
pktSwchSnaPULlc2FrStatRNRFramesIn
Counter32,
pktSwchSnaPULlc2FrStatRNRFramesOut
Counter32,
pktSwchSnaPULlc2FrStatXIDsIn
Counter32,
pktSwchSnaPULlc2FrStatXIDsOut
Counter32,
pktSwchSnaPULlc2FrStatTESTsIn
Counter32,
pktSwchSnaPULlc2FrStatTESTsOut
Counter32,
pktSwchSnaPULlc2FrStatREJsIn
Counter32,
pktSwchSnaPULlc2FrStatREJsOut
Counter32,
pktSwchSnaPULlc2FrStatFRMRsIn
Counter32,
pktSwchSnaPULlc2FrStatFRMRsOut
Counter32,
pktSwchSnaPULlc2FrStatDISCsIn
Counter32,
pktSwchSnaPULlc2FrStatDISCsOut
Counter32,
pktSwchSnaPULlc2FrStatUAsIn
Counter32,
pktSwchSnaPULlc2FrStatUAsOut
Counter32,
pktSwchSnaPULlc2FrStatDMsIn
Counter32,
pktSwchSnaPULlc2FrStatDMsOut
Counter32,
pktSwchSnaPULlc2FrStatSABMEsIn
Counter32,
pktSwchSnaPULlc2FrStatSABMEsOut
Counter32,
pktSwchSnaPULlc2FrStatRetransmitsIn
Counter32,
pktSwchSnaPULlc2FrStatRetransmitsOut
Counter32,
pktSwchSnaPULlc2FrStatUpperState
INTEGER,
pktSwchSnaPULlc2FrStatLowerState
INTEGER,
pktSwchSnaPULlc2FrStatNRMStatus
INTEGER,
pktSwchSnaPULlc2FrStatFlowCtlStatus
INTEGER
}
pktSwchSnaPULlc2FrStatNumber OBJECT-TYPE
    SYNTAX Integer32
    MAX-ACCESS  read-only
    STATUS  current
    DESCRIPTION
"Unique Identifier for this PU. The value in this field is used as a common Key in both this table and the Main PU table. "
    ::= {pktSwchSnaPULlc2FrStatEntry 1 }

pktSwchSnaPULlc2FrStatSide OBJECT-TYPE
    SYNTAX INTEGER {
	    sideA(1),
	    sideB(2)
	    }
    MAX-ACCESS  read-only
    STATUS  current
    DESCRIPTION
"Indicates for each side (SIDE-A and SIDE-B) if the Protocol Interface for that side has been defined or not. "
    ::= {pktSwchSnaPULlc2FrStatEntry 2}

pktSwchSnaPULlc2FrStatOctetsIn OBJECT-TYPE
 SYNTAX Counter32
 MAX-ACCESS  read-only
 STATUS  current
 DESCRIPTION
    ""
	::= { pktSwchSnaPULlc2FrStatEntry 3}

pktSwchSnaPULlc2FrStatOctetsOut OBJECT-TYPE
 SYNTAX Counter32
 MAX-ACCESS  read-only
 STATUS  current
 DESCRIPTION
    ""
	::= { pktSwchSnaPULlc2FrStatEntry 4}

pktSwchSnaPULlc2FrStatIFramesIn OBJECT-TYPE
 SYNTAX Counter32
 MAX-ACCESS  read-only
 STATUS  current
 DESCRIPTION
    ""
	::= { pktSwchSnaPULlc2FrStatEntry 5}

pktSwchSnaPULlc2FrStatIFramesOut OBJECT-TYPE
 SYNTAX Counter32
 MAX-ACCESS  read-only
 STATUS  current
 DESCRIPTION
    ""
	::= { pktSwchSnaPULlc2FrStatEntry 6}

pktSwchSnaPULlc2FrStatRRFramesIn OBJECT-TYPE
 SYNTAX Counter32
 MAX-ACCESS  read-only
 STATUS  current
 DESCRIPTION
    ""
	::= { pktSwchSnaPULlc2FrStatEntry 7}

pktSwchSnaPULlc2FrStatRRFramesOut OBJECT-TYPE
 SYNTAX Counter32
 MAX-ACCESS  read-only
 STATUS  current
 DESCRIPTION
    ""
	::= { pktSwchSnaPULlc2FrStatEntry 8}

pktSwchSnaPULlc2FrStatRNRFramesIn OBJECT-TYPE
 SYNTAX Counter32
 MAX-ACCESS  read-only
 STATUS  current
 DESCRIPTION
    ""
	::= { pktSwchSnaPULlc2FrStatEntry 9}

pktSwchSnaPULlc2FrStatRNRFramesOut OBJECT-TYPE
 SYNTAX Counter32
 MAX-ACCESS  read-only
 STATUS  current
 DESCRIPTION
    ""
	::= { pktSwchSnaPULlc2FrStatEntry 10}

pktSwchSnaPULlc2FrStatXIDsIn OBJECT-TYPE
 SYNTAX Counter32
 MAX-ACCESS  read-only
 STATUS  current
 DESCRIPTION
    ""
	::= { pktSwchSnaPULlc2FrStatEntry 11}

pktSwchSnaPULlc2FrStatXIDsOut OBJECT-TYPE
 SYNTAX Counter32
 MAX-ACCESS  read-only
 STATUS  current
 DESCRIPTION
    ""
	::= { pktSwchSnaPULlc2FrStatEntry 12}

pktSwchSnaPULlc2FrStatTESTsIn OBJECT-TYPE
 SYNTAX Counter32
 MAX-ACCESS  read-only
 STATUS  current
 DESCRIPTION
    ""
	::= { pktSwchSnaPULlc2FrStatEntry 13}

pktSwchSnaPULlc2FrStatTESTsOut OBJECT-TYPE
 SYNTAX Counter32
 MAX-ACCESS  read-only
 STATUS  current
 DESCRIPTION
    ""
	::= { pktSwchSnaPULlc2FrStatEntry 14}

pktSwchSnaPULlc2FrStatREJsIn OBJECT-TYPE
 SYNTAX Counter32
 MAX-ACCESS  read-only
 STATUS  current
 DESCRIPTION
    ""
	::= { pktSwchSnaPULlc2FrStatEntry 15}

pktSwchSnaPULlc2FrStatREJsOut OBJECT-TYPE
 SYNTAX Counter32
 MAX-ACCESS  read-only
 STATUS  current
 DESCRIPTION
    ""
	::= { pktSwchSnaPULlc2FrStatEntry 16}

pktSwchSnaPULlc2FrStatFRMRsIn OBJECT-TYPE
 SYNTAX Counter32
 MAX-ACCESS  read-only
 STATUS  current
 DESCRIPTION
    ""
	::= { pktSwchSnaPULlc2FrStatEntry 17}

pktSwchSnaPULlc2FrStatFRMRsOut OBJECT-TYPE
 SYNTAX Counter32
 MAX-ACCESS  read-only
 STATUS  current
 DESCRIPTION
    ""
	::= { pktSwchSnaPULlc2FrStatEntry 18}

pktSwchSnaPULlc2FrStatDISCsIn OBJECT-TYPE
 SYNTAX Counter32
 MAX-ACCESS  read-only
 STATUS  current
 DESCRIPTION
    ""
	::= { pktSwchSnaPULlc2FrStatEntry 19}

pktSwchSnaPULlc2FrStatDISCsOut OBJECT-TYPE
 SYNTAX Counter32
 MAX-ACCESS  read-only
 STATUS  current
 DESCRIPTION
    ""
	::= { pktSwchSnaPULlc2FrStatEntry 20}

pktSwchSnaPULlc2FrStatUAsIn OBJECT-TYPE
 SYNTAX Counter32
 MAX-ACCESS  read-only
 STATUS  current
 DESCRIPTION
    ""
	::= { pktSwchSnaPULlc2FrStatEntry 21}

pktSwchSnaPULlc2FrStatUAsOut OBJECT-TYPE
 SYNTAX Counter32
 MAX-ACCESS  read-only
 STATUS  current
 DESCRIPTION
    ""
	::= { pktSwchSnaPULlc2FrStatEntry 22}

pktSwchSnaPULlc2FrStatDMsIn OBJECT-TYPE
 SYNTAX Counter32
 MAX-ACCESS  read-only
 STATUS  current
 DESCRIPTION
    ""
	::= { pktSwchSnaPULlc2FrStatEntry 23}

pktSwchSnaPULlc2FrStatDMsOut OBJECT-TYPE
 SYNTAX Counter32
 MAX-ACCESS  read-only
 STATUS  current
 DESCRIPTION
    ""
	::= { pktSwchSnaPULlc2FrStatEntry 24}

pktSwchSnaPULlc2FrStatSABMEsIn OBJECT-TYPE
 SYNTAX Counter32
 MAX-ACCESS  read-only
 STATUS  current
 DESCRIPTION
    ""
	::= { pktSwchSnaPULlc2FrStatEntry 25}

pktSwchSnaPULlc2FrStatSABMEsOut OBJECT-TYPE
 SYNTAX Counter32
 MAX-ACCESS  read-only
 STATUS  current
 DESCRIPTION
    ""
	::= { pktSwchSnaPULlc2FrStatEntry 26}

pktSwchSnaPULlc2FrStatRetransmitsIn OBJECT-TYPE
 SYNTAX Counter32
 MAX-ACCESS  read-only
 STATUS  current
 DESCRIPTION
    ""
	::= { pktSwchSnaPULlc2FrStatEntry 27}

pktSwchSnaPULlc2FrStatRetransmitsOut OBJECT-TYPE
 SYNTAX Counter32
 MAX-ACCESS  read-only
 STATUS  current
 DESCRIPTION
    ""
	::= { pktSwchSnaPULlc2FrStatEntry 28}

pktSwchSnaPULlc2FrStatUpperState  OBJECT-TYPE
 SYNTAX INTEGER {
    unbound(1),
    bindPending(2),
    unbindPend(3),
    idle(4),
    unattached(5),
    attachPend(6),
    detachPend(7),
    udqosPending(8),
    outconPend(9),
    inconPending(10),
    connResPend(11),
    dataxfer(12),
    userResetPend(13),
    provRstPend(14),
    rstResPend(15),
    discon8Pend(16),
    discon9Pend(17),
    discon11Pend(18),
    discon12Pend(19),
    discon13Pend(20),
    subsBindPend(21),
    noChange(22)
	}
 MAX-ACCESS read-only
 STATUS current
 DESCRIPTION
    "The internal DLPI state of the connection."
	::= { pktSwchSnaPULlc2FrStatEntry 29}

pktSwchSnaPULlc2FrStatLowerState  OBJECT-TYPE
 SYNTAX INTEGER  {
    linkClosed(1),
    disconnected(2),
    linkOpening(3),
    disconnecting(4),
    frmrSent(5),
    linkOpened(6),
    localBusy(7),
    rejection(8),
    checkpointing(9),
    cpLocalBusy(10),
    cpRejection(11),
    resetting(12),
    remoteBusy(13),
    lBusyRBusy(14),
    rejLBusy(15),
    rejRBusy(16),
    cpRejLBusy(17),
    cpClearing(18),
    cpRejClr(19),
    rejLbusyRbusy(20),
    frmrReceived(21),
    programError(22),
    noChange(23)
	}
 MAX-ACCESS read-only
 STATUS current
 DESCRIPTION
    "The internal Llc2Fr state of the connection."
	::= { pktSwchSnaPULlc2FrStatEntry 30}

pktSwchSnaPULlc2FrStatNRMStatus OBJECT-TYPE
 SYNTAX INTEGER	 {sync(1),notSync(2)}
 MAX-ACCESS  read-only
 STATUS  current
 DESCRIPTION
    "This variable indicates if the link is in Normal Response Mode or not."
	::= { pktSwchSnaPULlc2FrStatEntry 31}

pktSwchSnaPULlc2FrStatFlowCtlStatus OBJECT-TYPE
 SYNTAX INTEGER	 {noRNR(1),txFlow(2), rxFlow(3), rxAndTx(4)}
 MAX-ACCESS  read-only
 STATUS  current
 DESCRIPTION
    "This variable indicates the flow control status of the PU interface."
	::= { pktSwchSnaPULlc2FrStatEntry 32}


pktSwchSnaGlobal  OBJECT IDENTIFIER ::= { pktSwchSna 14 }

pktSwchSnaGlobalSrcMacAddrS OBJECT-TYPE
  SYNTAX OCTET STRING (SIZE(6))
  MAX-ACCESS read-write
  STATUS current
  DESCRIPTION
  "LLC2 source MAC address used for all LLC2\RFC1490 protocol interfaces,
   Scratch variable. Format: XX XX XX XX XX XX"
 ::= {pktSwchSnaGlobal 1}

pktSwchSnaGlobalSrcMacAddrA OBJECT-TYPE
  SYNTAX OCTET STRING (SIZE(6))
  MAX-ACCESS read-only
  STATUS current
  DESCRIPTION
  "LLC2 source MAC address used for all LLC2\RFC1490 protocol interfaces,
   Active variable. Format: XX XX XX XX XX XX"
 ::= {pktSwchSnaGlobal 2}


pktSwchSnaGlobalDefFrLlc2LinkS OBJECT-TYPE
    SYNTAX  Integer32
    MAX-ACCESS  read-write
    STATUS  current
    DESCRIPTION
    "The FR Link to where a mac frame will be routed when the destination
     MAC address of the frame does not match the SPS source mac address."
         ::= {pktSwchSnaGlobal 3}

pktSwchSnaGlobalDefFrLlc2LinkA OBJECT-TYPE
    SYNTAX  Integer32
    MAX-ACCESS  read-only
    STATUS  current
    DESCRIPTION
    "The FR Link to where a mac frame will be routed when the destination
     MAC address of the frame does not match the SPS source mac address."
         ::= {pktSwchSnaGlobal 4}

pktSwchSnaGlobalDefFrLlc2DlciS OBJECT-TYPE
    SYNTAX  Integer32
    MAX-ACCESS  read-write
    STATUS  current
    DESCRIPTION
    "The FR DLCI to where a mac frame will be routed when the destination
     MAC address of the frame does not match the SPS source mac address.
     DLCI range is 16..991."
         ::= {pktSwchSnaGlobal 5}

pktSwchSnaGlobalDefFrLlc2DlciA OBJECT-TYPE
    SYNTAX  Integer32
    MAX-ACCESS  read-only
    STATUS  current
    DESCRIPTION
    "The FR DLCI to where a mac frame will be routed when the destination
     MAC address of the frame does not match the SPS source mac address.
     DLCI range is 16..991."
         ::= {pktSwchSnaGlobal 6}

pktSwchSnaGlobalMaxPus OBJECT-TYPE
    SYNTAX  Integer32
    MAX-ACCESS  read-only
    STATUS  current
    DESCRIPTION
    "The maximum number of PUs that can be defined on this device. "
         ::= {pktSwchSnaGlobal 7}

pktSwchSnaGlobalStatus OBJECT-TYPE
    SYNTAX  INTEGER {
       valid(1),
       underCreation(3)
     }
    MAX-ACCESS  read-write
    STATUS  current
    DESCRIPTION
    "The status of this SNA Global entry.
     Used for saving the mac address, llc2 port, and dlci. "
         ::= {pktSwchSnaGlobal 8}

pktSwchEthernet    OBJECT IDENTIFIER ::= { radPS 12}

pktSwchEthernetLinkTable    OBJECT-TYPE
    SYNTAX  SEQUENCE  OF PktSwchEthernetLinkEntry
    MAX-ACCESS  not-accessible
    STATUS  current
    DESCRIPTION
        "The Ethernet link table defines the parameters in the PS
         Ethernet links."
     ::=  { pktSwchEthernet 1 }

pktSwchEthernetLinkEntry OBJECT-TYPE
    SYNTAX  PktSwchEthernetLinkEntry
    MAX-ACCESS  not-accessible
    STATUS  current
    DESCRIPTION
        "The Ethernet Link Entry defines the contents of each link in the
         Ethernet Link Table."
    INDEX   {ifIndex }
    ::=  { pktSwchEthernetLinkTable 1 }

PktSwchEthernetLinkEntry ::= SEQUENCE {
pktSwchEthernetLinkOperationMode
INTEGER,
pktSwchEthernetLinkUserDefMacAddr
OCTET STRING,
pktSwchEthernetLinkPointToPointDest
DisplayString,
pktSwchEthernetLinkTotalFramesIn
Counter32,
pktSwchEthernetLinkTotalFramesOut
Counter32,
pktSwchEthernetLinkIpFramesIn
Counter32,
pktSwchEthernetLinkIpFramesOut
Counter32,
pktSwchEthernetLinkLlc2FramesIn
Counter32,
pktSwchEthernetLinkLlc2FramesOut
Counter32,
pktSwchEthernetLinkBridgFramesIn
Counter32,
pktSwchEthernetLinkBridgFramesOut
Counter32,
pktSwchEthernetLinkDiscardedByFilter
Counter32
     }

pktSwchEthernetLinkOperationMode  OBJECT-TYPE
    SYNTAX INTEGER{
        bridging         (3),
        ip               (4),
        ip-and-bridging  (7),
        llc              (8),
        llc-and-bridging (11),
        ip-and-llc       (12),
        all              (15),
        none             (255) -- disabled
	       }
    MAX-ACCESS  read-write
    STATUS  current
    DESCRIPTION
        "This parameter shows the frame handling mode on this link.

         When IP mode is defined, the IP frames received on this link
         are handled and routed by the IP module in the PS.
         If IP mode is disabled, the IP frames will not be handled by the
         IP module and will be handled as bridged data.

         When Bridging mode is enabled, the PS will perform bridging from
         this link according to the bridging configuration. If disabled,
         bridge data will be ignored.

         When LLC is enabled, frames received on this link are handled by
         the LLC module in the PS. If disabled, the LLC frames will be
         treated as bridged data.

         Any combination of bridging, ip and LLC is allowed. If both IP
         and LLC are enabled, LLC frames will be handled by the LLC module,
         IP frames will be handled by the IP module, and all the other frames
         will treated as bridged data. If the bridge mode is disabled, the
         other frames will be discarded."

    ::= { pktSwchEthernetLinkEntry 1 }


pktSwchEthernetLinkUserDefMacAddr  OBJECT-TYPE
    SYNTAX OCTET STRING (SIZE(6))
    MAX-ACCESS read-write
    STATUS current
    DESCRIPTION
        "This parameter allows the user to define a different MAC address
         for this link other than the device MAC address.
         Possible values:
         6 sets of 2 Hexadecimal digits with
         spaces between them (XX XX XX XX XX XX) "
        ::= { pktSwchEthernetLinkEntry 2 }

pktSwchEthernetLinkPointToPointDest  OBJECT-TYPE
    SYNTAX DisplayString
    MAX-ACCESS read-write
    STATUS current
    DESCRIPTION
    "Destination of the frames which are received on this link.
     Possible values:
     X.25 PVC:       Port:LCN
     X.25 SVC:       X.25 Addr or 'cid' followed by a predefined Call ID
                     number.
     Frame Relay:    Port:DLCI
     No Destination: None

     If no destination, frames will be forwarded according to the
     filter table in 1st priority. If no filter match, the frames will be
     forwarded according to dynamic learning.

     Default value: None"
     ::={ pktSwchEthernetLinkEntry 3 }

pktSwchEthernetLinkTotalFramesIn     OBJECT-TYPE
    SYNTAX Counter32
    MAX-ACCESS read-only
    STATUS current
    DESCRIPTION
    "Total number of frames which were received on this link."
     ::={ pktSwchEthernetLinkEntry 4 }

pktSwchEthernetLinkTotalFramesOut     OBJECT-TYPE
    SYNTAX Counter32
    MAX-ACCESS read-only
    STATUS current
    DESCRIPTION
    "Total number of frames which were transmitted from this link."
     ::={ pktSwchEthernetLinkEntry 5 }

pktSwchEthernetLinkIpFramesIn     OBJECT-TYPE
    SYNTAX Counter32
    MAX-ACCESS read-only
    STATUS current
    DESCRIPTION
    "Number of IP frames which were received on this link."
     ::={ pktSwchEthernetLinkEntry 6 }

pktSwchEthernetLinkIpFramesOut     OBJECT-TYPE
    SYNTAX Counter32
    MAX-ACCESS read-only
    STATUS current
    DESCRIPTION
    "Number of IP frames which were transmitted from this link."
     ::={ pktSwchEthernetLinkEntry 7 }


pktSwchEthernetLinkLlc2FramesIn     OBJECT-TYPE
    SYNTAX Counter32
    MAX-ACCESS read-only
    STATUS current
    DESCRIPTION
    "Number of LLC2 frames which were received on this link."
     ::={ pktSwchEthernetLinkEntry 8 }

pktSwchEthernetLinkLlc2FramesOut     OBJECT-TYPE
    SYNTAX Counter32
    MAX-ACCESS read-only
    STATUS current
    DESCRIPTION
    "Number of LLC2 frames which were transmitted from this link."
     ::={ pktSwchEthernetLinkEntry 9 }

pktSwchEthernetLinkBridgFramesIn     OBJECT-TYPE
    SYNTAX Counter32
    MAX-ACCESS read-only
    STATUS current
    DESCRIPTION
    "Number of Bridged frames which were received on this link."
     ::={ pktSwchEthernetLinkEntry 10 }

pktSwchEthernetLinkBridgFramesOut     OBJECT-TYPE
    SYNTAX Counter32
    MAX-ACCESS read-only
    STATUS current
    DESCRIPTION
    "Number of Bridged frames which were transmitted from this link."
     ::={ pktSwchEthernetLinkEntry 11 }

pktSwchEthernetLinkDiscardedByFilter     OBJECT-TYPE
    SYNTAX Counter32
    MAX-ACCESS read-only
    STATUS current
    DESCRIPTION
    "Number of Bridged frames which were received on this link."
     ::={ pktSwchEthernetLinkEntry 12 }


pktSwchEthernetFilterTable    OBJECT-TYPE
    SYNTAX  SEQUENCE  OF PktSwchEthernetFilterEntry
    MAX-ACCESS  not-accessible
    STATUS  current
    DESCRIPTION
        "The Ethernet filter table defines the frame filtering and
         routing through the PS Ethernet links."
     ::=  { pktSwchEthernet 2 }

pktSwchEthernetFilterEntry OBJECT-TYPE
    SYNTAX  PktSwchEthernetFilterEntry
    MAX-ACCESS  not-accessible
    STATUS  current
    DESCRIPTION
        "The Ethernet Filter Entry defines the filtering on each Ethernet
         link. The filter entry is operational only if Bridging Handling
         is enabled and there is no point to point destination configured
         for this link. If there is a point to point destination configured,
         the frames will be directed to this destination."
    INDEX   {ifIndex, pktSwchEthernetFilterId}
    ::=  { pktSwchEthernetFilterTable 1 }

PktSwchEthernetFilterEntry ::= SEQUENCE {
pktSwchEthernetFilterId
Integer32,
pktSwchEthernetFilterMacAddr
OCTET STRING,
pktSwchEthernetFilterProtType
INTEGER,
pktSwchEthernetFilterDest
DisplayString,
pktSwchEthernetFilterStatus
INTEGER
     }

pktSwchEthernetFilterId  OBJECT-TYPE
    SYNTAX   Integer32 (1..10)
    MAX-ACCESS  read-only
    STATUS  current
    DESCRIPTION
        "Identification Number of an entry in the filter table.
         The ID together with the ifindex define an entry."
    ::= { pktSwchEthernetFilterEntry 1 }

pktSwchEthernetFilterMacAddr  OBJECT-TYPE
    SYNTAX OCTET STRING (SIZE(6))
    MAX-ACCESS read-write
    STATUS current
    DESCRIPTION
        "This parameter defines the MAC address in the current entry
         of the filter table.
         The MAC address in the filter table is compared with the MAC
         address in the received frame. If the MAC address and protocol
         type of the frame are equal to the values in the filter table,
         the frame will be directed to the destination address specified
         in the filter table.

         Possible values:
         MAC Address : 6 sets of 2 Hexadecimal digits with
                       spaces between them (XX XX XX XX XX XX)
         Broadcasting: FF FF FF FF FF FF
         Don't Care  : 00 00 00 00 00 00

         For Broadcasting:
         If a broadcasting entry contains a destination, the frame will
         not be broadcasted. It will be directed to the destination in this
         entry.

         For Don't care:
         The MAC address in the frame and in the filter table are not compared.
         The frames will be directed to the destination specified in the
         filter table if there is a match between the protocol types in the
         frame and in the filter table.

         Default value: 00 00 00 00 00 00 "
    ::= { pktSwchEthernetFilterEntry 2 }

pktSwchEthernetFilterProtType OBJECT-TYPE
    SYNTAX INTEGER{
        llc       (256),
        ip        (2048),
        arp       (2054),
        appleTalk (32923),
        dontCare  (65535)
	       }
    MAX-ACCESS  read-write
    STATUS  current
    DESCRIPTION
        "The protocol type which is compared with the protocol type
         in the received frame. Each protocol in the IP frame is assigned
         16 bits (see RFC1700.txt on the assignment of protocol parameters
         for the Internet protocol suite.).

         If 65535 is entered for the protocol, it means Don't Care.

         If there is a match between this protocol and the protocol in
         the received frame and a match in the MAC addresses, the frame
         will be directed to the destination specified in this table.

         Default value: dontCare (65535)."
    ::= { pktSwchEthernetFilterEntry 3}

pktSwchEthernetFilterDest OBJECT-TYPE
    SYNTAX DisplayString
    MAX-ACCESS read-write
    STATUS current
    DESCRIPTION
        "Destination of the frames which match this current entry.
         The match is in the MAC address and protocol.

         Possible values:
         X.25 PVC:     Port:LCN
         X.25 SVC:     X.25 Addr or 'cid' followed by a predefined Call ID number
         Frame Relay:  Port:DLCI
         No Destination: None

         If No Destination, the frames will be discarded.

         Default value: None ."

        ::={ pktSwchEthernetFilterEntry 4}

pktSwchEthernetFilterStatus OBJECT-TYPE
    SYNTAX  INTEGER {
       valid(1),
       createRequest(2),
       underCreation(3),
       invalid(4)
     }
    MAX-ACCESS  read-write
    STATUS  current
    DESCRIPTION
    "The status of this filter table entry.
     valid         - This entry was saved.
     createRequest - Request to create a new entry.
     underCreation - For a new/updated entry.
     invalid       - Entry is deleted."
         ::= {pktSwchEthernetFilterEntry 5}


pktSwchEthernetBridging    OBJECT IDENTIFIER ::=  { pktSwchEthernet 3 }

pktSwchEthernetBridgingWanToWan OBJECT-TYPE
    SYNTAX INTEGER{
        disable (2),
        enable  (3)
	       }
    MAX-ACCESS  read-write
    STATUS  current
    DESCRIPTION
    "Enable/Disable Ethernet Bridging, WAN to WAN."
         ::= {pktSwchEthernetBridging 1}

pktSwchEthernetBridgingTimer OBJECT-TYPE
    SYNTAX   Integer32 (0..255)
    MAX-ACCESS  read-write
    STATUS  current
    DESCRIPTION
    "Timer used for WAN to WAN communication in order to prevent broadcast
     frames looping forever between devices. When the timer expires,
     the frames are discarded.

     Possible values:
          0 - No timer is used.
     1..255 - Timer value in units of 100 mili sec."
         ::= {pktSwchEthernetBridging 2}

pktSwchEthernetBridgingStatus OBJECT-TYPE
    SYNTAX  INTEGER {
       valid(1),
       underCreation(3)
     }
    MAX-ACCESS  read-write
    STATUS  current
    DESCRIPTION
    "The status of the Ethernet Bridging Parameters.
     valid         - This table was saved.
     underCreation - The table was updated and not yet saved."
         ::= {pktSwchEthernetBridging 3}


pktSwchEthernetBroadcastDestTable    OBJECT-TYPE
    SYNTAX  SEQUENCE  OF PktSwchEthernetBroadcastDestEntry
    MAX-ACCESS  not-accessible
    STATUS  current
    DESCRIPTION
    "The Ethernet Broadcast Destination table defines all the Bridging
     destinations of the PS. Each Broadcasted frame will be
     broadcasted to all these destinations."
     ::=  { pktSwchEthernet 4 }


pktSwchEthernetBroadcastDestEntry OBJECT-TYPE
    SYNTAX  PktSwchEthernetBroadcastDestEntry
    MAX-ACCESS  not-accessible
    STATUS  current
    DESCRIPTION
        "The Ethernet Broadcast Entry defines destinations for Ethernet
         bridge data."
    INDEX   {pktSwchEthernetBroadcastDestProtocol,
             pktSwchEthernetBroadcastDestId}
    ::=  { pktSwchEthernetBroadcastDestTable 1 }

PktSwchEthernetBroadcastDestEntry ::= SEQUENCE {
pktSwchEthernetBroadcastDestProtocol
INTEGER,
pktSwchEthernetBroadcastDestId
Integer32,
pktSwchEthernetBroadcastDestDestination
DisplayString,
pktSwchEthernetBroadcastDestStatus
INTEGER
     }

pktSwchEthernetBroadcastDestProtocol  OBJECT-TYPE
    SYNTAX INTEGER{
        x25        (2),
        frameRelay (3)
	       }
    MAX-ACCESS  read-only
    STATUS  current
    DESCRIPTION
        "The protocol of the Broadcasted frames."
    ::= { pktSwchEthernetBroadcastDestEntry 1 }

pktSwchEthernetBroadcastDestId  OBJECT-TYPE
    SYNTAX   Integer32 (1..10)
    MAX-ACCESS  read-only
    STATUS  current
    DESCRIPTION
        "Identification Number of an entry in the Ethernet Broadcast
         Destination table."
    ::= { pktSwchEthernetBroadcastDestEntry 2 }

pktSwchEthernetBroadcastDestDestination OBJECT-TYPE
    SYNTAX DisplayString
    MAX-ACCESS read-write
    STATUS current
    DESCRIPTION
        "Destination for the Ethernet frames.

         Possible values for X25:
         X.25 PVC:     Port:LCN
         X.25 SVC:     X.25 Addr or 'cid' followed by a predefined Call ID number

         Possible values for fr:
         Frame Relay:  Port:DLCI

         No Destination: None"
        ::={ pktSwchEthernetBroadcastDestEntry 3}

pktSwchEthernetBroadcastDestStatus OBJECT-TYPE
    SYNTAX  INTEGER {
       valid(1),
       createRequest(2),
       underCreation(3),
       invalid(4)
     }
    MAX-ACCESS  read-write
    STATUS  current
    DESCRIPTION
    "The status of this Ethernet Destination table entry.
     valid         - This entry was saved.
     createRequest - Request to create a new entry.
     underCreation - For a new/updated entry.
     invalid       - Entry is deleted."
         ::= {pktSwchEthernetBroadcastDestEntry 4}


pktSwchIp       OBJECT IDENTIFIER ::= { radPS 13}

pktSwchIpGlobal OBJECT IDENTIFIER ::=  { pktSwchIp 1 }

pktSwchIpGlobalMaxHopCount OBJECT-TYPE
    SYNTAX   Integer32 (5..65000)
    MAX-ACCESS  read-write
    STATUS  current
    DESCRIPTION
    "Maximum no. of hops the device will support.
     The default value is 15. Legal values: 5 to 65000."
         ::= {pktSwchIpGlobal 1}

pktSwchIpIntervalBetweenUpdates OBJECT-TYPE
    SYNTAX   Integer32 (30..2550)
    MAX-ACCESS  read-write
    STATUS  current
    DESCRIPTION
    "The time in seconds from one update of the device's dynamic routing
     table to the next update. The time is in steps of 10 seconds.
     Default value: 30
     Legal values: 30,40,50 ... 2550"
         ::= {pktSwchIpGlobal 2}

pktSwchIpGlobalStatus OBJECT-TYPE
    SYNTAX  INTEGER {
       valid(1),
       underCreation(3)
     }
    MAX-ACCESS  read-write
    STATUS  current
    DESCRIPTION
    "The status of this IP Global entry.
     Used for saving the IP Global parameters. "
         ::= {pktSwchIpGlobal 3}

pktSwchIpInterfaceTable    OBJECT-TYPE
    SYNTAX  SEQUENCE  OF PktSwchIpInterfaceEntry
    MAX-ACCESS  not-accessible
    STATUS  current
    DESCRIPTION
        "The Ip interface table defines the Ip interfaces and their
         parameters in the PS device."
     ::=  { pktSwchIp 2 }

pktSwchIpInterfaceEntry OBJECT-TYPE
    SYNTAX  PktSwchIpInterfaceEntry
    MAX-ACCESS  not-accessible
    STATUS  current
    DESCRIPTION
        "The IP interface Entry defines the IP configuration parameters
         for each IP interface."
    INDEX   {pktSwchIpInterfaceId}
    ::=  { pktSwchIpInterfaceTable 1 }

PktSwchIpInterfaceEntry ::= SEQUENCE {
pktSwchIpInterfaceId
Integer32,
pktSwchIpInterfaceAddress
IpAddress,
pktSwchIpInterfaceAddressMask
IpAddress,
pktSwchIpInterfaceSendDefRoutMsgOnly
INTEGER,
pktSwchIpInterfaceDest
DisplayString,
pktSwchIpInterfaceInactivity
Integer32,
pktSwchIpInterfaceLinkCost
Integer32,
pktSwchIpInterfaceOptions
INTEGER,
pktSwchIpInterfaceStatus
INTEGER,
pktSwchIpInterfaceRxFrames
Counter32,
pktSwchIpInterfaceRxExpiredTtl
Counter32,
pktSwchIpInterfaceRxUnknownDest
Counter32,
pktSwchIpInterfaceTxFrames
Counter32,
pktSwchIpInterfaceTxQueueBufs
Counter32,
pktSwchIpInterfaceTxDiscarded
Counter32,
pktSwchIpInterfaceRipRxFrames
Counter32,
pktSwchIpInterfaceRipTxFrames
Counter32,
pktSwchIpInterfaceRipWaitingMsgs
Counter32
     }

pktSwchIpInterfaceId  OBJECT-TYPE
    SYNTAX   Integer32 (1..200)
    MAX-ACCESS  read-only
    STATUS  current
    DESCRIPTION
        "Identification Number of an entry in the IP interface table."
    ::= { pktSwchIpInterfaceEntry 1 }

pktSwchIpInterfaceAddress  OBJECT-TYPE
    SYNTAX  IpAddress
    MAX-ACCESS read-write
    STATUS current
    DESCRIPTION
        "The IP address of the interface. Legal input: any legal IP address.
         Default value: 0.0.0.0 "
    ::= { pktSwchIpInterfaceEntry 2 }

pktSwchIpInterfaceAddressMask OBJECT-TYPE
    SYNTAX  IpAddress
    MAX-ACCESS  read-write
    STATUS  current
    DESCRIPTION
        "The IP mask of the interface. Legal input: any legal IP mask:
         A string of the format X.X.X.X where every X is a number in
         the range 0-255.
         Default value: 255.255.255.255 "
    ::= { pktSwchIpInterfaceEntry 3 }

pktSwchIpInterfaceSendDefRoutMsgOnly OBJECT-TYPE
    SYNTAX  INTEGER {
       disable (2),
       enable(3)
     }
    MAX-ACCESS  read-write
    STATUS  current
    DESCRIPTION
        "Some of the RIP messages are default router messages.
         These messages inform who the default router is.

         This MIB object allows the user to configure the device so
         that it will send default router messages only.

         If sendDefaultRoutMsgOnly is set to enable, the
         device will not send any RIP messages except for default router
         messages.

         Default value: disable ."

    ::= { pktSwchIpInterfaceEntry 4 }

pktSwchIpInterfaceDest OBJECT-TYPE
    SYNTAX DisplayString
    MAX-ACCESS read-write
    STATUS current
    DESCRIPTION
        "Destination of the packets received on this interface.

         Possible values:
         X.25 PVC:       Port:LCN
         X.25 SVC:       X.25 Addr or 'cid' followed by a predefined Call ID
                         number.
         Frame Relay:    Port:DLCI
         HDLC:           'H' followed by the HDLC Port Number
         SLIP:           'S' followed by the SLIP Channel Number
         Ethernet:       'E' followed by the Ethernet Port Number
         PPP:            'P' followed by the PPP Port Number.
         Bundles(for PPP)'B' followed by the PPP Bundle Number.
         No destination:  None

         Default :       None

         Examples:
         1. For SLIP destination which is Link no. 1, the destination
            will be S100 (100 instead of 1 is for Async).
         2. For SLIP destination of APS-8, channel no. 8:
            S8
         3. For PPP destination of APS-8, Sync Link no. 1: P1
         4. For PPP destination of APS-8, Async channel on link 1: P100

         Note for PPP:
         PPP protocol is allowed to be applied on Sync Links (1-3)
         as well as Async channels (1-24).
         In the ascii terminal: If the user writes P1 for example the device
         has to check which P1 it is. Is it the async channel 1 or
         Link no. 1. The device does NOT ALLOW configuring PPP on both
         Sync Link no. 1 and async RJ45 channel 1.
         When P1 is entered by the user, the protocols on async channel 1 and sync
         link 1 are checked. As only one of them is PPP, it will apply to the
         only PPP chan/link."
         ::= { pktSwchIpInterfaceEntry 5 }

pktSwchIpInterfaceInactivity OBJECT-TYPE
    SYNTAX   Integer32 (0..255)
    MAX-ACCESS  read-write
    STATUS  current
    DESCRIPTION
        "Inactivity time in minutes before disconnecting the X25 SVC call.
         Range: 0..255. Default: 2."
        ::= { pktSwchIpInterfaceEntry 6 }

pktSwchIpInterfaceLinkCost OBJECT-TYPE
    SYNTAX   Integer32
    MAX-ACCESS  read-write
    STATUS  current
    DESCRIPTION
        "This value will be added to the value written in the
         metric field of the received frame.
         Range: 1..pktSwchIpGlobalMaxHopCount
         Default: 1."
         ::= { pktSwchIpInterfaceEntry 7 }

pktSwchIpInterfaceOptions OBJECT-TYPE
    SYNTAX  INTEGER {
             netIpAddress (2),
             none         (255)
    }
    MAX-ACCESS  read-write
    STATUS  current
    DESCRIPTION
        "When netIpAddress is selected the interface IP address
         will not be the IP address of the interface. It will be the IP
         address of the NetWork which is connected to this interface.
         This option is for an interface which does not require a
         unique IP address.
         Default is none."
        ::= { pktSwchIpInterfaceEntry 8 }

pktSwchIpInterfaceStatus OBJECT-TYPE
    SYNTAX  INTEGER {
       valid(1),
       createRequest(2),
       underCreation(3),
       invalid(4)
     }
    MAX-ACCESS  read-write
    STATUS  current
    DESCRIPTION
    "The status of this filter table entry.
     valid         - This entry was saved.
     createRequest - Request to create a new entry.
     underCreation - For a new/updated entry.
     invalid       - Entry is deleted."
        ::= { pktSwchIpInterfaceEntry 9 }

pktSwchIpInterfaceRxFrames OBJECT-TYPE
    SYNTAX  Counter32
    MAX-ACCESS  read-only
    STATUS  current
    DESCRIPTION
    "No. of frames which were received on this IP interface."
        ::= { pktSwchIpInterfaceEntry 10 }

pktSwchIpInterfaceRxExpiredTtl OBJECT-TYPE
    SYNTAX  Counter32
    MAX-ACCESS  read-only
    STATUS  current
    DESCRIPTION
    "No. of frames which were received on this IP interface
     with an Expired Time to Live value."
    ::= { pktSwchIpInterfaceEntry 11 }

pktSwchIpInterfaceRxUnknownDest OBJECT-TYPE
    SYNTAX  Counter32
    MAX-ACCESS  read-only
    STATUS  current
    DESCRIPTION
    "No. of frames which were received on this IP interface
     with an unknown IP destination. No default router is configured.
     These frames will be discarded."
    ::= { pktSwchIpInterfaceEntry 12 }

pktSwchIpInterfaceTxFrames OBJECT-TYPE
    SYNTAX  Counter32
    MAX-ACCESS  read-only
    STATUS  current
    DESCRIPTION
    "No. of frames which were Transmitted from this IP interface."
    ::= { pktSwchIpInterfaceEntry 13 }

pktSwchIpInterfaceTxQueueBufs OBJECT-TYPE
    SYNTAX  Counter32
    MAX-ACCESS  read-only
    STATUS  current
    DESCRIPTION
    "No. of buffers which are waiting in the Trasnsmit Queue. "
     ::= { pktSwchIpInterfaceEntry 14 }

pktSwchIpInterfaceTxDiscarded OBJECT-TYPE
    SYNTAX  Counter32
    MAX-ACCESS  read-only
    STATUS  current
    DESCRIPTION
    "No. of frames which were ready to be transmitted but were
     Discarded. The PS will discard frames if the transmit queue
     is too long."
     ::= { pktSwchIpInterfaceEntry 15 }

pktSwchIpInterfaceRipRxFrames OBJECT-TYPE
    SYNTAX  Counter32
    MAX-ACCESS  read-only
    STATUS  current
    DESCRIPTION
    "No. of RIP frames which were received on this IP interface."
    ::= { pktSwchIpInterfaceEntry 16 }

pktSwchIpInterfaceRipTxFrames OBJECT-TYPE
    SYNTAX  Counter32
    MAX-ACCESS  read-only
    STATUS  current
    DESCRIPTION
    "No. of RIP Frames which were transmitted from this IP interface."
    ::= { pktSwchIpInterfaceEntry 17 }

pktSwchIpInterfaceRipWaitingMsgs OBJECT-TYPE
    SYNTAX  Counter32
    MAX-ACCESS  read-only
    STATUS  current
    DESCRIPTION
    "No. of RIP messages which are waiting to be transmitted to the
     Network."
     ::= { pktSwchIpInterfaceEntry 18 }


pktSwchIsdn       OBJECT IDENTIFIER ::= { radPS 14}

--  Packet Switching devices with Integrated Services Digital Network.

pktSwchIsdnGlobal  OBJECT IDENTIFIER ::= { pktSwchIsdn 1 }

--  ISDN Global Parameters

pktSwchIsdnGlobalCallRetries OBJECT-TYPE
    SYNTAX Integer32 (0..255)
    MAX-ACCESS  read-write
    STATUS  current
    DESCRIPTION
    "Number of times the call request is repeated after failure.
     Possible values:
     0     - Disable retry mechanism
     1-255 - Number of retries
     default value: 0"
     ::= {pktSwchIsdnGlobal 1}

pktSwchIsdnGlobalCallRetryDelay OBJECT-TYPE
    SYNTAX Integer32 (5..250)
    MAX-ACCESS  read-write
    STATUS  current
    DESCRIPTION
    "Time interval between retries (in seconds).
     Possible values:
     5 - 250
     Default value: 15"
     ::= {pktSwchIsdnGlobal 2}

pktSwchIsdnGlobalCallinactivity OBJECT-TYPE
    SYNTAX Integer32 (0..65000)
    MAX-ACCESS  read-write
    STATUS  current
    DESCRIPTION
    "Time of inactivity in seconds, after which the call will be
     disconnected. An x.25 link is considered inactive when there are
     no open calls on the link. A frame relay link is considered inactive
     when there is no traffic on the link.
     Possible values:
     0 - No disconnection on inactivity.
     1 - 65000 - Time period (in seconds).
     Default value: 180"
     ::= {pktSwchIsdnGlobal 3}

pktSwchIsdnGlobalStatus OBJECT-TYPE
    SYNTAX  INTEGER {
       valid(1),
       underCreation(3)
     }
    MAX-ACCESS  read-write
    STATUS  current
    DESCRIPTION
    "The status of the Isdn Global parameters.
     Used for saving the Isdn global parameters."
         ::= {pktSwchIsdnGlobal 4}


pktSwchIsdnRoutTable    OBJECT-TYPE
    SYNTAX  SEQUENCE  OF PktSwchIsdnRoutEntry
    MAX-ACCESS  not-accessible
    STATUS  current
    DESCRIPTION
	"The Isdn Routing Table entries in the Packet Switch."
     ::=  { pktSwchIsdn 2 }

pktSwchIsdnRoutEntry OBJECT-TYPE
    SYNTAX  PktSwchIsdnRoutEntry
    MAX-ACCESS  not-accessible
    STATUS  current
    DESCRIPTION
        "Isdn Routing Entry defines the contents of each entry in the table.
         The outgoing addresses are in a different table -
         pktSwchIsdnRoutAddrTable. The row status in this
         table will be used for both tables."
         INDEX   { pktSwchIsdnRoutId }
         ::=  { pktSwchIsdnRoutTable 1 }

PktSwchIsdnRoutEntry ::=  SEQUENCE {
    pktSwchIsdnRoutId
    Integer32,
    pktSwchIsdnRoutDataBandWidth
     INTEGER,
    pktSwchIsdnRoutOptions
     INTEGER,
    pktSwchIsdnRoutStatus
     INTEGER
    }

pktSwchIsdnRoutId OBJECT-TYPE
    SYNTAX Integer32 (1..200)
        MAX-ACCESS  read-only
	STATUS  current
	DESCRIPTION
        "Number of this routing entry."
        ::= { pktSwchIsdnRoutEntry 1 }

pktSwchIsdnRoutDataBandWidth OBJECT-TYPE
    SYNTAX  INTEGER {
        bw56Kbps(2),
        bw64Kbps(3)
	}
    MAX-ACCESS  read-write
    STATUS  current
    DESCRIPTION
    "Isdn Bandwidth which will be used for the data routed via this
     entry. The ISDN interface will be configured with the speed
     which is selected.
     Possible values:
     2 - 56 Kbps.
     3 - 64 Kbps.
     Default value: 3 "
    ::= { pktSwchIsdnRoutEntry 2 }

pktSwchIsdnRoutOptions OBJECT-TYPE
    SYNTAX  INTEGER {
        noOptions(1),
        returnToMainLink(2)
	}
    MAX-ACCESS  read-write
    STATUS  current
    DESCRIPTION
    "Special Options for this routing entry.
     Possible values:
     1 - No special options.
     2 - Return to main link. This option is used when the current link
         is defined as a backup link and the main link becomes active.
     Default value: 1 "
    ::= { pktSwchIsdnRoutEntry 3 }

pktSwchIsdnRoutStatus OBJECT-TYPE
    SYNTAX  INTEGER {
       valid(1),
       createRequest(2),
       underCreation(3),
       invalid(4)
     }
    MAX-ACCESS  read-write
    STATUS  current
    DESCRIPTION
    "The status of this routing table entry + address table
     (pktSwchIsdnOutAddrTable).
     For creating a new entry select createRequest. A new route entry
     will be created together with an out address entry. There may be
     more than 1 addresses. For example, if there is 1 outgoing address
     and 2 alternatives, the new address entry will have 3 indices.
     For deleting an entry select invalid. The relevant address entry
     should be deleted too.
     For saving an entry select valid. Save should include the addresses
     of the current entry in the pktSwchIsdnOutAddrTable"
     ::= { pktSwchIsdnRoutEntry 4 }


pktSwchIsdnOutAddrTable    OBJECT-TYPE
    SYNTAX  SEQUENCE  OF PktSwchIsdnOutAddrEntry
    MAX-ACCESS  not-accessible
    STATUS  current
    DESCRIPTION
    "Outgoing ISDN addresses used by the ISDN routing table.
     The address table contains outgoing
     addresses and alternative addresses in case the connection
     to the first addresses does not succeed."
    ::=  { pktSwchIsdn 3 }

pktSwchIsdnOutAddrEntry OBJECT-TYPE
    SYNTAX  PktSwchIsdnOutAddrEntry
    MAX-ACCESS  not-accessible
    STATUS  current
    DESCRIPTION
        "Isdn Outgoing Address  Entry defines the contents of each entry in
         the outgoing address table.
         Each entry has 2 indices:
         1. RoutId is the ID in the routing table.
         2. AddrId is the ID containing the Outgoing address and
            sub address. "
    INDEX   { pktSwchIsdnOutAddrRoutId, pktSwchIsdnOutAddrId }
    ::=  { pktSwchIsdnOutAddrTable 1 }


PktSwchIsdnOutAddrEntry ::=  SEQUENCE {
    pktSwchIsdnOutAddrRoutId
    Integer32,
    pktSwchIsdnOutAddrId
    Integer32,
    pktSwchIsdnOutAddr
     DisplayString,
    pktSwchIsdnOutSubAddr
     DisplayString
    }

 pktSwchIsdnOutAddrRoutId OBJECT-TYPE
    SYNTAX Integer32 (1..200)
        MAX-ACCESS  read-only
	STATUS  current
	DESCRIPTION
        "ID in the ISDN routing table."
        ::= { pktSwchIsdnOutAddrEntry 1 }


pktSwchIsdnOutAddrId OBJECT-TYPE
    SYNTAX Integer32 (1..3)
        MAX-ACCESS  read-only
	STATUS  current
	DESCRIPTION
        "Number of the address + subaddress pair for each routing ID."
        ::= { pktSwchIsdnOutAddrEntry 2 }

pktSwchIsdnOutAddr      OBJECT-TYPE
    SYNTAX DisplayString (SIZE (0..17))
    MAX-ACCESS  read-write
    STATUS  current
    DESCRIPTION
        "Destination ISDN Outgoing (Remote) address.
	 The data will be routed out to this address.
         Possible values:
         Up to 17 decimal digits.
         Default value: string of length 0."
    ::= { pktSwchIsdnOutAddrEntry 3 }

pktSwchIsdnOutSubAddr      OBJECT-TYPE
    SYNTAX DisplayString (SIZE (0..6))
    MAX-ACCESS  read-write
    STATUS  current
    DESCRIPTION
        "Destination ISDN Outgoing (Remote) sub address.
         The data will be routed out to the out addrress with
         this sub address.
         Possible values:
         Up to 6 decimal digits.
         Default value: string of length 0."
    ::= { pktSwchIsdnOutAddrEntry 4 }


pktSwchIsdnAcceptTable    OBJECT-TYPE
    SYNTAX  SEQUENCE  OF PktSwchIsdnAcceptEntry
    MAX-ACCESS  not-accessible
    STATUS  current
    DESCRIPTION
        "Table of Isdn addresses which will be accepted by the agent.
         If there is a dial back (answer) address, the incoming call
         will be disconnected and dial back will initiate. Most of
         the accept list parameters are in RFC2128 in the
         dialCtlPeerCfgTable. The parameters which are not in the
         the standard RFC2128 and are required, are defined here
         in the private PS MIB."
     ::=  { pktSwchIsdn 4 }

pktSwchIsdnAcceptEntry OBJECT-TYPE
    SYNTAX  PktSwchIsdnAcceptEntry
    MAX-ACCESS  not-accessible
    STATUS  current
    DESCRIPTION
	"Isdn Accept Entry defines the contents of each entry in the table."
    INDEX   { pktSwchIsdnAcceptId }
    ::=  { pktSwchIsdnAcceptTable 1 }

PktSwchIsdnAcceptEntry ::=  SEQUENCE {
    pktSwchIsdnAcceptId
    Integer32,
    pktSwchIsdnAcceptSecondaryLink
    Integer32,
    pktSwchIsdnAcceptDialbkSubAddress
     DisplayString,
    pktSwchIsdnAcceptStatus
     INTEGER
    }

pktSwchIsdnAcceptId OBJECT-TYPE
    SYNTAX Integer32 (1..200)
    MAX-ACCESS  read-write
    STATUS  current
    DESCRIPTION
        "Identifier of Accept table entry."
        ::= { pktSwchIsdnAcceptEntry 1 }

pktSwchIsdnAcceptSecondaryLink OBJECT-TYPE
    SYNTAX Integer32 (1..255)
    MAX-ACCESS  read-write
    STATUS  current
    DESCRIPTION
    "A valid Isdn link number on which the call will be accepted
     when the Primary link (RFC2128.dialCtlPeerCfgLowerIf)is unavailable.

     Possible values:
     255 - No Secondary link.
     or
     The complementary to the primary ISDN link number.
     Complementary links are: [1;2] and [7;8].
     If Primary Link Number is set to first available <0>,
     the Secondary link must be set to No Secondary link <255>.

     Default value is complementary to the primary link no. defined in
     rfc2128.dialCtlPeerCfgLowerIf."
     ::= { pktSwchIsdnAcceptEntry 2 }

pktSwchIsdnAcceptDialbkSubAddress OBJECT-TYPE
    SYNTAX DisplayString (SIZE (0..6))
    MAX-ACCESS  read-write
    STATUS  current
    DESCRIPTION
    "Isdn sub address which will be used by the agent for dialing
     back.
     Possible values:
     Up to 6 decimal digits.

     Default value: string of length 0."
     ::= { pktSwchIsdnAcceptEntry 3 }

pktSwchIsdnAcceptStatus OBJECT-TYPE
    SYNTAX  INTEGER {
       valid(1),
       createRequest(2),
       underCreation(3),
       invalid(4)
     }
    MAX-ACCESS  read-write
    STATUS  current
    DESCRIPTION
    "The status of this accept table entry.
     For creating a new entry select createRequest,
     For deleting an entry select invalid.
     For saving an entry select valid."
     ::= { pktSwchIsdnAcceptEntry 4 }

pktSwchIsdnLinkTable    OBJECT-TYPE
    SYNTAX  SEQUENCE  OF PktSwchIsdnLinkEntry
    MAX-ACCESS  not-accessible
    STATUS  current
    DESCRIPTION
        "Table of Isdn Link parameters. Most of the link parameters
         are in in RFC2127. Isdn Call statistics are RFC2128.
         The parameters which are not in the the standard RFCs ,
         and are required, are defined here in the private PS MIB."
    ::=  { pktSwchIsdn 5 }

pktSwchIsdnLinkEntry OBJECT-TYPE
    SYNTAX  PktSwchIsdnLinkEntry
    MAX-ACCESS  not-accessible
    STATUS  current
    DESCRIPTION
        "Isdn Link Entry defines the contents of each entry in the table."
    INDEX   {ifIndex }
    ::=  { pktSwchIsdnLinkTable 1 }

PktSwchIsdnLinkEntry ::=  SEQUENCE {
    pktSwchIsdnLinkBchannel
    INTEGER,
    pktSwchIsdnCallsClrs
    Counter32,
    pktSwchIsdnTestCmd
    INTEGER,
    pktSwchIsdnTestAddr
    DisplayString,
    pktSwchIsdnTestSubAddr
    DisplayString
    }

pktSwchIsdnLinkBchannel OBJECT-TYPE
    SYNTAX  INTEGER {
       noBchannel(1),
       b1(2),
       b2(3),
       b1Andb2(4)
     }
    MAX-ACCESS  read-write
    STATUS  current
    DESCRIPTION
    "Defines which B channels are used for Leased Lines Only.
     Default value: noBchannel(1)."
     ::= { pktSwchIsdnLinkEntry 1 }

pktSwchIsdnCallsClrs OBJECT-TYPE
    SYNTAX  Counter32
    MAX-ACCESS  read-only
    STATUS  current
    DESCRIPTION
    "Number of calls on this link which were cleared since the link was
         activated."
    ::= { pktSwchIsdnLinkEntry 2 }

pktSwchIsdnTestCmd OBJECT-TYPE
    SYNTAX INTEGER {
        noOp     (2),
        activate (3)
        }
    MAX-ACCESS  read-write
    STATUS  current
    DESCRIPTION
    "Activate/Stop an ISDN test on the current ISDN link.
     In order to Activate the test, set the TestCmd to 3 (activate).
     For stopping the test, set the TestCmd to 2 (noOp).

     Important: In order for the test to succeed, the user must set
     the pktSwchIsdnTestAddr and Subaddr to their required values before
     activating the test. "
    ::= { pktSwchIsdnLinkEntry 3 }

pktSwchIsdnTestAddr      OBJECT-TYPE
    SYNTAX DisplayString (SIZE (0..17))
    MAX-ACCESS  read-write
    STATUS  current
    DESCRIPTION
        "Destination ISDN Outgoing (Remote) address which will be
         called in order to test the ISDN.
         Possible values:
         Up to 17 decimal digits.
         Default value: string of length 0.

        Important: In order for the test to succeed, the user must also set
        the pktSwchIsdnTestSubAddr to the required values before
        activating the test. "
    ::= { pktSwchIsdnLinkEntry 4 }

pktSwchIsdnTestSubAddr      OBJECT-TYPE
    SYNTAX DisplayString (SIZE (0..6))
    MAX-ACCESS  read-write
    STATUS  current
    DESCRIPTION
        "Destination ISDN Outgoing (Remote) address which will be
         called in order to test the ISDN.
         Possible values:
         Up to 6 decimal digits.
         Default value: string of length 0.

        Important: In order for the test to succeed, the user must also set
        the pktSwchIsdnTestAddr to the required values before
        activating the test. "
    ::= { pktSwchIsdnLinkEntry 5 }


pktSwchPpp       OBJECT IDENTIFIER ::= { radPS 15}

--  Point to Point Protocol in the Packet Switching devices.

--  PPP Global Parameters:
--  All the parameters are in: RFC1472, PPP  Security Secrets Table.
--  The Security Secrets table contains pairs of Identity and secrets
--  (Port User Name and Port Password).
--  The link no. which is used for the Secrets table is: 0.
--  Link no. 0 in RFC1472 means that the ID/Secret pair applies to all links.
--
--  The ROW status of rfc1472 could not be used because it has only 2 values:
--  valid and invalid. There is no option for create request as is used
--  in the Packet Switches.
--  The only parameter which was added here is the ROW status for the table.

pktSwchPppSecretsTable    OBJECT-TYPE
    SYNTAX  SEQUENCE  OF PktSwchPppSecretsEntry
    MAX-ACCESS  not-accessible
    STATUS  current
    DESCRIPTION
        "Table of PPP Secret parameters.
         The parameters are defined in rfc1472 except for the ROW status
         which is defined here.
         In the standard, there is no create request option, so in order
         to be consistent with other ROW statuses in the Packet Switches
         it is defined here."
    ::=  { pktSwchPpp 1 }

pktSwchPppSecretsEntry OBJECT-TYPE
    SYNTAX  PktSwchPppSecretsEntry
    MAX-ACCESS  not-accessible
    STATUS  current
    DESCRIPTION
    "PPP Secrets Entry defines the contents of each entry in the table."
    INDEX   {pktSwchPppSecretsPairId}
    ::=  { pktSwchPppSecretsTable 1 }

PktSwchPppSecretsEntry ::=  SEQUENCE {
    pktSwchPppSecretsPairId
    Integer32,
    pktSwchPppSecretsStatus
    INTEGER
    }

pktSwchPppSecretsPairId OBJECT-TYPE
    SYNTAX Integer32 (1..200)
	MAX-ACCESS  read-only
	STATUS  current
	DESCRIPTION
        "Index of the Secrets Pair."
        ::= { pktSwchPppSecretsEntry 1 }

pktSwchPppSecretsStatus OBJECT-TYPE
    SYNTAX  INTEGER {
       valid(1),
       createRequest(2),
       underCreation(3),
       invalid(4)
     }
    MAX-ACCESS  read-write
    STATUS  current
    DESCRIPTION
    "The status of the PPP Secrets table.
     For creating a new entry select createRequest,
     For deleting an entry select invalid.
     For saving an entry select valid."
        ::= { pktSwchPppSecretsEntry 2 }


pktSwchPppChanTable    OBJECT-TYPE
    SYNTAX  SEQUENCE  OF PktSwchPppChanEntry
    MAX-ACCESS  not-accessible
    STATUS  current
    DESCRIPTION
        "Table of PPP Channel parameters.
         The table can be used for Async as well as Sync parameters.
         In case a parameter is irrelevant for Async or Sync a  value may be returned.
         Statistics Parameters are already defined in rfc1213:
         ifInUcastPkts, ifOutUcastPkts, ifInErrors, ifOutErrors"
    ::=  { pktSwchPpp 2 }

pktSwchPppChanEntry OBJECT-TYPE
    SYNTAX  PktSwchPppChanEntry
    MAX-ACCESS  not-accessible
    STATUS  current
    DESCRIPTION
        "PPP Channel Entry defines the contents of each entry in the table."
    INDEX   {ifIndex }
    ::=  { pktSwchPppChanTable 1 }

PktSwchPppChanEntry ::=  SEQUENCE {
    pktSwchPppChanSpeed
    INTEGER,
    pktSwchPppChanFlowCtlDuration
    Integer32,
    pktSwchPppChanStopBits
     INTEGER,
    pktSwchPppChanBitPerChar
     Integer32,
    pktSwchPppChanParity
     INTEGER,
    pktSwchPppChanNegotiationTrigger
    INTEGER,
    pktSwchPppChanMRU
    Integer32,
    pktSwchPppChanACCM
    OCTET STRING,
    pktSwchPppChanAuthentication
    INTEGER,
    pktSwchPppChanInternalClock
    INTEGER,
    pktSwchPppChanBundle
    Integer32,
    pktSwchpPppChanIsdnRoutId
    Integer32,
    pktSwchpPppChanLastEvent
    DisplayString
    }

pktSwchPppChanSpeed OBJECT-TYPE
    SYNTAX  INTEGER {
       s110bps    (1),
       s300bps    (2),
       s1200bps   (3),
       s600bps    (4),
       s75bps     (5),
       s150bps    (6),

       s2400bps  (12),
       s4800bps  (13),
       s9600bps  (14),
       s19200bps (15),

       s38400bps (19),
       s57600bps (20),
       s115200bps(21),
       notApplicable(255)
           }
    MAX-ACCESS  read-write
    STATUS  current
    DESCRIPTION
    "The port's speed in bits per second.
     For Async channels: Default value: 14 .
     For Sync  Links: Use not_applicable(255)
     The Sync Links have an internal clock with
     different values."
     ::= { pktSwchPppChanEntry 1 }

pktSwchPppChanFlowCtlDuration OBJECT-TYPE
    SYNTAX Integer32 (0..255)
    MAX-ACCESS  read-write
    STATUS  current
    DESCRIPTION  " Hardware Flow Control Duration.
         1..254 - Duration (in 50ms intervals).
                  when timer expires, flow control stops.
              0 - No Hardware flow control.
            255 - Continuous Flow Control.
         Default value: 0.
         For Sync Links, return 0."
     ::= { pktSwchPppChanEntry 2 }

pktSwchPppChanStopBits OBJECT-TYPE
    SYNTAX  INTEGER  {
       one       (1),
       two       (2),
       oneAndHalf(3),
       notApplicable(255)
    }
    MAX-ACCESS  read-write
    STATUS  current
    DESCRIPTION
    "This entry indicates the number of stop bits per character.
     The options are either (1) one stop bit, (2) two stop bits,
     or (3) 1.5 stop bits.
     For Sync Links: notApplicable(255)."
    ::= { pktSwchPppChanEntry 3 }

pktSwchPppChanBitPerChar  OBJECT-TYPE
    SYNTAX Integer32 (0..8)
    MAX-ACCESS  read-write
    STATUS  current
    DESCRIPTION
    "The number of data bits per character supported by the ppp
     link. Legal values for Async channels: 5..8 .
     For Sync Links: 0"
    ::= { pktSwchPppChanEntry 4 }

pktSwchPppChanParity  OBJECT-TYPE
    SYNTAX  INTEGER  {
       space(1),
       mark(2),
       even(3),
       odd(4),
       none(255)
    }
    MAX-ACCESS  read-write
    STATUS  current
    DESCRIPTION
    "This entry selects the type of parity to be checked or
     generated.
     The options are (1) space parity, (2) mark parity,
     (3) even parity, (4) odd parity, or (255) no parity.
     For Sync Links: none(255)."
    ::= { pktSwchPppChanEntry 5 }

pktSwchPppChanNegotiationTrigger OBJECT-TYPE
    SYNTAX  INTEGER {
       hw-signal        (1),
       data-triggered   (2),
       hw-signal-or-data(3),
       after-reset      (255)
    }
    MAX-ACCESS  read-write
    STATUS  current
    DESCRIPTION
    "The trigger which is used in order to start the Negotiation.
     The HW signals which are used are:
     DCD (Data Carrier  Detect) - issued by DCE
     DSR (Data Set Ready)       - issued by DCE
     DTR (Data Terminal Ready)  - issued by DTE

   1 -   Start negotiation on signal assertion.
         The Peer will issue a DCD/DSR Signal if it is DCE or
         DTR if it is DTE.
         If the current channel/link is DCE, it will check the DTR.
         If the current channel/link is DTE, it will check the DCD/DSR.

         When the HW signal is issued, negotiation will begin.

   2 - Data Triggered.
         The current channel/link will issue a HW signal.
         Negotiation will begin when data is received.

   3   - Combination of option 1 and option 2.
   255 - Starts negotiation after reset. Ignore HW signals.

        Default Value for Async Channel: 255.
        Default Value for Sync Link:     3"
     ::= { pktSwchPppChanEntry 6 }

pktSwchPppChanMRU OBJECT-TYPE
    SYNTAX  Integer32 (1500..4096)
    MAX-ACCESS  read-write
    STATUS  current
    DESCRIPTION
    "Maximum Receive Unit.
     Size of the packet which is negotiated with the connected device.

     Default value: 1500 ."
    ::= { pktSwchPppChanEntry 7 }

pktSwchPppChanACCM OBJECT-TYPE
    SYNTAX  OCTET STRING (SIZE (4))
    MAX-ACCESS  read-write
    STATUS  current
    DESCRIPTION
    "Async Control Character Map -
     The ACCM value serves as a mask for the first 32 characters
     in the ASCII table.

     Control characters may cause problems when they are transferred
     on the network. This can be handled by escaping them
     ( adding escape character to them ).
     For example , when using modems in the network which can not
     receive X-on and X-off characters. The ACCM is a mask which shows
     which control characters will be handled with an escape sequence.
     Each bit represents one character.

     Possible values:
     Octet string of 4 bytes: 00000000 .
     A bit with value 1 will cause the character to be in an escape sequence.
     0 will leave the character as it is.
     Example : to use XON and XOFF as escape sequence : 000A0000

     Default value: 00000000.
     For Sync Links return the default."
    ::= { pktSwchPppChanEntry 8 }

pktSwchPppChanAuthentication OBJECT-TYPE
    SYNTAX  INTEGER {
       no-authentication(1),
       pap-or-chap      (2),
       chap-only        (3)
    }
    MAX-ACCESS  read-write
    STATUS  current
    DESCRIPTION
        "Port Authentication Type.
         1 - No Authentication: User side Only.
         2 - Configuration of the Host side.
             PAP (Password Authentication Protocol) or
             CHAP (Challenge Handshake Authentication Protocol)
             will be accepted by the current host.
         3 - Configuration of the host side as CHAP only.
             Only CHAP will be accepted by the current host.

         Default value: 1 ."
     ::= { pktSwchPppChanEntry 9 }

pktSwchPppChanInternalClock OBJECT-TYPE
    SYNTAX INTEGER {
       r3000bps (1),
       r4800bps (2),
       r9600bps (3),
       r14400bps(4),
       r19200bps(5),
       r38400bps(6),
       r48Kbps  (7),
       r56Kbps  (8),
       r64Kbps  (9),
       r128Kbps (10),
       r256Kbps (11),
       r384Kbps (12),
       r512Kbps (13),
       r768Kbps (14),
       r1024Kbps(15),
       r1445Kbps(16),
       r2048Kbps(17),
       external(255)
    }
    MAX-ACCESS  read-write
    STATUS  current
    DESCRIPTION
        "The internal clock rate of the MLPPP Link.
         Default value: 9.
         For Async channels: return 255."
     ::= { pktSwchPppChanEntry 10 }

pktSwchPppChanBundle OBJECT-TYPE
    SYNTAX  Integer32 (0..255)
    MAX-ACCESS  read-write
    STATUS  current
    DESCRIPTION
    "Bundle Number.
     It is possible to attach a few channels/links to a bundle.
     If the User enters a non existing bundle number, the PS will
     create a new bundle with this number.
     The bundle number may be: 1..255
     If the bundle number is 0 it means: do not attach to bundle.

     Default value: 0 ."
    ::= { pktSwchPppChanEntry 11 }

pktSwchpPppChanIsdnRoutId OBJECT-TYPE
    SYNTAX   Integer32 (0..200)
    MAX-ACCESS   read-write
    STATUS   current
    DESCRIPTION
       "ISDN destination. ID (1..200) in the ISDN routing table containing
        the outgoing ISDN address for this channel/link.

        For no destination: 0
        Default value: 0 "
    ::= { pktSwchPppChanEntry 12 }


pktSwchpPppChanLastEvent  OBJECT-TYPE
    SYNTAX DisplayString (SIZE (0..80))
    MAX-ACCESS  read-only
    STATUS  current
    DESCRIPTION
        "Status showing the last PPP event which occured on the line
         described in an ascii string.
         Examples:
         1. Received Configuration Request.
         2. Sent Protocol Reject.
         3. Error: Can Not Compress Frame.

         Default: 0 for no last event on this link or channel."
    ::= { pktSwchPppChanEntry 13 }


-- TRAPS for use by the PS

linkProtocolChanged        NOTIFICATION-TYPE
	OBJECTS { pktSwchPhyInterfaceIfIndex, pktSwchPhyInterfaceProtocolA}
    STATUS  current
	DESCRIPTION
	"Upon setting of a new protocol to a specific interface."
	::= { radSysPSEvents 1 }

enrollmentPS        NOTIFICATION-TYPE
    STATUS  current
    DESCRIPTION
    "Periodic trap to be sent to the list of managers."
    ::= { radSysPSEvents 2 }


rtsChange NOTIFICATION-TYPE
    OBJECTS  { pktSwchChannelNumberA }
    STATUS  current
    DESCRIPTION
    " "
    ::= { radSysPSEvents 3 }


ledStatusChange NOTIFICATION-TYPE
    OBJECTS  { agnLed }
    STATUS  current
    DESCRIPTION
    "The trap is sent when one of the Hazard LEDs has changed."
    ::= { radSysPSEvents 4 }
-- 
-- file :v:\doc\rdv\mib\ver485\modem.txt
-- 
--                 MODMSYS MIB	(MODEMS)

--Title:     RAD's Modems MIB
--Version:   1.0
--Date:      24.12.95
--By:        Yair Arian	and Smadar Tauber
--File:      modem.txt
--
--Last update: 15-Apr-2002	 by  Shlomo Shoham 
		  

modmSys  OBJECT IDENTIFIER  ::=  {radWan 4}


modmSystem  OBJECT IDENTIFIER  ::=  {modmSys 1}

modmSa	OBJECT IDENTIFIER  ::=  {modmSystem 1}
modmHub OBJECT IDENTIFIER  ::=  {modmSystem 2}

modmSaConfigTable  OBJECT-TYPE
      SYNTAX SEQUENCE OF ModmSaConfigEntry
      MAX-ACCESS not-accessible
      STATUS  current
      DESCRIPTION
      "Configuration parameters of the Central and Remote Modems.
       The table will be RW for a Central agent and RO for a 
       Remote agent."
       ::= { modmSa 1 }

modmSaConfigEntry OBJECT-TYPE
      SYNTAX ModmSaConfigEntry
      MAX-ACCESS not-accessible
      STATUS current
	DESCRIPTION  "An entry in table."
	INDEX {modmSaConfigMode}
      ::= { modmSaConfigTable 1}

ModmSaConfigEntry ::=
      SEQUENCE {
	  modmSaConfigMode             INTEGER,
	  modmSaConfigLoopback         INTEGER,
	  modmSaConfigAlrClearOnCmd    INTEGER,
	  modmSaConfigAlrClearAllCmd   INTEGER,
	  modmSaConfigTestClearCmd     INTEGER,
	  modmSaConfigClkMaster        INTEGER,
	  modmSaConfigResetStatistics  INTEGER,
	  modmSaConfigActiveTs         Integer32,
	  modmSaConfigReset            INTEGER,
	  modmSaConfigRemote           INTEGER,
	  modmSaConfigPsType	       INTEGER,
	  
	  modmSaConfigWorkMode		   INTEGER	
	  
      }

modmSaConfigMode OBJECT-TYPE
      SYNTAX INTEGER {
                central(1),
      		    remote (2),
				remote2(3),
				remote3(4),
				remote4(5),
				remote5(6),
				remote6(7),
				remote7(8),
				remote8(9),
				remote9(10),
				remote10(11)

		            }
      MAX-ACCESS read-only
      STATUS current
      DESCRIPTION
      "The mode indicates if the configuration parameters refer 
       the Central or the Remote Modem.
       For AMC 102 the remote means regenerator. 
       There can be some regenerators connecting one by the other."
      ::= { modmSaConfigEntry 1}

modmSaConfigLoopback OBJECT-TYPE
      SYNTAX INTEGER {  noLoopback(1),
      					localPortLoop(2),
      					localLineLoop(3),
      					remPortLoop(4)
      				}
      MAX-ACCESS read-write
      STATUS current
      DESCRIPTION
      "The possible loopbacks. It is not possible to have a 
       remPortLoop(4) in both, Central and Remote units 
       simultaneously."
      ::= { modmSaConfigEntry 2}

modmSaConfigAlrClearOnCmd  OBJECT-TYPE
      SYNTAX  INTEGER
	      {
		off(2),
		on (3)
	      }
      MAX-ACCESS  read-write
      STATUS  current
      DESCRIPTION
      "Setting this attribute to on, clears all the events, 
       both from the active alarms list and from the alarms buffer. 
       Upon completion, the value will automatically change to 
       off(2)."
      ::= { modmSaConfigEntry 3 }

modmSaConfigAlrClearAllCmd  OBJECT-TYPE
      SYNTAX  INTEGER
	      {
		off(2),
		on (3)
	      }
      MAX-ACCESS  read-write
      STATUS  current
      DESCRIPTION
      "Setting this attribute to on, clears all the alarms of the
       alarm buffer and active alarms list. Upon completion, the 
       value will automatically change to off(2)."
      ::= { modmSaConfigEntry 4 }

modmSaConfigTestClearCmd  OBJECT-TYPE
      SYNTAX  INTEGER
	      {
		off(2),
		on (3)
	      }
      MAX-ACCESS  read-write
      STATUS  current
      DESCRIPTION
      "Setting this attribute to on, clears all the user-initiated
       tests and loopbacks. The variable modmSaConfigLoopback should
       automatically change to noLoopback. Upon completion, the 
       value will automatically change to off(2)."
      ::= { modmSaConfigEntry 5 }

modmSaConfigClkMaster  OBJECT-TYPE
      SYNTAX  INTEGER
	      {
		external(2),
		internal(3),
		station (4)
	      }
      MAX-ACCESS  read-write
      STATUS  current
      DESCRIPTION
      "Modem configured as Central: 
       External - Locked to the clock signal provided by the user's
                  equipment by user's port.       
       Internal - Internal oscillator.
	   Station  - Station clock (is relevant only for cards).
       Modem configured as Remote: 
       External - Always locked to the recovered receive clock of 
       the HDSL line."
      ::= { modmSaConfigEntry 6 }

modmSaConfigResetStatistics  OBJECT-TYPE
      SYNTAX  INTEGER
	      {
	    off(2),
		on (3),
		notApplicable (255)
	      }
      MAX-ACCESS  read-write
      STATUS  current
      DESCRIPTION
      "In the on state all statistics counters (including E1 
       counters) are zeroed.  Upon completion, the value will 
       automatically change to off(2).
       Modems that do not support statistics - the value will 
       always be off (this object is not applicable for them).
       notApplicable - for modems with no statistics support."
      ::= { modmSaConfigEntry 7 }

modmSaConfigActiveTs  OBJECT-TYPE
      SYNTAX  Integer32 (1..255)
      MAX-ACCESS  read-write
      STATUS  current
      DESCRIPTION
      "This object will be RO for the Remote modem.
       This is the number of active HDSL Time Slots, that 
       determines user's data rate.
       Valid values: 1..maximum supported by the specific modem.
       255 = notApplicable."
      ::= { modmSaConfigEntry 8 }

modmSaConfigReset  OBJECT-TYPE
      SYNTAX  INTEGER
	      {
	    off         (2),
		hw          (3),
		hwAndConfig (4),
		notApplicable (255)
	      }
      MAX-ACCESS  read-write
      STATUS  current
      DESCRIPTION
      "Reset of modem.
	   hw - HW Reset. The configured values will not change.
	   hwAndConfig - HW Reset and initializing the default values.
       notApplicable - for modems with no Reset support.
       After 'hw' or 'hwAndConfig' is Set, agent will turn the 
       value to 'off'."
      ::= { modmSaConfigEntry 9 }

modmSaConfigRemote  OBJECT-TYPE
      SYNTAX  INTEGER
	      {
           notApplicable (1),
		   off           (2),
		   on            (3)
	      }
      MAX-ACCESS  read-write
      STATUS  current
      DESCRIPTION
      "This parameter enables or disables automatic configuration
       of the remote moden in Proxy mode."
      ::= { modmSaConfigEntry 10 }

modmSaConfigPsType OBJECT-TYPE
      SYNTAX  INTEGER
	      {
		  notApplicable (1),
	      ac            (2),
	      dc            (3),
	      ac-dc         (4)
	      }
      MAX-ACCESS  read-only
      STATUS  current
      DESCRIPTION
      "The type of PS."
      ::= {modmSaConfigEntry 11}


modmSaConfigWorkMode OBJECT-TYPE
      SYNTAX INTEGER {
                notApplicable(1),
      		    transparent (2),
				termination(3)
		            }
      MAX-ACCESS read-write
      STATUS current
      DESCRIPTION
      "The work mode indicates if devices work in transparent mode or termination mode."
       
      ::= { modmSaConfigEntry 12}


      

modmSaStatTable  OBJECT-TYPE
      SYNTAX SEQUENCE OF ModmSaStatEntry
      MAX-ACCESS not-accessible
      STATUS  current
      DESCRIPTION
      "Status of the Central and Remote Modems."
       ::= { modmSa 2 }

modmSaStatEntry OBJECT-TYPE
      SYNTAX ModmSaStatEntry
      MAX-ACCESS not-accessible
      STATUS current
	DESCRIPTION  "An entry in table."
	INDEX {modmSaConfigMode}
      ::= { modmSaStatTable 1}

ModmSaStatEntry ::=
      SEQUENCE {
	  modmSaStatHwTest            Integer32,
	  modmSaStatAlarms            OCTET STRING,
	  modmSaStatClkSrc            INTEGER,
	  modmSaStatAlarmsMask        OCTET STRING,
	  modmSaStatDeviceType		  INTEGER,
	  modmSaStatSwVersion		  DisplayString,
	  modmSaStatHwVersion		  DisplayString
      }

modmSaStatHwTest OBJECT-TYPE
      SYNTAX Integer32 
      MAX-ACCESS read-only
      STATUS current
      DESCRIPTION
      "The variable contains the results of the last hardware test.
       It is a sum of 2**n where n is as follows:
       0 - EPROM Failure  (or Database chksum error)
       1 - I/O Expander Error
       2 - Counter Error
       3 - HDSL Framer Failure
       4 - Transceiver Failure
       5 - NVRAM Failure  (applicable only for HCD-E1>=r3) 
       6 - NSFIFO Failure (applicable for HCD-E1>=r3 and HCD-4)
       7 - BERT Failure	  (applicable only for HCD-E1>=r3)
       8 - E1 Framer Failure (applicable only for HCD-E1>=r3)
       9 - XRT Failure    (applicable only for HCD-E1>=r3)
	   10- HDSL Framer 1 Failure (applicable only for HCD-4)
	   11- HDSL Framer 2 Failure (applicable only for HCD-4)
	   12- DSP 1 Failure (applicable only for HCD-4)
	   13- DSP 2 Failure (applicable only for HCD-4)
	   14- XRT 1 Failure (applicable only for HCD-4)
	   15- XRT 2 Failure (applicable only for HCD-4)
       if the variable is 0 then there are No Errors "
      ::= { modmSaStatEntry 1}

modmSaStatAlarms OBJECT-TYPE
      SYNTAX OCTET STRING (SIZE(10)) 
      MAX-ACCESS read-only
      STATUS current
      DESCRIPTION
      "The variable contains the status of the Alarms in the alarm 
       buffer.
       For bit location of each Alarm in the OctetString see Modem's
	   specification.
       If the value is 0 then there are No 'On' Alarms in the alarm 
       buffer."
      ::= { modmSaStatEntry 2}

modmSaStatClkSrc  OBJECT-TYPE
      SYNTAX  INTEGER
    {
        master   (1),
        fallback (2)
	}
      MAX-ACCESS  read-only
      STATUS  current
      DESCRIPTION
     "This entry indicates the source of the modem clock."
      ::= { modmSaStatEntry 3}

modmSaStatAlarmsMask OBJECT-TYPE
      SYNTAX OCTET STRING (SIZE(10)) 
      MAX-ACCESS read-write
      STATUS current
      DESCRIPTION
      "This variable uses to mask alarms.
       Location of each Alarm Mask in the OctetString, 
       is identical to the Alarm OctetString. 
       If the value is 0 then none of the alarms is masked."
      ::= { modmSaStatEntry 4}

modmSaStatDeviceType  OBJECT-TYPE
      SYNTAX  INTEGER
    {
        notApplicable 	 (1),
        amc102SA		 (2),
		amc102Card		 (3)
	}
      MAX-ACCESS  read-only
      STATUS  current
      DESCRIPTION
     "This entry indicates the device type (or utility)."
      ::= { modmSaStatEntry 5}

modmSaStatSwVersion  OBJECT-TYPE
      SYNTAX      DisplayString
      MAX-ACCESS  read-only
      STATUS  current
      DESCRIPTION
      "Display String of the modem SW version.
	   Format: W.      X       Y         Z
	           0..9	   0..99   A,B,E     0..99
		(Z+P are optional.)
		A=alpha, B=beta, E=end of development.
       Examples: 2.23A8 
				 3.4  "
      ::= {modmSaStatEntry 6}

modmSaStatHwVersion	  OBJECT-TYPE
      SYNTAX      DisplayString
      MAX-ACCESS  read-only
      STATUS  current
      DESCRIPTION
      "Display String of the modem HW version."
      ::= {modmSaStatEntry 7}




modmSaAlarmBuffTable  OBJECT-TYPE
      SYNTAX SEQUENCE OF ModmSaAlarmBuffEntry
      MAX-ACCESS not-accessible
      STATUS  current
      DESCRIPTION
      "The alarm buffer of the Central and Remote Modems."
       ::= { modmSa 3 }

modmSaAlarmBuffEntry OBJECT-TYPE
      SYNTAX ModmSaAlarmBuffEntry
      MAX-ACCESS not-accessible
      STATUS current
	DESCRIPTION  "An entry in table."
	INDEX {modmSaConfigMode,modmSaAlarmBuffIndex}
      ::= { modmSaAlarmBuffTable 1}

ModmSaAlarmBuffEntry ::=
      SEQUENCE {
	  modmSaAlarmBuffIndex Integer32,
	  modmSaAlarmBuffCode  Integer32,
	  modmSaAlarmBuffTime  DisplayString,
	  modmSaAlarmBuffState INTEGER
      }

modmSaAlarmBuffIndex OBJECT-TYPE
      SYNTAX Integer32 
      MAX-ACCESS read-only
      STATUS current
      DESCRIPTION
      "The index of the alarm buffer Table."
      ::= { modmSaAlarmBuffEntry 1}

modmSaAlarmBuffCode OBJECT-TYPE
      SYNTAX Integer32
      MAX-ACCESS read-only
      STATUS current
      DESCRIPTION
      "The code of the alarm. For text description of each Alarm 
       code see Modem's	specification."
      ::= { modmSaAlarmBuffEntry 2}

modmSaAlarmBuffTime OBJECT-TYPE
      SYNTAX DisplayString
      MAX-ACCESS read-only
      STATUS current
      DESCRIPTION
      "The time stamp at which the alarm has occurred. The format
       is hh:mm:ss "
      ::= { modmSaAlarmBuffEntry 3}

modmSaAlarmBuffState OBJECT-TYPE
      SYNTAX INTEGER  { off(2),
	                    on(3)
					  }
      MAX-ACCESS read-only
      STATUS current
      DESCRIPTION
      "The new status of the alarm."
      ::= { modmSaAlarmBuffEntry 4}

-- Modem parameters - all parameters refer the Agent itself only

modmSaParam OBJECT IDENTIFIER  ::=  {modmSa 4}

modmSaMode OBJECT-TYPE
      SYNTAX INTEGER  
      { 
      central (1),
	  remote  (2),
	  remote2  (3),
	  remote3  (4),
	  remote4  (5),
	  remote5  (6),
	  remote6  (7),
	  remote7  (8),
	  remote8  (9),
	  remote9  (10),
	  remote10  (11)
	   
  	  }
      MAX-ACCESS read-only
      STATUS current
      DESCRIPTION
      "The agent's current mode.
      For AMC 102 remote means regenerator. 
      There can be some regenerators connecting one by the other."
      ::= {modmSaParam 1}

modmSaFarEndIpAddress OBJECT-TYPE
      SYNTAX IpAddress
      MAX-ACCESS read-write
      STATUS current
      DESCRIPTION
      "The IP address of the agent on the far end. If the Remote 
       modem is NOT an agent, the variable will be 0.0.0.0.
       Set - will be enabled only to a Central modem that works as
             Proxy."
      ::= {modmSaParam 2}

modmSaFarEndType OBJECT-TYPE
      SYNTAX INTEGER  
      { 
      unknown   (1),
	  sa        (2),  --same product as near-end
	  card      (3),  --same product as near-end
	  saLowCost (4),  --same product as near-end
	  hcdSa     (5),
	  hcdSaL    (6),
	  hcdCard   (7),
	  htu2Sa    (8),
	  htu2Card  (9),
	  htuE1Sa  (10),
	  htuE1SaL (11),
	  htuE1Card(12),
	  hcd4Sa   (13),
	  hcdPF    (14),
      unmanaged(100)  --MP/DXC card
  	  }
      MAX-ACCESS read-only
      STATUS current
      DESCRIPTION
      "The type of the Far-End modem."
      ::= {modmSaParam 3}

modmSaRptrType OBJECT-TYPE
      SYNTAX INTEGER  
      { 
	  none    (2), 
	  hrpt    (3),
	  notApplicable (255)
	  }
      MAX-ACCESS read-only
      STATUS current
      DESCRIPTION
      "The Repeater between the Near and Far modem.
       none - no repeater exists between the modems.
       notApplicable - for modems that do not support this feature."
      ::= {modmSaParam 4}

modmSaLearnLineMode OBJECT-TYPE
      SYNTAX INTEGER  
      { 
	  notApplicable (1),
	  manually		(2),
	  automatic		(3)
	  
	  }
      MAX-ACCESS read-write
      STATUS current
      DESCRIPTION
      "This parameter is for the central unit only.
       Indicates if learn the regenerator order and number every time there 
       is a fail in line or manually by user."
       ::= {modmSaParam 5}

modmSaNumOfUnits  OBJECT-TYPE
      SYNTAX  Integer32 
      MAX-ACCESS  read-only
      STATUS  current
      DESCRIPTION
      "This object will hold the number of regenerators in the line."
      ::= {modmSaParam 6}


-- Repeater Table
modmSaRptrTable  OBJECT-TYPE
      SYNTAX SEQUENCE OF ModmSaRptrEntry
      MAX-ACCESS not-accessible
      STATUS  current
      DESCRIPTION
      "The Repeaters parameters known to the central modem."
       ::= { modmSa 5 }

modmSaRptrEntry OBJECT-TYPE
      SYNTAX ModmSaRptrEntry
      MAX-ACCESS not-accessible
      STATUS current
	DESCRIPTION  "An entry in table."
	INDEX {modmSaIndex, modmSaRptrIndex}
      ::= { modmSaRptrTable 1}

ModmSaRptrEntry ::=
      SEQUENCE {
      modmSaIndex                Integer32,
      modmSaRptrIndex            Integer32,
      modmSaRptrTest             INTEGER,
      modmSaRptrActiveAlarms     OCTET STRING,
      modmSaRptrAlrClear         INTEGER,
	  modmSaRptrVersion	         DisplayString
      }

modmSaIndex OBJECT-TYPE
      SYNTAX  Integer32
      MAX-ACCESS  read-only
      STATUS  current
      DESCRIPTION
      "A unique number to identify the modem that reports about the repeater."
      ::= {modmSaRptrEntry 1}

modmSaRptrIndex OBJECT-TYPE
      SYNTAX Integer32
      MAX-ACCESS read-only
      STATUS current
      DESCRIPTION
      "The index of the Repeater."
      ::= { modmSaRptrEntry 2 }

modmSaRptrTest OBJECT-TYPE
      SYNTAX INTEGER {
            none      (1),
            loopLHrpt (2)
          }
      MAX-ACCESS read-write
      STATUS current
      DESCRIPTION
      "The possible loopbacks."
::= { modmSaRptrEntry 3 }

modmSaRptrActiveAlarms OBJECT-TYPE
      SYNTAX OCTET STRING
      MAX-ACCESS read-only
      STATUS current
      DESCRIPTION
      "Status of the Alarms. Each bit represents a specific
       alarm .
       For bit location of each alarm in the
       Octet String see modem's specification.
       If the value is 0 then there are No Alarms."
::= { modmSaRptrEntry 4 }

modmSaRptrAlrClear OBJECT-TYPE
      SYNTAX INTEGER {
            off      (1),
            on       (2)
          }
      MAX-ACCESS read-write
      STATUS current
      DESCRIPTION
      "Setting this attribute to on, clears all the active (On) 
       alarms of the repeater. Upon completion, the value will 
       automatically change to off(2).."
      ::= { modmSaRptrEntry 5 }

modmSaRptrVersion  OBJECT-TYPE
      SYNTAX  DisplayString
      MAX-ACCESS  read-only
      STATUS  current
      DESCRIPTION
      "SW/HW version of the repeater"
      ::= { modmSaRptrEntry 6 }
 
       
--modmHub OBJECT IDENTIFIER  ::=  {modmSystem 2}

--Modem - Hub Parameters

modmHubParam OBJECT IDENTIFIER  ::=  {modmHub 1}

modmHubTermConnect OBJECT-TYPE
      SYNTAX INTEGER  
              {
                no  (2),
                yes (3)
              }
      MAX-ACCESS read-only
      STATUS current
      DESCRIPTION
      "Status: is the Terminal connected or not."
      ::= {modmHubParam 1}

modmHubController OBJECT-TYPE
      SYNTAX INTEGER  
              {
                nms      (1),
                terminal (2)
              }
      MAX-ACCESS read-write
      STATUS current
      DESCRIPTION
      "Selection of Hub controller during normal operation. If 
       'terminal' is selected, NMS can still return control to 
       itself by setting this object to 'nms'. While terminal is
       the controller, NMS can perform Get operations and Set trap
       masks."
      ::= {modmHubParam 2}

modmHubId OBJECT-TYPE
      SYNTAX OCTET STRING (SIZE(2))  
      MAX-ACCESS read-write
      STATUS current
      DESCRIPTION
      "4 Hex characters, identifying the Hub. The last two 
       characters (least significant) will be displayed on the 
       Hub's CL card by a 7 segment display."
      ::= {modmHubParam 3}

modmHubT1E1 OBJECT-TYPE
      SYNTAX INTEGER  
              {
                other (1),
                t1    (2),
				e1    (3)
              }
      MAX-ACCESS read-only
      STATUS current
      DESCRIPTION
      "The T1/E1 value determines the Hub's clock rate."
      ::= {modmHubParam 4}

modmHubClockSource OBJECT-TYPE
      SYNTAX INTEGER  
              {
                other         (1),
                external      (2),
				internal      (3),
				g703Section10 (4),
				receive       (5),
				station       (6)
              }
      MAX-ACCESS read-write
      STATUS current
      DESCRIPTION
      "Clock source."
      ::= {modmHubParam 5}

modmHubClockRate OBJECT-TYPE
      SYNTAX INTEGER  
              {
                e1r2048000 (1),
                e1r1024000 (2),
				e1r512000  (3),
				e1r256000  (4),
				e1r128000  (5),
				e1r64000   (6),
				e1r32000   (7),
				e1r16000   (8),
				e1r8000    (9),

                t1r1544000 (31),
				t1r772000  (32),
				t1r386000  (33),
				t1r193000  (34),
				t1r96500   (35),
				t1r48250   (36),

                notApplicable (255)
              }
      MAX-ACCESS read-write
      STATUS current
      DESCRIPTION
      "Clock Rate in bps. The rates are the original T1/E1 rates
       or the rates divided by 2n.
       For modmHubT1E1=e1, instances (1)-(9) are applicable.
       For modmHubT1E1=t1, instances (31)-(36) are applicable.
       For modmHubT1E1=other, instance (255) is applicable."
      ::= {modmHubParam 6}

modmHubIpMode OBJECT-TYPE
      SYNTAX INTEGER  
              {
                single        (1), 
                multi         (2)
              }
      MAX-ACCESS read-write
      STATUS current
      DESCRIPTION
      "single - Upon BootP request from S-MOD, CM-2 will 
       assign a 'private IP' (CM-2 IP + slot number of S-MOD),
       which will be applicable only between the S-MOD and CM-2.
       multi - CM-2 assigns up to 12/24 consequent IP addresses. 
       One for each S-MOD according to the slot number."
      ::= {modmHubParam 7}

modmHubInstallation OBJECT-TYPE
      SYNTAX OCTET STRING  
      MAX-ACCESS read-write
      STATUS current
      DESCRIPTION
      "The string will be a multiple set of 16 bit corresponds 
      to its card position, and each set corresponds to a modem, 
      where set #1 is the first modem on each card, and set n is 
      the n-st modem in each card.
     
      1........10.....16|1........10.....16|
        modem 1         |    modem 2       |

      MSB								LSB  

      Bits 1-3 and 16 will be ignored.
      For LRS-52 detailed bit assignment see product's spec."
      ::= {modmHubParam 8}


--Modem - Hub Alarms

modmHubAlarms OBJECT IDENTIFIER  ::=  {modmHub 2}

modmHubActiveAlarms OBJECT-TYPE
      SYNTAX OCTET STRING  
      MAX-ACCESS read-only
      STATUS current
      DESCRIPTION
      "Status of the Alarms for each Slot. Each bit represents a 
       Slot of the Hub. For bit location of each Alarm in the 
       Octet String see Hub's specification.
	   A bit is '1' (On) if at least one 'On' alarm exists for this
	   Slot.
       If the value is 0 then there are No 'On' Alarms in any Slot.
       For LRS52  - read 'modem' instead of the word 'slot'"
      ::= {modmHubAlarms 1}

modmHubAlrClear  OBJECT-TYPE
      SYNTAX  INTEGER
	      {
		off(2),
		on (3)
	      }
      MAX-ACCESS  read-write
      STATUS  current
      DESCRIPTION
      "Setting this attribute to on, clears all the active (On) 
       alarms of the Hub. Upon completion, the value will 
       automatically change to off(2)."
      ::= {modmHubAlarms 2}

modmHubMaskAlarms OBJECT-TYPE
      SYNTAX OCTET STRING  
      MAX-ACCESS read-write
      STATUS current
      DESCRIPTION
      "Mask of Alarms per Slot. Each bit represents a 
       Slot of the Hub. For bit location of each Slot in the 
       Octet String see Hub's specification (same as 
       modmHubActiveAlarms).
	   When a bit is '1' (On) it is masked ; all alarms of this Slot
	   should not be sent and Alarm LED should not be lit. This 
	   mask overrides the mask on the specific alarms of each Slot
	   or modem.
	   If the value is 0 then all alarms should be sent.
	   For LRS52  - read 'modem' instead of the word 'slot'."
      ::= {modmHubAlarms 3}


modmMdl  OBJECT IDENTIFIER  ::=  {modmSys 2}

modmMdlParam OBJECT IDENTIFIER  ::=  {modmMdl 1}

mdlParamTable  OBJECT-TYPE 
      SYNTAX SEQUENCE OF MdlParamEntry
      MAX-ACCESS not-accessible
      STATUS  current
      DESCRIPTION
      "Parameters table of cards in the Hub."
      ::= { modmMdlParam 1 }

mdlParamEntry OBJECT-TYPE
      SYNTAX MdlParamEntry
      MAX-ACCESS not-accessible
      STATUS current
	DESCRIPTION  "An entry in table."
	INDEX { mdlSIdx }
      ::= { mdlParamTable 1}

MdlParamEntry ::=
      SEQUENCE {
      mdlSIdx               INTEGER,
	  mdlSNoOfModems        Integer32,
      mdlCardType           INTEGER,
      mdlSPanelType         INTEGER,
	  mdlSLed               OCTET STRING,
	  mdlSActiveAlarms      OCTET STRING,
	  mdlAlrClear           INTEGER,
	  mdlSConfigMismatch    INTEGER,
	  mdlConfigSource       INTEGER,
	  mdlConfigGround       INTEGER
      }

mdlSIdx OBJECT-TYPE
      SYNTAX  INTEGER
	      {
	      psA   (1),
	      psB   (2),
	      cl    (3),
	      io1   (4),
	      io2   (5),
	      io3   (6),
	      io4   (7),
	      io5   (8),
	      io6   (9),
	      io7  (10),
	      io8  (11),
	      io9  (12),
	      io10 (13),
	      io11 (14),
	      io12 (15)
	      }
      MAX-ACCESS  read-only
      STATUS  current
      DESCRIPTION
      "A unique number to identify a slot position in the modems 
       Hub."
      ::= { mdlParamEntry 1}


mdlSNoOfModems  OBJECT-TYPE
      SYNTAX  Integer32
      MAX-ACCESS  read-only
      STATUS  current
      DESCRIPTION
      "Number of modems on this card.
       255 = notApplicable. "
      ::= { mdlParamEntry 2 }


mdlCardType  OBJECT-TYPE
      SYNTAX  INTEGER
	      {
		unknown   (1),
		empty     (2),
		ps48V     (3),
		ps110V    (4),
		ps230V    (5),
		cm2       (6),
		smod      (7),
		asmi24    (8),
		asmi31    (9),
		asmi32    (10),
		asmi50    (11),
		mtmi20    (12),
		fomi40    (13),
		fomiE1T1  (14),
		asm40cd     (15),
		asmi50cd    (16),
		fomi40cd    (17),
		fomiE1T1cd  (18),
        ps110V-24   (19),
		ps230V-24   (20),
		ps48V-24    (21),
		asmi31cq    (22),
		asmi51cq    (23),
		asmi51cd    (24),
		asmi52cd    (25),
		asmi52cq    (26),

--SMODs
		fomiE3      (51),
		fomiT3      (52),
		optimux4E1  (53),
		optimux4T1  (54),
		amc102		(55),

		notApplicable (255)
	      }
      MAX-ACCESS  read-only
      STATUS  current
      DESCRIPTION
      "Card's type."
      ::= { mdlParamEntry 3 }


mdlSPanelType  OBJECT-TYPE
      SYNTAX  INTEGER
	      {
		empty           (1),
		f2              (2),   --rj45AndDb25
		f3              (3),   --rj45AndG703
		f5              (5),   --2*rj45And2*26HD
		f6              (6),   --rj45+2BNCAnd2*26HD
		f7              (7),   --asmi32
		f9              (9),   --rj45AndV35
		f10            (10),   --rj45AndRj45 
		f11            (11),   --rj45And2rj45
		f12            (12),   --rj45AndX21
		f13            (13),   --2*rj45And2*rj45
		f14            (14),   --2*4381And2*rj45
		f18            (15),   --scsi68And4*rj11
		f19            (16),   --scsi68And4*TB
		f22            (17),   --iripRj45
		f20			   (18),   --4TB2And4RJ45 for CQ
		f21			   (19),   --4TB2AndDB25 for CQ
		f23			   (20),   --2RJ45And2IP for CD	

-- Panels with an Optical connector
        fO1            (21),   --stAndDb25
        fO2            (22),   --stAndV35
        fO3            (23),   --stAndDb15
        fO4            (24),   --stAndG703
        fO5            (25),   --scAndDb25
        fO6            (26),   --scAndV35
        fO7            (27),   --scAndDb15
        fO8            (28),   --scAndG703
        fO9            (29),   --stAndEthernet
        fO10           (30),   --scAndEthernet
        fO11           (31),   --2*st/fcAnd2*SCSI
        fO12           (32),   --2*st/fcAnd2*rj45
        fO13           (33),   --2*scAnd2*SCSI
        fO14           (34),   --2*scAndr2*j45
        fO15           (35),   --(2*st/fcAnd2*4381)eth
        fO16           (36),   --(2*scAnd2*4381)eth 
        fO17           (37),   --(2*st/fcAndBNC)e3/t3 
        fO18           (38),   --(2*scAndBNC)e3/t3 
        fO19           (39),   --(2*st/fcAnd2*bnc)wdm
        fO20           (40),   --(2*scAnd2*scsi)wdm 
        fO21           (41),   --(4*MBNC And 2*st/fc)e1/t1 
        fO22           (42),   --(4*MBNC And 2*sc)e1/t1 


--Power Supply panels
		ps230And115    (81),   --PS 230V, 115V without phantom
		psp230And115   (82),   --PS 230V, 115V with phantom
		ps48           (83),   --PS 48V without phantom
		psp48          (84),   --PS 48V with phantom

--Panels of CM2 card (CL)
		f1Cm2          (91),   --CM2 UTP
		f2Cm2          (92),   --CM2 BNC
		f3Cm2          (93),   --CM2 V35
		f4Cm2          (94),   --CM2 RS-530
		f5Cm2          (95),   --CM2 X21
		f1Cm2New	   (96),   --CM2 UTP with embedded LEDs
		notApplicable (255)
	      }
      MAX-ACCESS  read-only
      STATUS  current
      DESCRIPTION
      "LRS-12 Card connectors' panel type.
       fx    - IMOD panels
       psxxx - PS panels
       fxCm2 - CM-2 panels."
      ::= { mdlParamEntry 4 }

mdlSLed  OBJECT-TYPE   
      SYNTAX  OCTET STRING 
      MAX-ACCESS  read-only
      STATUS  current
      DESCRIPTION
	  "LEDs status on the card . Each led will be represented by 4 
	   bits where the first 2 bits (left) will specify  the Status :
	   (00=NA, 01=OFF, 10=ON, 11=BLINK),
       and the next two bits (right) will specify the Color :
       (00=GREEN, 01=RED, 10=YELLOW, 11=ORANGE).
       This object is not applicable for the 'smod', 'empty' and 
       'unknown' card types. For them 0 will be sent. "
      ::= { mdlParamEntry 5}

mdlSActiveAlarms OBJECT-TYPE
      SYNTAX OCTET STRING  
      MAX-ACCESS read-only
      STATUS current
      DESCRIPTION
      "This object is applicable only for PS and CL cards.
       It gives the status of the Alarms for each Slot. Each bit 
       represents an alarm in the slot. For bit location of each 
       Alarm in the Octet String see Hub's specification.
	   A bit is '1' if the alarm is On. 
	   If the value is 0 then there are No 'On' Alarms in the Slot."
      ::= {mdlParamEntry 6}

mdlAlrClear  OBJECT-TYPE
      SYNTAX  INTEGER
	      {
		off(2),
		on (3)
	      }
      MAX-ACCESS  read-write
      STATUS  current
      DESCRIPTION
      "Setting this attribute to on, clears all the active (On) 
       alarms of the Slot. Upon completion, the value will 
       automatically change to off(2)."
      ::= {mdlParamEntry 7}

mdlSConfigMismatch  OBJECT-TYPE
      SYNTAX  INTEGER
	      {
		off   (2),
		on    (3),
		line1 (4),
		line2 (5),
		notApplicable (255)
	      }
      MAX-ACCESS  read-only
      STATUS  current
      DESCRIPTION
      "This object is applicable only for slots containing 
       IMOD cards.
       ON - when CM-2 realizes that the configuration of the 
            Near-End modem1 is different from that of its Far-End 
            modem. 
            In this case it expects user to decide which of the 
            modems' configuration is the correct one (by 
            'mdlConfigSource'), or change the incorrect modem 
            configuration.  
			When one of these conditions is fulfilled, the value 
			will automatically turn to OFF. Applicable for a single 
			modem.
       Line1 - The same as for ON but for modem-1 line. Applicable 
            for a double modem.
       Line2 - The same as for ON but for modem-2 line. Applicable
            for a double modem.
       OFF - Near-End and Far-End modems have the same 
            configuration (OK). "
      ::= {mdlParamEntry 8}

mdlConfigSource  OBJECT-TYPE
      SYNTAX  INTEGER
	      {
		nearEnd (1),
		farEnd  (2),
		nearEnd2 (3),
		farEnd2  (4),
		notApplicable (255)
	      }
      MAX-ACCESS  read-write
      STATUS  current
      DESCRIPTION
      "This object is applicable only for slots containing 
       IMOD cards, when mdlSConfigMismatch=on/on1/on2.
       nearEnd - Near End - 1 modem has the correct configuration
       farEnd  - Far  End - 1 has the correct configuration  
       nearEnd - Near End - 2 has the correct configuration
       farEnd  - Far  End - 2 has the correct configuration."
      ::= {mdlParamEntry 9}

mdlConfigGround OBJECT-TYPE
      SYNTAX  INTEGER
	      {
	       notApplicable (1),
		   disconnect    (2),
		   connect       (3)
	      }
      MAX-ACCESS  read-only
      STATUS  current
      DESCRIPTION
      "Enables to connect or disconnect an IMOD card to the 
        ground.
       disconnect    -  not connected to ground.
       connect       -  connected to ground.
       notApplicable -  for other cards."
      ::= {mdlParamEntry 10}

--mdlConfigRedundancy OBJECT-TYPE
--      SYNTAX  INTEGER
--	      {
--	      notApplicable (1),
--		 disable (2),
--		 enable (3)
--	      }
--      MAX-ACCESS  read-write
--      STATUS  current
--      DESCRIPTION
--      "PS of the SA modem and/or repeaters that are connected
--       to the specific module."
--      ::= {mdlParamEntry 12}



--Modem data - the modem can either belong to the Hub or
--             be a Far-End modem connected to a modem of 
--             the Hub.	The data applies only for IMOD cards.
--             This table is used also by DXC, for data about 
--             far unit	of each external port of DSL16 card.
--             For DXC, modemIdx=ifIndex of External port of DSL16.

modem    OBJECT IDENTIFIER  ::=  {modmSys 3}

modemParam OBJECT IDENTIFIER  ::=  {modem 1}

modemParamTable  OBJECT-TYPE 
      SYNTAX SEQUENCE OF ModemParamEntry
      MAX-ACCESS not-accessible
      STATUS  current
      DESCRIPTION
      "This parameters table is applicable only for modems that are
       not agents."
      ::= { modemParam 1 }

modemParamEntry OBJECT-TYPE
      SYNTAX ModemParamEntry
      MAX-ACCESS not-accessible
      STATUS current
	DESCRIPTION  "An entry in table."
	INDEX { modemIdx }
      ::= { modemParamTable 1}

ModemParamEntry ::=
      SEQUENCE {
      modemIdx                 Integer32,
	  modemType                INTEGER,
	  modemConfigMode          INTEGER,
	  modemModeTemporary       INTEGER,
	  modemNoOfDte             Integer32,
	  modemWire                INTEGER,
      modemMngLink			   INTEGER,
	  modemReset     		   INTEGER,
	  modemSlot                INTEGER,
	  modemHubId               OCTET STRING,
	  modemIpAddress           IpAddress,
	  modemPsType              INTEGER,
	  modemMaskTraps           Integer32,
	  modemActiveAlarms		   OCTET STRING,
	  modemAlrClear			   INTEGER,
	  modemAlrBufClear		   INTEGER,
	  modemMaskSignaling       OCTET STRING,
	  modemPanelType           INTEGER,
	  modemIType               INTEGER,
	  modemRcvPower            Integer32,
	  modemSwVersion           Integer32,
	  modemLed                 OCTET STRING,
	  modemRemoteType          INTEGER,
	  modemConfigPhantom       INTEGER,
	  modemRemoteTestEnable    INTEGER,
	  modemSwVerString		   DisplayString,
	  modemRemoteIdx		   Integer32,
	  modemHwVerString		   DisplayString,
	  modemResetStatistics	   INTEGER,
	  modemMaxRate             INTEGER,
	  modemBoxMaterial 		   INTEGER
      }

modemIdx OBJECT-TYPE
      SYNTAX  Integer32
      MAX-ACCESS  read-only
      STATUS  current
      DESCRIPTION
      "For LRS:
         A unique number to identify a modem in the Hub or its 
         far-end modem.
       For DXC:
         This will be the ifIndex of the External Port of DSL16 card,
         that works with this modem/product."
      ::= {modemParamEntry 1}

modemType OBJECT-TYPE
      SYNTAX  INTEGER
	      {
	       unknown    (1),
	       asmi24c    (2),
		   asmi31c    (3),
		   asmi32c    (4),
		   asmi50c    (5),
		   mtmi20c    (6),
		   fomi40c    (7),
		   fomiE1T1c  (8), 
		   asm40cd    (9),
		   asmi31cq   (10),
		   asmi51cq   (11),
		   asmi51cd   (12),
		   asmi52cq   (13),
		   asmi52cd   (14),

	       asmi24r    (22),
		   asmi31r    (23),
		   asmi32r    (24),
		   asmi50r    (25),
		   mtmi20r    (26),

	       asmi24     (42),
		   asmi31     (43),
		   asmi32     (44),
		   asmi50     (45),
		   mtmi20     (46),
		   fomi40     (47),
		   fomiE1T1   (48),
		   asmi51     (49),
		   asmi52S    (50),	 --Slave
		   asmi52M    (51),	 --Master

           lrs52      (71)
 	      }
      MAX-ACCESS  read-only
      STATUS  current
      DESCRIPTION
      "Modem type.
       xxxxxx  - Stand-Alone modem.
       xxxxxxc - Modem on a Card within a Hub having an Agent.
       xxxxxxr - Modem on a Card within a Hub having no Agent.
       xxxxxxcd - Modem on a Double-Modem Card within a Hub  
                  having an Agent. Each modem has it's own CPU.
       xxxxxxcq - Modem on a Quad-Modem Card within a Hub  
                  having an Agent. One CPU for all modems.
       lrs52 - Modem within the LRS-52 device."
      ::= {modemParamEntry 2}

modemConfigMode OBJECT-TYPE
      SYNTAX INTEGER {
                master (1),
      		    slave  (2)
		            }
      MAX-ACCESS read-write
      STATUS current
      DESCRIPTION
      "The mode identifies if the Modem operates as the Master 
       unit or as the Slave unit.
       For modems having a jumper for this function, this object 
       will be RO. 
	   This object can be Set only to the Master unit when 
	   modemModeTemporary=no (the Far-End unit will receive its 
	   new mode from the Central unit, via management link 
	   between the modems).	   
	   Regarding other objects (except modemModeTemporary):
       If Modem is Master, it can perform RW operations for 
       both Master and Slave modem. 
       If Modem is Slave, it can perform RO operations for 
       both Master and Slave modem." 
      ::= {modemParamEntry 3}

modemModeTemporary OBJECT-TYPE
      SYNTAX INTEGER {
                no  (2),
      		    yes (3)
		            }
      MAX-ACCESS read-write
      STATUS current
      DESCRIPTION
      "This object specifies if the Modem operates as 
       modemConfigMode value (Master/Slave) temporarily or
       permanently. 
	   This object can be Set only when:
	   - modemConfigMode=master AND modemModeTemporary=no
	   - modemConfigMode=slave  AND modemModeTemporary=yes
	     this is an exception to the fact that all other objects
		 in this case are RO.
	   The other unit will receive its value for this object
	   from the Set unit, via management link between the modems." 
      ::= {modemParamEntry 4}

modemNoOfDte OBJECT-TYPE
      SYNTAX  Integer32
      MAX-ACCESS  read-only
      STATUS  current
      DESCRIPTION
      "Number of DTE ports in the modem."
      ::= {modemParamEntry 5}

modemWire OBJECT-TYPE
      SYNTAX  INTEGER
	      {
          w2wire   (1),
          w4wire   (2),
		  notApplicable (255)
	      }
      MAX-ACCESS  read-write
      STATUS  current
      DESCRIPTION
      "Modem wiring."
      ::= {modemParamEntry 6}

modemMngLink  OBJECT-TYPE
      SYNTAX  INTEGER
	      {
		off(2),
		on (3)
	      }
      MAX-ACCESS  read-only
      STATUS  current
      DESCRIPTION
      "Communication status between the pair of modems."
      ::= {modemParamEntry 7}

modemReset  OBJECT-TYPE
      SYNTAX  INTEGER
	      {
           off        (2),
           hwReset    (3),
		   configReset(4)
             }
      MAX-ACCESS  read-write
      STATUS  current
      DESCRIPTION
      "When this object is set to the value of hwReset(3),
       the module performs HW Reset. 
	   When this object is set to the value of configReset(4),
       the modem performs Configuration Reset, which will set 
       the modem to the last parameters it was configured."
      ::= {modemParamEntry 8}

modemSlot OBJECT-TYPE
      SYNTAX  INTEGER
	      {
	      io1   (4),
	      io2   (5),
	      io3   (6),
	      io4   (7),
	      io5   (8),
	      io6   (9),
	      io7  (10),
	      io8  (11),
	      io9  (12),
	      io10 (13),
	      io11 (14),
	      io12 (15),
	      io13 (16),
	      io14 (17),
	      io15 (18),
		  notApplicable (255)
	      }
      MAX-ACCESS  read-only
      STATUS  current
      DESCRIPTION
      "A unique number to identify the slot position of the  
       modem (card)in its Hub.
       notApplicable - for a stand-alone modem or Rack 214
                       card.
       io13..io15 - are for DXC use in case of a Far-Unit that is DSL16 card."
      ::= {modemParamEntry 9}

modemHubId OBJECT-TYPE
      SYNTAX OCTET STRING (SIZE(2))  
      MAX-ACCESS read-only
      STATUS current
      DESCRIPTION
      "4 Hex characters, identifying the Hub. The last two 
       characters (least significant) will be displayed on the 
       Hub's CL card by a 7 segment display.
       This object is applicable only for LRS-12 modems."
      ::= {modemParamEntry 10}

modemIpAddress OBJECT-TYPE
      SYNTAX IpAddress
      MAX-ACCESS read-only
      STATUS current
      DESCRIPTION
      "For LRS:
       The IP address of the LRS-12 agent . If the modem is NOT 
       an LRS-12 card, the variable will be 0.0.0.0.
       For DXC: the IP Address of the Far-End unit."
      ::= {modemParamEntry 11}

modemPsType OBJECT-TYPE
      SYNTAX  INTEGER
	      {
	      ac   (1),
	      dc   (2),
		  notApplicable (255)
	      }
      MAX-ACCESS  read-only
      STATUS  current
      DESCRIPTION
      "The type of PS, for a stand-alone modem. 
       notApplicable - for LRS-12 or Rack 214 card."
      ::= {modemParamEntry 12}

modemMaskTraps OBJECT-TYPE
      SYNTAX  Integer32
      MAX-ACCESS  read-write
      STATUS  current
      DESCRIPTION
      "The value determines the modem traps the agent should mask 
       and not send to the management console. 
       The value is a sum of 2**n, where n is a bit assigned to a 
       certain trap. For bit assignment see modem's specification.
       Value of '0', means that no trap should be masked."
      ::= {modemParamEntry 13}

modemActiveAlarms OBJECT-TYPE
      SYNTAX OCTET STRING  
      MAX-ACCESS read-only
      STATUS current
      DESCRIPTION
      "Status of the Alarms for each modem. Each bit represents an 
       alarm. For bit location of each Alarm in the Octet String 
       see modem's specification.
	   A bit is '1' if the alarm is On.
       If the value is 0 then there are no 'On' alarms on this
       modem."
      ::= {modemParamEntry 14}

modemAlrClear  OBJECT-TYPE
      SYNTAX  INTEGER
	      {
		off(2),
		on (3)
	      }
      MAX-ACCESS  read-write
      STATUS  current
      DESCRIPTION
      "Setting this attribute to on, clears all the active (On) 
       alarms of the modem. Upon completion, the value will 
       automatically change to off(2)."
      ::= {modemParamEntry 15}

modemAlrBufClear  OBJECT-TYPE
      SYNTAX  INTEGER
	      {
		off(2),
		on (3)
	      }
      MAX-ACCESS  read-write
      STATUS  current
      DESCRIPTION
      "Setting this attribute to on, clears all the alarms in the 
       buffer alarm of the modem. Upon completion, the value will 
       automatically change to off(2)."
      ::= {modemParamEntry 16}

modemMaskSignaling OBJECT-TYPE
      SYNTAX OCTET STRING  
      MAX-ACCESS read-write
      STATUS current
      DESCRIPTION
      "Mask of Signals per modem. When a signal is masked,  
	   the agent will not send the modemSignalingChange TRAP, upon 
	   change of this signal's value and it will not enter 
	   the History Log. 
       Each bit represents a signal of the modem. 
       For bit location of each signal in the Octet String see 
       modem's specification.
	   When a bit is '1' (On) it is masked ."
      ::= {modemParamEntry 17}

modemPanelType OBJECT-TYPE
      SYNTAX  INTEGER
	      {
	      f2      (2),   --rj45AndDb25
	   	  f3      (3),   --rj45AndG703
		  f7      (7),   --asmi32
		  f9      (9),   --rj45AndV35
		  f10    (10),   --rj45AndRj45 
		  f11    (11),   --rj45And2rj45
		  f12    (12),   --rj45AndX21

-- Panels with an Optical connector
          fO1    (21),   --stAndDb25
          fO2    (22),   --stAndV35
          fO3    (23),   --stAndDb15
          fO4    (24),   --stAndG703
          fO5    (25),   --scAndDb25
          fO6    (26),   --scAndV35
          fO7    (27),   --scAndDb15
          fO8    (28),   --scAndG703
          fO9    (29),   --stAndEthernet
          fO10   (30),   --scAndEthernet

	      pcu   (101),
	      lcd   (102),
		  notApplicable (255)
	      }
      MAX-ACCESS  read-only
      STATUS  current
      DESCRIPTION
      "The panel type of the modem.
       This parameter is applicable only for Far-End modems that 
       are stand-alone or cards of another LRS-12. It enables 
       displaying the correct panel of the modem.
       - Stand-alone : applicable only for ASMi-24 and ASMi-50 
         modems.
              pcu - with connector for Portable Control Unit 
              lcd - LCD display and buttons.
       - LRS-12 card : fx is the connectors panel of the modem. "
      ::= {modemParamEntry 18}

modemIType  OBJECT-TYPE
      SYNTAX  INTEGER
	      {
		notApplicable (1),
		no            (2),
		yes           (3)
	      }
      MAX-ACCESS  read-write
      STATUS  current
      DESCRIPTION
      "Is the modem Intelligent (ASMi-xx) ; or not - (ASM-xx).
       This object is used only for the Far-End modem (with the 
       relevant modemIdx).
       notApplicable - for ASMi-32, ASMi-50
       no -  modem is NOT I-Type so it doesn't have a management 
             link to its pair-modem.
       yes - modem is I-Type so it has a management link to its 
             pair-modem."
      ::= {modemParamEntry 19} 

modemRcvPower  OBJECT-TYPE
      SYNTAX  Integer32
      MAX-ACCESS  read-only
      STATUS  current
      DESCRIPTION
      "The Rx Level of the modem, in dBm.
       Valid values: -99 .. 0.
       255=not applicable. "
      ::= {modemParamEntry 20}
      
modemSwVersion  OBJECT-TYPE
      SYNTAX  Integer32
      MAX-ACCESS  read-only
      STATUS  current
      DESCRIPTION
      "SW version of the modem, multiplied by 100.
	   Example: 115 means SW ver: 1.15
       0 = notApplicable. "
      ::= {modemParamEntry 21}
 
modemLed  OBJECT-TYPE   
      SYNTAX  OCTET STRING 
      MAX-ACCESS  read-only
      STATUS  current
      DESCRIPTION
	  "LEDs status on the card . Each led will be represented by 4 
	   bits where the first 2 bits (left) will specify  the Status :
	   (00=NA, 01=OFF, 10=ON, 11=BLINK),
       and the next two bits (right) will specify the Color :
       (00=GREEN, 01=RED, 10=YELLOW, 11=ORANGE).
       This object is applicable for modems located on a card that contains
       more than one modem. When not applicable 0 will be sent. "
      ::= { modemParamEntry 22}

modemRemoteType  OBJECT-TYPE
      SYNTAX  INTEGER
	      {
		notApplicable     (1),
		unknown           (2),
		sa                (3),
		single            (4),
		double            (5),
		rack              (6),
		quad              (7),
		saSlave           (8),
		fcd               (9),
		dxcCard4p        (10), --DXC30 4 links - D4GSL
		dxcCard8p        (11),  --DXC30 8 links - D8GSL
		lrs52			 (12)
	      }
      MAX-ACCESS  read-only
      STATUS  current
      DESCRIPTION
      "Remote modem card type. Not applicable to near - end modems.
       For LRS-52, sa(3)=saMaster."
      ::= {modemParamEntry 23}

modemConfigPhantom OBJECT-TYPE
      SYNTAX  INTEGER
	      {
	      notApplicable (1),
	      off           (2),
		  on            (3),
		  notValid      (4)
	      }
      MAX-ACCESS  read-write
      STATUS  current
      DESCRIPTION
      "Enables to supply electric power to remote devices (SA modem,  
       repeaters), through the current module.
       off - remote devices will not get PS through the current modem.
       on  - remote devices will get PS through the current modem.
       notApplicable - for a modem without a phantom unit.
       notValid - In case the unit exists but is not functioning."
      ::= {modemParamEntry 24}

modemRemoteTestEnable OBJECT-TYPE
      SYNTAX INTEGER {
	            notApplicable (1),
                no   (2),
      		    yes  (3)
		            }
      MAX-ACCESS read-write
      STATUS current
      DESCRIPTION
      "This parameter identifies if the remote Modem allowed to operates 
       tests.
       For Near-End modems this parameter will be ON." 
      ::= {modemParamEntry 25}

modemSwVerString  OBJECT-TYPE
      SYNTAX      DisplayString
      MAX-ACCESS  read-only
      STATUS  current
      DESCRIPTION
      "Display String of the modem SW version.
	   Format: X.      Y       Z         P
	           0..9	   0..99   A,B,E     0..99
		(Z+P are optional.)
		A=alpha, B=beta, E=end of development.
       Examples: 2.23A8 
				 3.4  "
      ::= {modemParamEntry 26}

modemRemoteIdx  OBJECT-TYPE
      SYNTAX  Integer32
      MAX-ACCESS  read-only
      STATUS  current
      DESCRIPTION
      "0 = notApplicable.
       For LRS: 
         The Remote modem index.
         Applicable only for modemRemoteType=double(5) or quad(7). 
       For DXC and LRS-52:
         - if Remote unit is an LRS Quad card: remote modem index (1..4)
         - if Remote unit is a DXC DSL16 card: external port index (1..16).
		 - if Remote unit is an LRS-52 modem: 1..24."
      ::= {modemParamEntry 27}

modemHwVerString  OBJECT-TYPE
      SYNTAX      DisplayString
      MAX-ACCESS  read-only
      STATUS  current
      DESCRIPTION
      "Display String of the modem HW version."
      ::= {modemParamEntry 28}

modemResetStatistics  OBJECT-TYPE
      SYNTAX  INTEGER
	      {
	    notApplicable (1),
	    off(2),
		on (3)
	      }
      MAX-ACCESS  read-write
      STATUS  current
      DESCRIPTION
      "In the on state all statistics counters (including E1 
       counters) are zeroed.  Upon completion, the value will 
       automatically change to off(2).
       notApplicable - for modems with no statistics support."
      ::= {modemParamEntry 29}

modemMaxRate        OBJECT-TYPE
      SYNTAX  INTEGER
	  {
	  notApplicable (1),
	  r2Mbps        (2),
	  r4Mbps        (3)
	  }
      MAX-ACCESS  read-only
      STATUS  current
      DESCRIPTION
      "Maximum rate supported by the modem "
      ::= {modemParamEntry 30}


modemBoxMaterial        OBJECT-TYPE
      SYNTAX  INTEGER
	  {
	  notApplicable  (1),
	  plastic        (2),
	  metal          (3)
	  }
      MAX-ACCESS  read-only
      STATUS  current
      DESCRIPTION
      "Shape (picture) of modem box is related to box material.
       Applicable for ASMi52 SA "
      ::= {modemParamEntry 31}


modemAlrBuffer OBJECT IDENTIFIER  ::=  {modem 2}

modemAlrBufTable  OBJECT-TYPE 
      SYNTAX SEQUENCE OF ModemAlrBufEntry
      MAX-ACCESS not-accessible
      STATUS  current
      DESCRIPTION
      "This parameters table is applicable only for modems that are
       not agents."
      ::= { modemAlrBuffer 1 }

modemAlrBufEntry OBJECT-TYPE
      SYNTAX ModemAlrBufEntry
      MAX-ACCESS not-accessible
      STATUS current
	DESCRIPTION  "An entry in table."
	INDEX { modemIdx, modemAlrBufIdx }
      ::= { modemAlrBufTable 1}

ModemAlrBufEntry ::=
      SEQUENCE {
     modemAlrBufIdx          Integer32,
     modemAlrBufCode         Integer32,
     modemAlrBufState        INTEGER,
     modemAlrBufDate         DisplayString,
     modemAlrBufTime         DisplayString,
	 modemAlrBufSysUpTime    TimeTicks
      }

modemAlrBufIdx OBJECT-TYPE
      SYNTAX  Integer32
      MAX-ACCESS  read-only
      STATUS  current
      DESCRIPTION
      "Running index of the alarm buffer table."
      ::= {modemAlrBufEntry 1}

modemAlrBufCode OBJECT-TYPE
      SYNTAX Integer32
      MAX-ACCESS read-only
      STATUS current
      DESCRIPTION
      "The code of the alarm. For text description of each Alarm 
       code see Modem's	specification."
      ::= {modemAlrBufEntry 2}

modemAlrBufState OBJECT-TYPE
      SYNTAX INTEGER  { off(2),
	                    on(3)
					  }
      MAX-ACCESS read-only
      STATUS current
      DESCRIPTION
      "The new status of the alarm."
      ::= {modemAlrBufEntry 3}

modemAlrBufDate OBJECT-TYPE
      SYNTAX DisplayString
      MAX-ACCESS read-only
      STATUS current
      DESCRIPTION
      "The Date at which the alarm has occurred. The format
       is according to the entered systemDate format."
      ::= {modemAlrBufEntry 4}

modemAlrBufTime OBJECT-TYPE
      SYNTAX DisplayString
      MAX-ACCESS read-only
      STATUS current
      DESCRIPTION
      "The time stamp at which the alarm has occurred. The format
       is hh:mm:ss "
      ::= {modemAlrBufEntry 5}


modemAlrBufSysUpTime  OBJECT-TYPE
      SYNTAX 	      TimeTicks
      MAX-ACCESS      read-only
      STATUS          current
      DESCRIPTION
      "The value of sysUpTime at the time the alarm has occurred.
      This object is applicable only for products that cannot support 
      calendar date (modemAlrBufDate) and time (modemAlrBufTime)
      When not applicable, this object contains a zero value" 
      ::= {modemAlrBufEntry 6}


modemStatistics OBJECT IDENTIFIER  ::=  {modem 3}

modemGeneralTable  OBJECT-TYPE
      SYNTAX SEQUENCE OF ModemGeneralEntry
      MAX-ACCESS not-accessible
      STATUS  current
      DESCRIPTION
      "The IMOD General data Table. The data is specific to each 
       modem."
       ::= { modemStatistics 1 }

modemGeneralEntry OBJECT-TYPE
      SYNTAX ModemGeneralEntry
      MAX-ACCESS not-accessible
      STATUS current
      DESCRIPTION
      "An entry in the modemGeneralTable. This entry is per modem. 
       Each modem has a specific index, which identifies it."
      INDEX {modemIdx}
      ::= { modemGeneralTable 1}

ModemGeneralEntry ::=
      SEQUENCE {
	  modemCurrentElapsedTime Integer32,
	  modemValidIntervals     Integer32
      }


modemCurrentElapsedTime	 OBJECT-TYPE
	  SYNTAX  Integer32 (0..899)
      MAX-ACCESS  read-only
      STATUS  current
      DESCRIPTION
	  "The number of seconds that have elapsed since the beginning
	   of the current error-measurement period."
	  ::= {modemGeneralEntry 1}

modemValidIntervals	 OBJECT-TYPE
	  SYNTAX  Integer32 (0..96)
      MAX-ACCESS  read-only
      STATUS  current
      DESCRIPTION
	  "The number of previous intervals for which data was 
	   collected.
	   The value will be 96 unless the interface was brought on-line 
	   within the last 24 hours, in which case the value will be the 
	   number of complete 15 minute intervals since the interface 
	   has been online."
	  ::= {modemGeneralEntry 2}


modemIntervalTable  OBJECT-TYPE
      SYNTAX SEQUENCE OF ModemIntervalEntry
      MAX-ACCESS not-accessible
      STATUS  current
      DESCRIPTION
      "The IMOD Interval Table. The data is specific to each 
       modem."
       ::= { modemStatistics 2 }

modemIntervalEntry OBJECT-TYPE
      SYNTAX ModemIntervalEntry
      MAX-ACCESS not-accessible
      STATUS current
      DESCRIPTION
      "An entry in the modemIntervalTable. This entry is per modem 
       and per interval selected." 
      INDEX {modemIdx, modemIntervalNumber}
      ::= { modemIntervalTable 1}

ModemIntervalEntry ::=
      SEQUENCE {
	  modemIntervalNumber     Integer32,
	  modemSyncLoss           Integer32,
	  modemLineQuality        INTEGER,
	  modemLineUtility        Integer32,
	  modemRTS                Integer32,
	  modemCD                 Integer32,
	  modemBertResult   DisplayString,
	  modemBpvError      OCTET STRING,
	  modemFoError       OCTET STRING
      }

modemIntervalNumber	 OBJECT-TYPE
	  SYNTAX  Integer32 (1..96)
      MAX-ACCESS  read-only
      STATUS  current
      DESCRIPTION
	  "The number between 1 and 96, where 1 is the most recently 
	   completed 15 minute interval and 96 is the least recently 
	   completed 15 minutes interval (assuming that all 96 
	   intervals are valid). Maximum valid number is 
	   modemValidIntervals."
	  ::= {modemIntervalEntry 1}

modemSyncLoss	 OBJECT-TYPE
	  SYNTAX  Integer32 (0..101)
      MAX-ACCESS  read-only
      STATUS  current
      DESCRIPTION
	  "Percent of interval, SyncLoss signal is ON.
	   101 = notApplicable/unknown. "
	  ::= {modemIntervalEntry 2}

modemLineQuality   OBJECT-TYPE
	  SYNTAX  INTEGER
	      {
		   notApplicable (1),
		   bad  (2),
		   mid  (3),
		   good (4),
		   unknown (5),
		   syncLoss(6)
	      }
      MAX-ACCESS  read-only
      STATUS  current
      DESCRIPTION
      "Quality of Line for the selected modem, in the selected valid 
       interval."
	  ::= {modemIntervalEntry 3}

modemLineUtility	 OBJECT-TYPE
	  SYNTAX  Integer32 (0..101)
      MAX-ACCESS  read-only
      STATUS  current
      DESCRIPTION
	  "Percent of interval, Line is utilized.
	   101 = notApplicable/unknown. "
	  ::= {modemIntervalEntry 4}

modemRTS	 OBJECT-TYPE
	  SYNTAX  Integer32 (0..101)
      MAX-ACCESS  read-only
      STATUS  current
      DESCRIPTION
	  "Percent of interval, RTS signal is ON.
	   101 = notApplicable/unknown. "
	  ::= {modemIntervalEntry 5}

modemCD	 OBJECT-TYPE
	  SYNTAX  Integer32 (0..101)
      MAX-ACCESS  read-only
      STATUS  current
      DESCRIPTION
	  "Percent of interval, CD signal is ON.
	   101 = notApplicable/unknown. "
	  ::= {modemIntervalEntry 6}

modemBertResult	 OBJECT-TYPE
	  SYNTAX  DisplayString 
      MAX-ACCESS  read-only
      STATUS  current
      DESCRIPTION
	  "Result of BERT for the selected modem, in the selected 
	   valid interval."
	  ::= {modemIntervalEntry 7}

modemBpvError OBJECT-TYPE
      SYNTAX OCTET STRING (SIZE(0..1)) 
      MAX-ACCESS read-only
      STATUS current
      DESCRIPTION
      "BPV Error.
       The Octet will be built as follows:
       MSB 7  6  5  4  3  2  1  0 LSB
           |__|  |______________|
         y=0..3      x=0..63
         
         
         BPV Error = x * (10**y)
         
       An Agent that does not support this object will send Size=0."
      ::= {modemIntervalEntry 8}

modemFoError OBJECT-TYPE
      SYNTAX OCTET STRING (SIZE(0..1)) 
      MAX-ACCESS read-only
      STATUS current
      DESCRIPTION
      "FO Error.
       The Octet will be built as follows:
       MSB 7  6  5  4  3  2  1  0 LSB
           |__|  |______________|
         y=0..3      x=0..63
         
         
         FO Error = x * (10**y)
         
       An Agent that does not support this object will send Size=0."
      ::= {modemIntervalEntry 9}



modmPrt  OBJECT IDENTIFIER  ::=  {modmSys 4}


-- Supervisory Port (SP) 

modmSpPort  OBJECT IDENTIFIER  ::=  {modmPrt 1}

modmPrtSpTable  OBJECT-TYPE
      SYNTAX SEQUENCE OF ModmPrtSpEntry
      MAX-ACCESS not-accessible
      STATUS  current
      DESCRIPTION
      "Configuration parameters of the Local or Remote Modem
       Supervisory Ports. The port will be identified by its 
       specific ifIndex value."
       ::= { modmSpPort 1 }

modmPrtSpEntry OBJECT-TYPE
      SYNTAX ModmPrtSpEntry
      MAX-ACCESS not-accessible
      STATUS current
	DESCRIPTION  "An entry in table."
	INDEX {ifIndex}
      ::= { modmPrtSpTable 1}

ModmPrtSpEntry ::=
      SEQUENCE {
	  modmPrtSpUsage       INTEGER,
	  modmPrtSpRate        INTEGER,
	  modmPrtSpDataBits    INTEGER,
	  modmPrtSpParity      INTEGER,
	  modmPrtSpInterface   INTEGER,
	  modmPrtSpCTS		   INTEGER,
	  modmPrtSpDcdDelay	   INTEGER,
	  modmPrtSpDsr		   INTEGER
      }

modmPrtSpUsage OBJECT-TYPE
      SYNTAX  INTEGER
	      {
		nmsSlip   (2),
		terminal  (3),
		agentSlip (4),
		nmsPpp    (5),
		agentPpp  (6)
	      }
      MAX-ACCESS  read-write
      STATUS  current
      DESCRIPTION
      "This attribute indicates what is the usage of the port."
      ::= { modmPrtSpEntry 1}

modmPrtSpRate     OBJECT-TYPE
      SYNTAX  INTEGER
	      {
        auto      (1),
        s300bps   (2),
        s1200bps  (3),
        s2400bps  (4),
        s4800bps  (5),
        s9600bps  (6)
	      }
      MAX-ACCESS  read-write
      STATUS  current
      DESCRIPTION
      "This attribute indicates the operation rate (speed) of the 
       port.
       auto - automatic rate selection, by the agent."
      ::= {modmPrtSpEntry 2}

modmPrtSpDataBits OBJECT-TYPE
      SYNTAX  INTEGER
	      {
        dataBits7 (1),
        dataBits8 (2)
	      }
      MAX-ACCESS  read-write
      STATUS  current
      DESCRIPTION
      "This attribute indicates the number of data bits in the 
       word format."
      ::= {modmPrtSpEntry 3}

modmPrtSpParity OBJECT-TYPE
      SYNTAX  INTEGER
	      {
        none  (1),
        odd   (2),
        even  (3)
	      }
      MAX-ACCESS  read-write
      STATUS  current
      DESCRIPTION
      "This attribute indicates the parity mode in async frame"
      ::= { modmPrtSpEntry 4}

modmPrtSpInterface OBJECT-TYPE
      SYNTAX  INTEGER
	      {
          dce  (1),
          dte  (2)
	      }
      MAX-ACCESS  read-write
      STATUS  current
      DESCRIPTION
      "This attribute indicates the supervisory port interface.
       dce - the modem appears as a DCE for the SP port.
       dte - the modem operates as a DTE, for connection via modem,
             for the SP port."
      ::= { modmPrtSpEntry 5}

modmPrtSpCTS OBJECT-TYPE
      SYNTAX  INTEGER
	      {
          on            (2),
          rts           (3)
	      }
      MAX-ACCESS  read-write
      STATUS  current
      DESCRIPTION
	  "CTS line state. "
      ::= {modmPrtSpEntry 6}

modmPrtSpDcdDelay OBJECT-TYPE
      SYNTAX  INTEGER
	      {
          d0   (2),
          d10  (3),
		  d50  (4),
		  d100 (5),
		  d200 (6),
		  d300 (7)
	      }
      MAX-ACCESS  read-write
      STATUS  current
      DESCRIPTION
	  "DCD delay in msec. 
	   d10 = delay of 10msec."
      ::= { modmPrtSpEntry 7}

modmPrtSpDsr OBJECT-TYPE
      SYNTAX  INTEGER
	      {
          on   (2),
          dtr  (3)
	      }
      MAX-ACCESS  read-write
      STATUS  current
      DESCRIPTION
	  "DSR line state."
      ::= {modmPrtSpEntry 8}

-- Ds1 Port (T1/E1)

modmDs1Port  OBJECT IDENTIFIER  ::=  {modmPrt 2}

modmPrtDs1Table  OBJECT-TYPE
      SYNTAX SEQUENCE OF ModmPrtDs1Entry
      MAX-ACCESS not-accessible
      STATUS  current
      DESCRIPTION
      "Statistics parameters of the Local and Remote modem Ds1 ports.
       The port will be identified by its specific ifIndex value."
       ::= { modmDs1Port 1 }

modmPrtDs1Entry OBJECT-TYPE
      SYNTAX ModmPrtDs1Entry
      MAX-ACCESS not-accessible
      STATUS current
	DESCRIPTION  "An entry in table."
	INDEX {ifIndex}
      ::= { modmPrtDs1Table 1}

ModmPrtDs1Entry ::=
      SEQUENCE {
	  modmPrtDs1HdslPriorityBumping OCTET STRING,
	  modmPrtDs1Sync        INTEGER,
	  modmPrtDs1BpvLastMin    Gauge32,
	  modmPrtDs1BpvMax        Gauge32,
	  modmPrtDs1LineLength    INTEGER,
	  modmPrtDs1CRCAvgError	  Gauge32
							 
      }

modmPrtDs1HdslPriorityBumping	 OBJECT-TYPE
	  SYNTAX  OCTET STRING (SIZE(4))
      MAX-ACCESS  read-write
      STATUS  deprecated
      DESCRIPTION
	  "The 4 bytes represent the 32 time slots of the E1 frame.
	   Each bit can be set to one, making the corresponding time
	   slot a HIGH priority. Bits 16 and 32 cannot be modified by the
	   user. The maximum number of HIGH priority time slots is 16.
	   The default value is LOW, i.e., 0. This variable is RO in the
	   Remote unit."
--  DEFVAL  { 0 }
	  ::= { modmPrtDs1Entry 1 }

modmPrtDs1Sync	 OBJECT-TYPE
	  SYNTAX  INTEGER { itu(2),
	                    fast(3),
						s62411(4)
					  }
      MAX-ACCESS  read-write
      STATUS  current
      DESCRIPTION
	  "The standard used for the time required for the E1 port to return
	   to normal operation after local loss of synchronization. Default:
	   itu(2)."
--  DEFVAL  { 2 }
	  ::= { modmPrtDs1Entry 2 }

modmPrtDs1BpvLastMin	 OBJECT-TYPE
	  SYNTAX  Gauge32
      MAX-ACCESS  read-only
      STATUS  current
      DESCRIPTION
	  "This object is applicable only for an E1 active port.
	   It provides the number of BPV (BiPolar Violation) events 
	   detected during the last	minute."
	  ::= { modmPrtDs1Entry 3 }

modmPrtDs1BpvMax	 OBJECT-TYPE
	  SYNTAX  Gauge32
      MAX-ACCESS  read-only
      STATUS  current
      DESCRIPTION
	  "This object is applicable only for an E1 active port.
	   It provides the maximal number of BPV (BiPolar Violation) 
	   events (per minute), detected during the worst minute."
	  ::= { modmPrtDs1Entry 4 }

modmPrtDs1LineLength  OBJECT-TYPE
      SYNTAX  INTEGER
       {
		unknown      (1),
        len0p133ft   (2),
        len134p266ft (3),
        len267p399ft (4),
        len400p533ft (5),
        len534p655ft (6),
        fcc68        (7),
		notApplicable(255)
	      }
      MAX-ACCESS  read-write
      STATUS  current
      DESCRIPTION
      "This attribute is the line length mask parameter used only 
       for T1/DSU interfaces.
       len400p533ft=length range: 400ft to 533ft 
       'fcc68' - provides compliance with the FCC 68.308 Option A
                 output pulse mask. "
   ::= { modmPrtDs1Entry 5 }

modmPrtDs1CRCAvgError OBJECT-TYPE
      SYNTAX Gauge32 
      MAX-ACCESS  read-only
      STATUS  current
      DESCRIPTION
      "Counts the average number of CRC error events per second.
       The average is updated every second"
      ::= { modmPrtDs1Entry 6 }


modmHdslPort  OBJECT IDENTIFIER  ::=  {modmPrt 3}

modmPrtHdslCurrentTable  OBJECT-TYPE
      SYNTAX SEQUENCE OF ModmPrtHdslCurrentEntry
      MAX-ACCESS not-accessible
      STATUS  current
      DESCRIPTION
      "The HDSL Current Table. The data collected is for the current
       15-minute interval."
       ::= { modmHdslPort 1 }

modmPrtHdslCurrentEntry OBJECT-TYPE
      SYNTAX ModmPrtHdslCurrentEntry
      MAX-ACCESS not-accessible
      STATUS current
      DESCRIPTION
      "An entry in the HDSL Current Table. This entry is per HDSL 
       interface (LOOP1 or LOOP2). Each modem (Central/Remote) has
       a specific ifIndex value for the port, which identifies it."
      INDEX {ifIndex}
      ::= { modmPrtHdslCurrentTable 1}

ModmPrtHdslCurrentEntry ::=
      SEQUENCE {
	  modmPrtHdslCurrentElapsedTime Integer32,
	  modmPrtHdslCurrentESs           Gauge32,
	  modmPrtHdslCurrentSESs          Gauge32,
	  modmPrtHdslCurrentBBEs          Gauge32,
	  modmPrtHdslCurrentUASs          Gauge32,
	  modmPrtHdslCurrentNoiseMargin	Integer32,
	  modmPrtHdslCurrentAttenuation	Integer32
      }

modmPrtHdslCurrentElapsedTime	 OBJECT-TYPE
	  SYNTAX  Integer32 (0..899)
      MAX-ACCESS  read-only
      STATUS  current
      DESCRIPTION
	  "The number of seconds that have elapsed since the beginning
	   of the current error-measurement period."
	  ::= { modmPrtHdslCurrentEntry 1 }

modmPrtHdslCurrentESs	 OBJECT-TYPE
	  SYNTAX  Gauge32
      MAX-ACCESS  read-only
      STATUS  current
      DESCRIPTION
	  "The number of Errored Seconds encountered by an HDSL 
	   interface in the current 15 minute interval. An Errored 
	   Second is any second containing one or more Errored Blocks 
	   or an occurrence of an SDP."
	  ::= { modmPrtHdslCurrentEntry 2 }

modmPrtHdslCurrentSESs	 OBJECT-TYPE
	  SYNTAX  Gauge32
      MAX-ACCESS  read-only
      STATUS  current
      DESCRIPTION
	  "The number of Severely Errored Seconds encountered by an HDSL 
	   interface in the current 15 minute interval. An SES is any 
	   second containing more than 30% Errored Blocks (50 blocks) or 
	   one or more SDPs."
	  ::= { modmPrtHdslCurrentEntry 3 }

modmPrtHdslCurrentBBEs	 OBJECT-TYPE
	  SYNTAX  Gauge32
      MAX-ACCESS  read-only
      STATUS  current
      DESCRIPTION
	  "The number of Background Block Errors encountered by an HDSL 
	   interface in the current 15 minute interval. A BBE is an 
	   errored block not occurring as part of an SES."
	  ::= { modmPrtHdslCurrentEntry 4 }

modmPrtHdslCurrentUASs	 OBJECT-TYPE
	  SYNTAX  Gauge32
      MAX-ACCESS  read-only
      STATUS  current
      DESCRIPTION
	  "The number of Unavailable Seconds encountered by an HDSL 
	   interface in the current 15 minute interval. A UAS is any 
	   second in which a failed signal state exists. A failure state 
	   is declared when 10 consecutive SESs occur, and is cleared 
	   after 10 consecutive seconds free of an SES."
	  ::= { modmPrtHdslCurrentEntry 5 }

modmPrtHdslCurrentNoiseMargin   OBJECT-TYPE
	  SYNTAX  Integer32 
      MAX-ACCESS  read-only
      STATUS  current
      DESCRIPTION
	  "The current noise margin in DB.
	   This object is not an accumulative one, therefore
	   it's value will appear only in this table."
	  ::= { modmPrtHdslCurrentEntry 6 }

modmPrtHdslCurrentAttenuation   OBJECT-TYPE
	  SYNTAX  Integer32 
      MAX-ACCESS  read-only
      STATUS  current
      DESCRIPTION
	  "The current attenuation in DB.
	   This object is not an accumulative one, therefore
	   it's value will appear only in this table."
	  ::= { modmPrtHdslCurrentEntry 7 }



modmPrtHdslIntervalTable  OBJECT-TYPE
      SYNTAX SEQUENCE OF ModmPrtHdslIntervalEntry
      MAX-ACCESS not-accessible
      STATUS  current
      DESCRIPTION
      "The HDSL Interval Table. The data collected is for the last 96
       completed 15-minute intervals."
       ::= { modmHdslPort 2 }

modmPrtHdslIntervalEntry OBJECT-TYPE
      SYNTAX ModmPrtHdslIntervalEntry
      MAX-ACCESS not-accessible
      STATUS current
      DESCRIPTION
      "An entry in the HDSL Interval Table. This entry is per an HDSL 
       interface (LOOP1 or LOOP2) and per 15 minute interval. The 
       port and unit (Central/Remote) is identified by its specific 
       ifIndex value."
      INDEX {ifIndex, modmPrtHdslIntervalNumber}
      ::= { modmPrtHdslIntervalTable 1}

ModmPrtHdslIntervalEntry ::=
      SEQUENCE { 
	  modmPrtHdslIntervalNumber        Integer32,
	  modmPrtHdslIntervalESs           Gauge32,
	  modmPrtHdslIntervalSESs          Gauge32,
	  modmPrtHdslIntervalBBEs          Gauge32,
	  modmPrtHdslIntervalUASs          Gauge32,
	  modmPrtHdslIntervalESR           Integer32,
	  modmPrtHdslIntervalSESR          Integer32,
	  modmPrtHdslIntervalBBER          Integer32
      }

modmPrtHdslIntervalNumber	 OBJECT-TYPE
	  SYNTAX  Integer32 (1..96)
      MAX-ACCESS  read-only
      STATUS  current
      DESCRIPTION
	  "The number between 1 and 96, where 1 is the most recently completed
	   15 minute interval and 96 is the least recently completed 15 minutes
	   interval (assuming that all 96 intervals are valid)."
	  ::= { modmPrtHdslIntervalEntry 1 }

modmPrtHdslIntervalESs	 OBJECT-TYPE
	  SYNTAX  Gauge32
      MAX-ACCESS  read-only
      STATUS  current
      DESCRIPTION
	  "The number of Errored Seconds encountered by an HDSL interface in
	   one of the previous 96, individual 15 minute, intervals."
	  ::= { modmPrtHdslIntervalEntry 2 }

modmPrtHdslIntervalSESs	 OBJECT-TYPE
	  SYNTAX  Gauge32
      MAX-ACCESS  read-only
      STATUS  current
      DESCRIPTION
	  "The number of Severely Errored Seconds encountered by an HDSL interface in
	   one of the previous 96, individual 15 minute, intervals."
	  ::= { modmPrtHdslIntervalEntry 3 }

modmPrtHdslIntervalBBEs	 OBJECT-TYPE
	  SYNTAX  Gauge32
      MAX-ACCESS  read-only
      STATUS  current
      DESCRIPTION
	  "The number of Background Block Errors encountered by an HDSL interface in
	   one of the previous 96, individual 15 minute, intervals."
	  ::= { modmPrtHdslIntervalEntry 4 }

modmPrtHdslIntervalUASs	 OBJECT-TYPE
	  SYNTAX  Gauge32
      MAX-ACCESS  read-only
      STATUS  current
      DESCRIPTION
	  "The number of Unavailable Seconds encountered by an HDSL interface in
	   one of the previous 96, individual 15 minute, intervals."
	  ::= { modmPrtHdslIntervalEntry 5 }

modmPrtHdslIntervalESR	 OBJECT-TYPE
	  SYNTAX  Integer32 (0..100)
      MAX-ACCESS  read-only
      STATUS  current
      DESCRIPTION
	  "The ratio of ESs to 900 seconds, encountered by an HDSL interface in
	   one of the previous 96, individual 15 minute, intervals."
	  ::= { modmPrtHdslIntervalEntry 6 }

modmPrtHdslIntervalSESR	 OBJECT-TYPE
	  SYNTAX  Integer32 (0..100)
      MAX-ACCESS  read-only
      STATUS  current
      DESCRIPTION
	  "The ratio of SESs to 900 seconds, encountered by an HDSL interface in
	   one of the previous 96, individual 15 minute, intervals."
	  ::= { modmPrtHdslIntervalEntry 7 }

modmPrtHdslIntervalBBER	 OBJECT-TYPE
	  SYNTAX  Integer32 (0..100)
      MAX-ACCESS  read-only
      STATUS  current
      DESCRIPTION
	  "The ratio of BBEs to 900 seconds, encountered by an HDSL interface in
	   one of the previous 96, individual 15 minute, intervals."
	  ::= { modmPrtHdslIntervalEntry 8 }


modmPrtHdslTotalTable  OBJECT-TYPE
      SYNTAX SEQUENCE OF ModmPrtHdslTotalEntry
      MAX-ACCESS not-accessible
      STATUS  current
      DESCRIPTION
      "The HDSL Total Table. The data collected is the cumulative 
       sum of the various statistics for the 24 hour period 
       preceding the current interval."
       ::= { modmHdslPort 3 }

modmPrtHdslTotalEntry OBJECT-TYPE
      SYNTAX ModmPrtHdslTotalEntry
      MAX-ACCESS not-accessible
      STATUS current
      DESCRIPTION
      "An entry in the HDSL Total Table. This entry is per an HDSL 
       interface (LOOP1 or LOOP2). The port and unit (Central/Remote) 
       is identified by its specific ifIndex value."
      INDEX {ifIndex}
      ::= { modmPrtHdslTotalTable 1}

ModmPrtHdslTotalEntry ::=
      SEQUENCE { 
	  modmPrtHdslTotalValidIntervals Integer32,
	  modmPrtHdslTotalESs              Gauge32,
	  modmPrtHdslTotalSESs             Gauge32,
	  modmPrtHdslTotalBBEs             Gauge32,
	  modmPrtHdslTotalUASs             Gauge32
      }

modmPrtHdslTotalValidIntervals	 OBJECT-TYPE
	  SYNTAX  Integer32 (0..96)
      MAX-ACCESS  read-only
      STATUS  current
      DESCRIPTION
	  "The number of previous intervals for which valid data was 
	   collected.
	   The value will be 96 unless the interface was brought on-line 
	   within the last 24 hours, in which case the value will be the 
	   number of complete 15 minute intervals since the interface 
	   has been online."
	  ::= { modmPrtHdslTotalEntry 1 }

modmPrtHdslTotalESs	 OBJECT-TYPE
	  SYNTAX  Gauge32
      MAX-ACCESS  read-only
      STATUS  current
      DESCRIPTION
	  "The number of Errored Seconds encountered by an HDSL 
	   interface in	the previous 24 hour interval."
	  ::= { modmPrtHdslTotalEntry 2 }

modmPrtHdslTotalSESs	 OBJECT-TYPE
	  SYNTAX  Gauge32
      MAX-ACCESS  read-only
      STATUS  current
      DESCRIPTION
	  "The number of Severely Errored Seconds encountered by an HDSL 
	   interface in	the previous 24 hour interval."
	  ::= { modmPrtHdslTotalEntry 3 }

modmPrtHdslTotalBBEs	 OBJECT-TYPE
	  SYNTAX  Gauge32
      MAX-ACCESS  read-only
      STATUS  current
      DESCRIPTION
	  "The number of Background Block Errors encountered by an HDSL 
	   interface in	the previous 24 hour interval."
	  ::= { modmPrtHdslTotalEntry 4 }

modmPrtHdslTotalUASs	 OBJECT-TYPE
	  SYNTAX  Gauge32
      MAX-ACCESS  read-only
      STATUS  current
      DESCRIPTION
	  "The number of Unavailable Seconds encountered by an HDSL 
	   interface in the previous 24 hour interval."
	  ::= { modmPrtHdslTotalEntry 5 }


modmPrtHdslTable  OBJECT-TYPE
      SYNTAX SEQUENCE OF ModmPrtHdslEntry
      MAX-ACCESS not-accessible
      STATUS  current
      DESCRIPTION
      "The HDSL Table."
       ::= { modmHdslPort 4 }

modmPrtHdslEntry OBJECT-TYPE
      SYNTAX ModmPrtHdslEntry
      MAX-ACCESS not-accessible
      STATUS current
      DESCRIPTION
      "An entry in the HDSL Table. The port and unit (Central/Remote) 
       is identified by its specific modmPrtHdslIndex value."
      INDEX {modmPrtHdslIndex}
      ::= { modmPrtHdslTable 1}

ModmPrtHdslEntry ::=
      SEQUENCE { 
	  modmPrtHdslIndex		     Integer32,
	  modmPrtHdslDedicatedTs     Integer32,
	  modmPrtHdslPriorityBumping OCTET STRING,
      modmPrtHdslMngProtocol     INTEGER, 
      modmPrtHdslRoutProtocol    INTEGER, 
      modmPrtHdslInbandMngRate 	 INTEGER
	  }

modmPrtHdslIndex OBJECT-TYPE
      SYNTAX Integer32
      MAX-ACCESS read-only
      STATUS current
      DESCRIPTION
      "The HDSL port index. In some cases it can equal ifIndex." 
      ::= { modmPrtHdslEntry 1}

modmPrtHdslDedicatedTs	 OBJECT-TYPE
	  SYNTAX  Integer32 (0..255)
      MAX-ACCESS  read-only
      STATUS  current
      DESCRIPTION
	  "The HDSL Current Dedicated TS.
	   Valid values: 0..31.
	   255 = None (no dedicated TS)."
	  ::= { modmPrtHdslEntry 2 } 

modmPrtHdslPriorityBumping	 OBJECT-TYPE
	  SYNTAX  OCTET STRING (SIZE(4))
      MAX-ACCESS  read-write
      STATUS  current
      DESCRIPTION
	  "The 4 bytes represent time slots 0..31 of the E1 frame.
	   Each bit can be set to '1', making the corresponding time slot a HIGH priority.
	   Bit 0 is always HIGH (cannot be modified by the user).
	   The maximum number of HIGH priority time slots is: 16 for E1 ; 13 for T1 
	   (including TS0).
	   The default value is LOW, i.e., 0."
--  DEFVAL  { 0 }
	  ::= { modmPrtHdslEntry 3 }

modmPrtHdslMngProtocol	 OBJECT-TYPE
	  SYNTAX  INTEGER {
              off         (2),
              dedicatedTs (4),
              dedicatedPpp(5),
              dedicatedFr (6)
                        }
      MAX-ACCESS  read-write
      STATUS  current
      DESCRIPTION
	  "A unique number to identify an Inband management over the 
       link."
	  ::= { modmPrtHdslEntry 4 } 

modmPrtHdslRoutProtocol  OBJECT-TYPE
      SYNTAX  INTEGER
       {
             notApplicable (1),
             none          (2),  
             proprietary   (3),
             rip2          (4)
       }
      MAX-ACCESS  read-write
      STATUS  current
      DESCRIPTION
      "Inband Mng Routing Protocol of the port.
       When modmPrtHdslMngProtocol is 'dedicatedPpp'-'proprietary' and
                                               'rip2' are applicable.
       For other values  - only 'proprietary' is applicable."             
      ::= {modmPrtHdslEntry 5}

modmPrtHdslInbandMngRate  OBJECT-TYPE
      SYNTAX  INTEGER
       {
          notApplicable(1),
          r4k   (2),
          r8k   (3),
          r12k  (4),
          r16k  (5),
          r32k  (6),
          r64k  (7)
       }
      MAX-ACCESS  read-write
      STATUS  current
      DESCRIPTION
      "A unique number to identify the rate of the Inband management.
       It is applicable only when modmPrtHdslDedicatedTs <> (255 Or 0)."
      ::= {modmPrtHdslEntry 6}

-- DTE (User) Port  

modmDtePort  OBJECT IDENTIFIER  ::=  {modmPrt 4}

modmPrtDteTable  OBJECT-TYPE
      SYNTAX SEQUENCE OF ModmPrtDteEntry
      MAX-ACCESS not-accessible
      STATUS  current
      DESCRIPTION
      "Configuration parameters of the Master and Slave Modem DTE 
       Ports. The port and unit (Master/Slave) is identified by 
       its specific modmPrtDteIndex value."
       ::= { modmDtePort 1 }

modmPrtDteEntry OBJECT-TYPE
      SYNTAX ModmPrtDteEntry
      MAX-ACCESS not-accessible
      STATUS current
	DESCRIPTION  "An entry in table."
	INDEX {modmPrtDteIndex}
      ::= { modmPrtDteTable 1}

ModmPrtDteEntry ::=
      SEQUENCE {
	  modmPrtDteIndex		   Integer32,
	  modmPrtDteProtocol       INTEGER,
	  modmPrtDteDataBits       INTEGER,
	  modmPrtDteStopBits       INTEGER,
	  modmPrtDteRate           INTEGER,
	  modmPrtDteCtsDelay       INTEGER,
	  modmPrtDteParity         INTEGER,
	  modmPrtDteIfType         INTEGER,
	  modmPrtDteRlbEnable      INTEGER,
	  modmPrtDteAlbEnable      INTEGER,
	  modmPrtDteRtsDcdEnable   INTEGER,
	  modmPrtDteDsrDtrEnable   INTEGER,
	  modmPrtDteSignaling      OCTET STRING,
      modmPrtDteLoops		   INTEGER,
      modmPrtDteTests		   Integer32,
	  modmPrtDteClearAllTests  INTEGER,
	  modmPrtDteBertResult     DisplayString,
	  modmPrtDteErrCorrect     INTEGER,
	  modmPrtDteV54DigitalTest	   		INTEGER,	
	  modmPrtDteV54DigitalTestStatus  	INTEGER,	
	  modmPrtDteTestTimeOut	   Integer32	
      }

modmPrtDteIndex OBJECT-TYPE
      SYNTAX Integer32
      MAX-ACCESS read-only
      STATUS current
      DESCRIPTION
      "The DTE port index." 
      ::= { modmPrtDteEntry 1}

modmPrtDteProtocol OBJECT-TYPE
      SYNTAX INTEGER {
                sync  (2),
                async (3)
		            }
      MAX-ACCESS read-write
      STATUS current
      DESCRIPTION
      "The DTE port Protocol." 
      ::= { modmPrtDteEntry 2}

modmPrtDteDataBits OBJECT-TYPE
      SYNTAX INTEGER {
        dataBits6  (1),
        dataBits7  (2),
        dataBits8  (3),
        dataBits9  (4),
        dataBits10 (5),
        dataBits11 (6),
        dataBits5  (7)
		}
      MAX-ACCESS read-write
      STATUS current
      DESCRIPTION
      "The DTE number of data bits." 
      ::= { modmPrtDteEntry 3}

modmPrtDteStopBits OBJECT-TYPE
      SYNTAX INTEGER {
          stopBits1Bit      (1),
          stopBits1dot5Bits (2),
          stopBits2Bits     (3)
		            }
      MAX-ACCESS read-write
      STATUS current
      DESCRIPTION
      "The DTE minimum number of stop bits in the tx async frame." 
      ::= { modmPrtDteEntry 4}

modmPrtDteRate OBJECT-TYPE
      SYNTAX INTEGER {
        r300bps      (1),
        r600bps      (2),
        r1200bps     (3),
        r2400bps     (4),
        r4800bps     (5),
        r9600bps     (6),
        r14400bps    (7),
	    r16000bps    (8),
        r19200bps    (9),
        r28800bps   (10),
        r32000bps   (11),
        r38400bps   (12),
        r48000bps   (13),
        r56000bps   (14),
	    r57600bps   (15),
        r64000bps   (16),
        r72000bps   (17),
        r96000bps   (18),
        r112000bps  (19),
        r115200bps  (20),
        r128Kbps    (21),
        r144Kbps    (22),
        r192Kbps    (23),
        r256Kbps    (24),
        r320Kbps    (25),
        r384Kbps    (26),
        r448Kbps    (27),
        r512Kbps    (28),
        r576Kbps    (29),
        r640Kbps    (30),
        r704Kbps    (31),
        r768Kbps    (32),
		r1024Kbps   (33),
		r1536Kbps   (34),
		r1544Kbps   (35),
		r2048Kbps   (36),
		e1          (37),
		t1          (38),
		r896Kbps    (39),
		r960Kbps    (40),
		r1152Kbps   (41),
		r1920Kbps   (42),
		r34Mbps     (43),	 -- e3
		r45Mbps     (44),	 -- t3

		r1088Kbps   (45),
		r1216Kbps   (46),
		r1344Kbps   (47),
		r1408Kbps   (48),
		r1472Kbps   (49),
		r1600Kbps   (50),
		r1664Kbps   (51),
		r1728Kbps   (52),
		r1792Kbps   (53),
		r1856Kbps   (54),
		r1984Kbps   (55),

		r1280Kbps   (56),
		r2304Kbps   (57),						   
		r832Kbps	(58),
												   
        r2176Kbps 	(59),						   
												   
        r2432Kbps 	(60),						   
        r2560Kbps 	(61),						   
        r2688Kbps 	(62),						   
        r2816Kbps 	(63),						   
        r2944Kbps 	(64),						   
        r3072Kbps 	(65),						   
        r3200Kbps 	(66),						   
        r3328Kbps 	(67),						   
        r3456Kbps 	(68),						   
        r3584Kbps 	(69),						   
        r3712Kbps 	(70),						   
        r3840Kbps 	(71),
        r3968Kbps 	(72),
        r4096Kbps 	(73),

        r2112Kbps   (74),
        r2240Kbps   (75),

        r4224Kbps   (76),
        r4352Kbps   (77),
        r4480Kbps   (78),
        r4608Kbps   (79) 

		}
      MAX-ACCESS read-write
      STATUS current
      DESCRIPTION
      "The DTE port rate." 
      ::= { modmPrtDteEntry 5}
	
modmPrtDteCtsDelay OBJECT-TYPE
      SYNTAX INTEGER 
          {
        d0       (1),
        d1       (2),
        d7       (3),
		d8       (4),
        d10      (5),
        d70      (6),
		disabled (7),
		enabled  (8),
        notApplicable (255)
                	}
      MAX-ACCESS read-write
      STATUS current
      DESCRIPTION
      "CTS/RTS delay, in msec.
       dxx = xx msec.
       notApplicable - for ASMi-31, ASMi-32." 
      ::= { modmPrtDteEntry 6}

modmPrtDteParity OBJECT-TYPE
      SYNTAX  INTEGER
	      {
          none  (1),
          odd   (2),
          even  (3)
	      }
      MAX-ACCESS  read-write
      STATUS  current
      DESCRIPTION
      "This attribute indicates the parity mode in async frame."
      ::= { modmPrtDteEntry 7}

modmPrtDteIfType OBJECT-TYPE
      SYNTAX  INTEGER
	      {
		  v24      (1),
		  rs530    (2),
		  x21      (3),
		  g703     (4),	  --E1
		  v36      (5),
		  v35      (6),
		  g703r64k (7),
		  hdb3     (8),
		  ethernet (9),	 --UTP
		  g703T1   (10),
		  ethBNC   (11),
          noIR     (15),
		  ipUtp    (16),
		  ethQ     (17),
		  rs530WA  (18),
		  v35WA    (19),
		  g704E1   (20),
		  ethQN	   (21),	

		  other    (255)
		  }
      MAX-ACCESS  read-only
      STATUS  current
      DESCRIPTION
      "The interface type of the DTE port."
      ::= { modmPrtDteEntry 8}

modmPrtDteRlbEnable OBJECT-TYPE
      SYNTAX INTEGER {
                disable  (2),
                enable   (3)
		            }
      MAX-ACCESS read-write
      STATUS current
      DESCRIPTION
      "Enable/Disable Remote Loop-Back on this modem, externally
       initiated." 
      ::= {modmPrtDteEntry 9}

modmPrtDteAlbEnable OBJECT-TYPE
      SYNTAX INTEGER {
                disable  (2),
                enable   (3)
		            }
      MAX-ACCESS read-write
      STATUS current
      DESCRIPTION
      "Enable/Disable Analog Loop-Back on this modem, externally
       initiated." 
      ::= {modmPrtDteEntry 10}

modmPrtDteRtsDcdEnable OBJECT-TYPE
      SYNTAX INTEGER {
                disable  (2),
                enable   (3)
		            }
      MAX-ACCESS read-write
      STATUS current
      DESCRIPTION
      "Enable/Disable RTS-DCD." 
      ::= {modmPrtDteEntry 11}

modmPrtDteDsrDtrEnable OBJECT-TYPE
      SYNTAX INTEGER {
                disable  (2),
                enable   (3)
		            }
      MAX-ACCESS read-write
      STATUS current
      DESCRIPTION
      "Enable/Disable DSR-DTR." 
      ::= {modmPrtDteEntry 12}

modmPrtDteSignaling OBJECT-TYPE
      SYNTAX OCTET STRING
      MAX-ACCESS read-only
      STATUS current
      DESCRIPTION
      "Each bit represents a specific signal state.
       1 - means : signal is ON , Enabled, Yes (exists)
       0 - means : signal is OFF, Disabled, No .
       For detailed bit assignment see product's spec." 
      ::= {modmPrtDteEntry 13}

modmPrtDteLoops  OBJECT-TYPE
      SYNTAX  INTEGER
	      {
		none        (1),
		ana         (2),
		rem         (3),
		anaAndBert  (4),
		remAndBert  (5),
		bert        (6),
		twoBerts    (7),
		digital     (8),
		dual        (9),
		clb         (10),
		clbAndBert  (11)
	      }
      MAX-ACCESS  read-write
      STATUS  current
      DESCRIPTION
      "Loops that can be run on the DTE port.
       none - no loop (stop running loop) 
       ana  - Local Analog Line loop
       rem  - Remote Analog Line loop
	   anaAndBert - ana & BERT together
	   remAndBert - rem & BERT together
	   bert - BERT test
	   twoBerts - 2 BERT test
	   digital - A remote loop on the local modem. 
	   dual - Remote loop and ana loop.
	   clb - Local loop on the DTE connection. Must 
	        be set together with modmPrtDteTestTimeOut parameter. 
	        Applicable to asmi51/CQ/CD.
	   clbAndBert - CLB & BERT together. 
	   		Applicable to asmi51/CQ/CD. "
      ::= {modmPrtDteEntry 14}

modmPrtDteTests  OBJECT-TYPE
      SYNTAX  Integer32
      MAX-ACCESS  read-write
      STATUS  current
      DESCRIPTION
      "This is a mask which indicates 
       - for Get: which tests are running on the DTE port.
       - for Set: tests the user wishes to start or stop.
       Each test has its specific bit. 
       - '1' means the test runs (Set: should run).
       - '0' means the test does not run (Set: should stop):

         TEST                  BIT
        -----------            ---
        LEDs                    0
		

        e.g : If the return value is 1 the LEDs test is running."
      ::= {modmPrtDteEntry 15}

modmPrtDteClearAllTests  OBJECT-TYPE
      SYNTAX  INTEGER
	      {
		off(2),
		on (3)
	      }
      MAX-ACCESS  read-write
      STATUS  current
      DESCRIPTION
      "Setting this attribute to on, clears all the running loops 
       and tests of the DTE port. Upon completion, the value will 
       automatically change to off(2)."
      ::= {modmPrtDteEntry 16}

modmPrtDteBertResult	 OBJECT-TYPE
	  SYNTAX  DisplayString 
      MAX-ACCESS  read-only
      STATUS  current
      DESCRIPTION
	  "Result of BERT for the selected DTE port. 
	   Applicable only if BERT is running on the DTE port."
	  ::= {modmPrtDteEntry 17}

modmPrtDteErrCorrect  OBJECT-TYPE
      SYNTAX  INTEGER
	      {
		notApplicable (1),
		off     (2),
		on      (3),
		onBurst (4)
	      }
      MAX-ACCESS  read-write
      STATUS  current
      DESCRIPTION
      "notApplicable - for modems that do not support this object
       on      - will start a random error correction process.
	   onBurst - will start a burst error correction process.
       Setting this object to 'off', will stop any kind of error correction process."
      ::= {modmPrtDteEntry 18}

modmPrtDteV54DigitalTest  OBJECT-TYPE
      SYNTAX  INTEGER
	      {
		notApplicable (1),
		disable(2),
		enable (3)
	      }
      MAX-ACCESS  read-write
      STATUS  current
      DESCRIPTION
      "Enables to start a remote digital loopback upon recognition of a special pattern.
      disable - will not start a digital loopback when a special pattern is 
      recognized.
      enable  - will start a loopback upon recognition of a special pattern."
      ::= {modmPrtDteEntry 19}

modmPrtDteV54DigitalTestStatus  OBJECT-TYPE
      SYNTAX  INTEGER
	      {
		notApplicable (1),
        off  (2),
        on   (3)
	      }
      MAX-ACCESS  read-only
      STATUS  current
      DESCRIPTION
      "Indicates whether a remote digital test was triggered by a pattern
      by the remote modem or not.
      no  - the digital test wasn't triggered by a pattern by the remote modem.
      yes - the digital test was triggered by a pattern by the remote modem."
      ::= {modmPrtDteEntry 20}

modmPrtDteTestTimeOut  OBJECT-TYPE
      SYNTAX  Integer32
      MAX-ACCESS  read-write
      STATUS  current
      DESCRIPTION
      "Indicates the timeout for LLB test.
       0=Forever "
      ::= {modmPrtDteEntry 21}


-- Line port 

modmLinePort  OBJECT IDENTIFIER  ::=  {modmPrt 5}

modmPrtLineTable  OBJECT-TYPE
      SYNTAX SEQUENCE OF ModmPrtLineEntry
      MAX-ACCESS not-accessible
      STATUS  current
      DESCRIPTION
      "Configuration parameters of the Master and Slave Modem Line 
       Ports. The port and unit (Master/Slave) is identified by 
       its specific modmPrtLineIndex value."
       ::= { modmLinePort 1 }

modmPrtLineEntry OBJECT-TYPE
      SYNTAX ModmPrtLineEntry
      MAX-ACCESS not-accessible
      STATUS current
	DESCRIPTION  "An entry in table."
	INDEX {modmPrtLineIndex}
      ::= { modmPrtLineTable 1}

ModmPrtLineEntry ::=
      SEQUENCE {
	  modmPrtLineIndex		   Integer32,
	  modmPrtLineClkSrc        INTEGER,
	  modmPrtLineTxLevel       INTEGER,
	  modmPrtLineRxLevel       INTEGER,
	  modmPrtLineOutImp        INTEGER,
	  modmPrtLineInImp         INTEGER,
	  modmPrtLineCarrCntrl     INTEGER,
	  modmPrtLineRAP           INTEGER,
	  modmPrtLineWaveLength    INTEGER,
	  modmPrtLineCdSense       INTEGER,
	  modmPrtLineAIS           INTEGER,
	  modmPrtLineCoding        INTEGER,
	  modmPrtLineLength        INTEGER,
	  modmPrtLineClkSrcPort    INTEGER,
	  modmPrtLineDteClkConfig  INTEGER,
	  modmPrtLineMaskAlr	   INTEGER		
      }

modmPrtLineIndex OBJECT-TYPE
      SYNTAX Integer32 
	  MAX-ACCESS read-only
      STATUS current
      DESCRIPTION
      "The Line port index." 
      ::= {modmPrtLineEntry 1}

modmPrtLineClkSrc OBJECT-TYPE
      SYNTAX INTEGER 
	      {
           localExtRemoteRcv     (1),
           localIntRemoteRcv     (2),
           localRcvRemoteInt     (3),
		   localRcvRemoteExt     (4),
		   localExtAutoRemoteRcv (5),
		   localRcvRemoteExtAuto (6),
		   localSysRemoteRcv     (7),
		   localRcvRemoteSys     (8),
		   internal              (9),
		   external              (10),
		   system                (11),
		   receive               (12),
		   
		   notApplicable         (255)
	      }
	  MAX-ACCESS read-write
      STATUS current
      DESCRIPTION
      "The clock source of the Line port. 
       (5),(6) - applicable only for ASMi-24 and ASMi-50.
       (7),(8) - System level Clock Source. Applicable to CQ modems." 
      ::= {modmPrtLineEntry 2}

modmPrtLineTxLevel OBJECT-TYPE
      SYNTAX  INTEGER
          {
           n12    (1),
		   n9     (2),
           n6     (3),
           n3     (4),
           p0     (5),
           p4     (6),
		   p6     (7),
           p10    (8)
          }            
      MAX-ACCESS  read-write
      STATUS  current
      DESCRIPTION
      "Transmit level in dBm.
       pxx = positive xx = +xx
       nxx = negative xx = -xx  "
      ::= {modmPrtLineEntry 3}

modmPrtLineRxLevel OBJECT-TYPE
      SYNTAX  INTEGER       
          {
           n14  (1),
		   n12  (2),
           n10  (3),
           n9   (4),
           n6   (5),
           n3   (6),
           p0   (7),
		   low  (8),
		   high (9)
          }            
      MAX-ACCESS  read-write
      STATUS  current
      DESCRIPTION
      "Rx Sensitivity in dBm.
       pxx = positive xx = +xx
       nxx = negative xx = -xx."
      ::= {modmPrtLineEntry 4}

modmPrtLineOutImp OBJECT-TYPE
      SYNTAX  INTEGER
      {
       infinite  (1),
       i75ohm    (2),
       i100ohm   (3),
       i120ohm   (4),
	   i150ohm   (5),
	   i300ohm   (6),
       i600ohm   (7)
      }            
      MAX-ACCESS  read-write
      STATUS  current
      DESCRIPTION
      "Output impedance in Ohm."
      ::= {modmPrtLineEntry 5}

modmPrtLineInImp OBJECT-TYPE
      SYNTAX  INTEGER
      {
       infinite  (1),
       i75ohm    (2),
       i100ohm   (3),
       i120ohm   (4),
	   i150ohm   (5),
	   i300ohm   (6),
       i600ohm   (7)
      }            
      MAX-ACCESS  read-write
      STATUS  current
      DESCRIPTION
      "Input impedance in Ohm."
      ::= {modmPrtLineEntry 6}

modmPrtLineCarrCntrl OBJECT-TYPE
      SYNTAX  INTEGER           
	      {
          off    (2),
          on     (3)
	      }
      MAX-ACCESS  read-write
      STATUS  current
      DESCRIPTION
      "Carrier control."
      ::= {modmPrtLineEntry 7}

modmPrtLineRAP OBJECT-TYPE
      SYNTAX  INTEGER
      {
       private (1),
       v110    (2),
       v220    (3),
	   notApplicable (255)
      }            
      MAX-ACCESS  read-write
      STATUS  current
      DESCRIPTION
      "Rate Adapting Protocol."
      ::= {modmPrtLineEntry 8}

modmPrtLineWaveLength OBJECT-TYPE
      SYNTAX  INTEGER
      {
       notApplicable (1),
       nm850         (2),
       nm1300        (3),
	   nm780Laser    (4),
	   nm1300Laser   (5),
	   nm1550Laser   (6)
      }            
      MAX-ACCESS  read-only
      STATUS  current
      DESCRIPTION
      "Wave Length of the optical Line.
       notApplicable - when the modem Line is not optical.
       The units are nano-meters [nm]."
      ::= {modmPrtLineEntry 9}

modmPrtLineCdSense OBJECT-TYPE
      SYNTAX  INTEGER
      {
       notApplicable (1),
       high          (2),
       low           (3)
      }            
      MAX-ACCESS  read-write
      STATUS  current
      DESCRIPTION
      "Carrier Detect Sense - Detection Sensitivity of Carrier Wave.
       high - high sensitivity
       low  - low  sensitivity. "
      ::= {modmPrtLineEntry 10}

modmPrtLineAIS OBJECT-TYPE
      SYNTAX  INTEGER
      {
       notApplicable (1),
       disable       (2),
       enable        (3)
      }            
      MAX-ACCESS  read-write
      STATUS  current
      DESCRIPTION
      "AIS enable/disable.
       notApplicable - for modems that do not support this feature."
      ::= {modmPrtLineEntry 11}


modmPrtLineCoding OBJECT-TYPE
      SYNTAX  INTEGER
      {
       notApplicable   	(1),
       ami   			(2),
       hdb3   			(3),
       b8zs 			(4)
      }            
      MAX-ACCESS  read-write
      STATUS  current
      DESCRIPTION
      "Line Coding."
      ::= {modmPrtLineEntry 12}


modmPrtLineLength OBJECT-TYPE
      SYNTAX  INTEGER
       {
		unknown      (1),
        len0p133ft   (2),
        len134p266ft (3),
        len267p399ft (4),
        len400p533ft (5),
        len534p655ft (6),

		notApplicable(255)
	      }
      MAX-ACCESS  read-write
      STATUS  current
      DESCRIPTION
      "This attribute is the line length mask parameter used only 
       for T1/DSU interfaces.
       len400p533ft=length range: 400ft to 533ft."
      ::= {modmPrtLineEntry 13}

modmPrtLineClkSrcPort OBJECT-TYPE
      SYNTAX  INTEGER
       {

		notApplicable(1),
		modem1 (2),
        modem2 (3),
        modem3 (4),
        modem4 (5)
	  }
      MAX-ACCESS  read-write
      STATUS  current
      DESCRIPTION
      "Clock Source Port.
      This parameter is relevant for external clock source."
      ::= {modmPrtLineEntry 14}

modmPrtLineDteClkConfig  OBJECT-TYPE
      SYNTAX  INTEGER
	  {
		notApplicable (1),
        dceExternal   (2),
        dce           (3)
	  }
      MAX-ACCESS  read-write
      STATUS  current
      DESCRIPTION
      "Indicates the clock source of the modems, which were not selected to supply
       the external clock."
      ::= {modmPrtLineEntry 15}

modmPrtLineMaskAlr  OBJECT-TYPE
      SYNTAX  INTEGER
	  {
		notApplicable (1),
        dontMask      (2),
        mask          (3)
	  }
      MAX-ACCESS  read-write
      STATUS  current
      DESCRIPTION
      "This parameter determine whether masking or not the alarms for this line."
      ::= {modmPrtLineEntry 16}


-- Traps

--NOTIFICATIONS

modmSaEvents OBJECT-IDENTITY
   STATUS  current
   DESCRIPTION
   "The events for Stand Alone Modems."
   ::= { modmSa 0 }

modmSysEvents OBJECT-IDENTITY
   STATUS  current
   DESCRIPTION
   "The events for General Modems."
   ::= { modmSys 0 }

modmSAlarmTrap NOTIFICATION-TYPE
      OBJECTS  {modmSaStatAlarms}
      STATUS  current
      DESCRIPTION
	  "The trap is sent every 5 seconds in which a change has 
	   occurred in the status of the variables sent. 
	   For modems containing a T1/E1 interface, dsx1LineStatus 
	   will be sent as well in the variables, after modmSaStatAlarms.
	   This trap is applicable for Stand-alone modems or Agents 
	   that are cards of a Hub."
      ::= { modmSaEvents 1 }


modmSLedTrap NOTIFICATION-TYPE
      OBJECTS  {agnLed}
      STATUS  current
      DESCRIPTION
	  "The trap is sent every 5 seconds in which a change has 
	   occurred in the state of one of the LEDs.
	   This trap is applicable for Stand-Alone modems or Agents 
	   that are cards of a Hub.
	   'agnLed' - will include both central and remote modems: 
	              first central, last remote."
      ::= { modmSaEvents 2 }

-- the following traps are for a modems-Hub or IMOD modems

modmHubConfigChange  NOTIFICATION-TYPE
      OBJECTS  {mdlCardType, mdlSPanelType}
      STATUS  current
      DESCRIPTION
	  "The trap is sent when any card of the modems Hub is inserted
	   or removed."
      ::= { modmSysEvents 3 }

modemMasterSlaveComm NOTIFICATION-TYPE
      OBJECTS  {modemMngLink}
      STATUS  current
      DESCRIPTION
	  "This trap is applicable only for IMOD modems .
	   The trap is sent when communication between a Master modem 
	   and its Slave is stopped or resumed.
	   'modemMngLink' includes the modemIdx."
      ::= { modmSysEvents 4 }

modemMasterChange NOTIFICATION-TYPE
      OBJECTS  {modemConfigMode, modemModeTemporary}
      STATUS  current
      DESCRIPTION
	  "This trap is applicable only for IMOD modems .
	   The trap is sent when a modem's permanent or temporary mode 
	   is changed.
	   'modemConfigMode' and 'modemModeTemporary' include the 
	    modemIdx."
      ::= { modmSysEvents 5 }

mngmntControlChange NOTIFICATION-TYPE
      OBJECTS  {modmHubController}
      STATUS  current
      DESCRIPTION
	  "This trap is applicable only for LRS-12.
	   The trap is sent when the Hub management controller is 
	   changed (NMS<->Terminal)."
      ::= { modmSysEvents 6 }

modemInvalidParameter NOTIFICATION-TYPE
      OBJECTS  {modemIdx}
      STATUS  current
      DESCRIPTION
	  "This trap is applicable only for IMOD cards of a Hub.
	   The trap is sent when an invalid parameter was Set to the 
	   modem."
      ::= { modmSysEvents 7 }

modemAlarm NOTIFICATION-TYPE
      OBJECTS  {modemActiveAlarms}
      STATUS  current
      DESCRIPTION
	  "This trap is applicable only for IMOD modems .
	   The trap is sent when the active alarms of an IMOD modem, 
	   change."
      ::= { modmSysEvents 8 }

cardStatusChange NOTIFICATION-TYPE
      OBJECTS  {mdlSLed}
      STATUS  current
      DESCRIPTION
	  "The trap is sent upon any change of the Leds status in the 
	   PS, CL or IMOD cards."
      ::= { modmSysEvents 9 }

modemSignalingChange NOTIFICATION-TYPE
      OBJECTS  {modmPrtDteSignaling}
      STATUS  current
      DESCRIPTION
	  "The trap is sent for any IMOD modem, when an unmasked
	   signal change occured in the attached variable (see
	   modemMaskSignaling object)."
      ::= { modmSysEvents 10 }

modmHubPsFail  NOTIFICATION-TYPE
      OBJECTS  {mdlSLed}
      STATUS  current
      DESCRIPTION
	  "The trap is sent when a PS card of the modems-Hub failed.
	   'mdlSLed' includes the mdlSIdx."
      ::= { modmSysEvents 11 }

modmHubIPModeChange  NOTIFICATION-TYPE
      OBJECTS  {modmHubIpMode}
      STATUS  current
      DESCRIPTION
	  "The trap is sent upon any change of modmHubIpMode parameter."
      ::= { modmSysEvents 12 }

modmInterfaceChange  NOTIFICATION-TYPE
      STATUS  current
      DESCRIPTION
	  "The trap is sent upon any change of interfaces for a modem that
	   is a card of a Hub or part of it.
	   In order to know what changed, for each product, specific variables will 
	   be attached. These variables will be specified in the product's spec.

	   For FOMi-E3/T3 and Optimux-4E1/T1-C : the trap will be sent when
	   the connectors card in LRS is removed/inserted."
      ::= { modmSysEvents 13 }


modmRackAlarms  NOTIFICATION-TYPE
      STATUS  current
      DESCRIPTION
	  "The trap is applicable for LRS-52.
	   The trap is sent when an alarm occurs. 
	   Attached variables are detailed in product specification."
      ::= { modmSysEvents 14 }


-- 
-- file :v:\doc\rdv\mib\ver485\dacs.txt
-- 

--Title:     RAD's DACS PRODUCTS MIB
--Version:   3.0
--Date:      27.04.95
--By:        Smadar Tauber
--File:      dacs.txt 
--
--Last update: 11-Aug-2002 Shlomo Shoham 


dacsMux       OBJECT IDENTIFIER ::= {radWan 3}

systemDacsMux OBJECT IDENTIFIER ::= {dacsMux 1}
mdlDacsMux    OBJECT IDENTIFIER ::= {dacsMux 2}
prtDacsMux    OBJECT IDENTIFIER ::= {dacsMux 3}
genDacsMux    OBJECT IDENTIFIER ::= {dacsMux 4}
    

--System level of DACS MIB
--
--Sa  - data specific to a stand-alone unit
--Hub - data specific to a Hub unit
--Rest of the branches are common to both types of units.

sysSa         OBJECT IDENTIFIER ::= {systemDacsMux 1}
sysHub        OBJECT IDENTIFIER ::= {systemDacsMux 2}
sysStatus     OBJECT IDENTIFIER ::= {systemDacsMux 3}
sysCurrentAlr OBJECT IDENTIFIER ::= {systemDacsMux 4}
sysBufferAlr  OBJECT IDENTIFIER ::= {systemDacsMux 5}
sysConfig     OBJECT IDENTIFIER ::= {systemDacsMux 6}
sysDbase      OBJECT IDENTIFIER ::= {systemDacsMux 7}


--Stand-alone specific parameters

sysSaSwchStatus OBJECT-TYPE
      SYNTAX  Integer32
      MAX-ACCESS  read-only
      STATUS  current
      DESCRIPTION
      "This object indicates the status of the switches on 
       the SA unit.
       Each switch is represented by a bit. The status is a sum
       of 2**n, according to the bits.
       
	   For SMODs products see modem's specification.
	   
	   For DXC product see the following:
       There are 4 switches:
       bit 0  SP-PAR (LSB)  '1' - Default parameters    
       bit 1  PSWRD         '1' - Password=default
                            '0' - Password=user selected
       bit 2  DB-INIT       '1' - DB initiated with default
                            '0' - DB initiated with NVRAM contents 
       bit 3  PC-SP  (MSB)  '1' - Management by terminal only
                            '0' - Management by NMS
       Example: If SP-PAR  and PSWRD bits are set ('1'), the value
             will be 3 (2**1 + 2**0).
       When the status of the switches is unknown, the value of
       this object will be 255."
      ::= { sysSa 1}

sysSaSwRevision OBJECT-TYPE
      SYNTAX  DisplayString (SIZE (0..255))
      MAX-ACCESS  read-only
      STATUS  current
      DESCRIPTION
      "This object indicates the Software revision of the 
       system."
      ::= {sysSa 2}

sysSaHwVersion OBJECT-TYPE
      SYNTAX  DisplayString (SIZE (0..255))
      MAX-ACCESS  read-only
      STATUS  current
      DESCRIPTION
      "This object indicates the Hardware version of the 
       system."
      ::= {sysSa 3}

sysSaPorts OBJECT-TYPE
      SYNTAX  Integer32
      MAX-ACCESS  read-only
      STATUS  current
      DESCRIPTION
   "This object indicates the ports that are present in the 
    system.
    Each possible port is represented by a bit.
    The value of this object is a sum of 2**n, n=number of bits.
    '1' - means that the port exists
    '0' - means that the port does not exist
    For detailed bit assignment, see product's spec.
    Bit 0 = LSB
    When this object is not relevant, the value will be 0.
    In some cases, this object may represent ports configuration
    of the system AND its far-end unit."
   ::= {sysSa 4}

sysSaReadSwch OBJECT-TYPE
      SYNTAX  Integer32
      MAX-ACCESS  read-write
      STATUS  current
      DESCRIPTION
      "This object indicates wether the configuration will be read from the DIP switches
       on the SA (stand alone) unit.
       Each switch is represented by a bit.
       If the bit is 1: the configuration will be read from the HW switch position.
       If the bit is 0: the configuration will be read from the SW user configuration.
       
       The DIP switches are different in each of the RAD devices.
       In the Tiny Router (starting from the LSB) the following switches exist:
       Bit 0: WAN Loop
       Bit 1: LAN Full Duplex (When LAN AUI connector, it is SQE)
       Bit 2: PPP (When WAN 4 Wire connector, it is LONG)
       Bit 3: IP Learn"
   ::= {sysSa 5}



--Hub specific parameters

--Hub Cassis data

sysChas  OBJECT IDENTIFIER ::= {sysHub 1}

chassTotalNoOfSlt  OBJECT-TYPE
      SYNTAX  Integer32
      MAX-ACCESS  read-only
      STATUS  current
      DESCRIPTION
      "This object indicates the number of physical slots in 
       the Hub chassis."
      ::= { sysChas 1 }

chassTotalNoOfIoSlt  OBJECT-TYPE
      SYNTAX  Integer32
      MAX-ACCESS  read-only
      STATUS  current
      DESCRIPTION
      "This object indicates the total number of physical IO slots 
       in the chassis, (not all slots must be occupied and active)."
      ::= { sysChas 2 }

chassTotalNoOfPsSlt  OBJECT-TYPE
      SYNTAX  Integer32
      MAX-ACCESS  read-only
      STATUS  current
      DESCRIPTION
      "This object indicates the number of physical Power Supply 
       slots in the chassis."
      ::= { sysChas 3 }

chassTotalNoOfClSlt  OBJECT-TYPE
      SYNTAX  Integer32
      MAX-ACCESS  read-only
      STATUS  current
      DESCRIPTION
      "This object indicates the number of physical Common Logic 
       slots in the chassis."
      ::= { sysChas 4 }

chassTotalNoOfMlSlt  OBJECT-TYPE
      SYNTAX  Integer32
      MAX-ACCESS  read-only
      STATUS  current
      DESCRIPTION
      "This object indicates the number of physical Main Link 
       slots in the chassis (Kmux)."
      ::= { sysChas 5 }


--Hub DCL parameters

sysDcl  OBJECT IDENTIFIER ::= {sysHub 2}


sysDclTable  OBJECT-TYPE
      SYNTAX SEQUENCE OF SysDclEntry
      MAX-ACCESS not-accessible
      STATUS  current
      DESCRIPTION
      "All the entries of this table are identical (have the 
       same value) for all the configurations (1..255) except 
       the TmpCnfg.
       The write operation into the Table Objects is valid only
       for the TmpCnfg entry."
       ::= { sysDcl 1}

sysDclEntry OBJECT-TYPE
      SYNTAX SysDclEntry
      MAX-ACCESS not-accessible
      STATUS current
	DESCRIPTION  "An entry in table."
	INDEX {sysDclCnfgIdx}
      ::= { sysDclTable 1}

SysDclEntry ::=
      SEQUENCE {
   		sysDclCnfgIdx        Integer32,
   		sysDclRedundancy     INTEGER,
   		sysDclActiveCl       INTEGER,
   		sysDclFlipDelay      INTEGER,
		sysDclFlipUponStnClk INTEGER 
      }

sysDclCnfgIdx OBJECT-TYPE
      SYNTAX Integer32 (1..255)
      MAX-ACCESS read-only
      STATUS current
      DESCRIPTION
      "This object indicates the Idx of the Cnfg(1..255) 
       being accessed ; Idx of 255 relates to the TmpCnfg.
       This object is identical for all the configurations (1..255).
       Only the TmpCnf(255) might have a  different value."
      ::= { sysDclEntry 1}
-- In phase I only the values 1 (Cnfg1) and 255 (temp) are valid.


sysDclRedundancy  OBJECT-TYPE
      SYNTAX  INTEGER
   {
   off (2),
   on  (3)
   }
      MAX-ACCESS  read-write
      STATUS  current
      DESCRIPTION
   " DCL redundancy desired state."
   ::= {sysDclEntry 2}

sysDclActiveCl  OBJECT-TYPE
      SYNTAX  INTEGER
   {
   auto (1),
   dclA (2),
   dclB (3)
   }
      MAX-ACCESS  read-write
      STATUS  current
      DESCRIPTION
   "Active desired DCL.
    When 'auto' is selected, the system automatically selects
    the active DCL."
   ::= {sysDclEntry 3}

sysDclFlipDelay  OBJECT-TYPE
      SYNTAX  INTEGER
   {
   t1min (1),
   t2min (2),
   t3min (3),
   t4min (4)
   }    
      MAX-ACCESS  read-write
      STATUS  current
      DESCRIPTION
   "If one DCL flip occured and a second one should be
    performed, the time from the previous flip is checked.
    If the time is shorter than the delay specified here
    (in minutes), the system should delay the flip operation 
    until time reaches the specified delay."
   ::= {sysDclEntry 4}

sysDclFlipUponStnClk  OBJECT-TYPE
      SYNTAX  INTEGER
   {
   notApplicable (1),
   no            (2),
   yes           (3)
   }    
      MAX-ACCESS  read-write
      STATUS  current
      DESCRIPTION
   "This object allows user to decide (yes/no) if Agent should Flip from 
    one DCL card to another, when there is Station Clock Fail in 
    the Online DCL card."
   ::= {sysDclEntry 5}


sysDclOnline  OBJECT-TYPE
      SYNTAX  INTEGER
   {
   dclA (1),
   dclB (2)
   }
      MAX-ACCESS  read-only
      STATUS  current
      DESCRIPTION
   "The active Dcl card of the agent."
   ::= {sysDcl 2}

sysDclCopyDbTable  OBJECT-TYPE
      SYNTAX SEQUENCE OF SysDclCopyDbEntry
      MAX-ACCESS not-accessible
      STATUS  current
      DESCRIPTION
      "This table enables to copy a cofiguration from the Offline
       Dcl to the Online Dcl."
       ::= { sysDcl 3}

sysDclCopyDbEntry OBJECT-TYPE
      SYNTAX SysDclCopyDbEntry
      MAX-ACCESS not-accessible
      STATUS current
	DESCRIPTION  "An entry in table."
	INDEX {sysDclCopyDbIdx}
      ::= { sysDclCopyDbTable 1}

SysDclCopyDbEntry ::=
      SEQUENCE {
   		sysDclCopyDbIdx       Integer32,
   		sysDclCopyDbCmd       INTEGER
      }

sysDclCopyDbIdx OBJECT-TYPE
      SYNTAX Integer32 (1..255)
      MAX-ACCESS read-only
      STATUS current
      DESCRIPTION
      "This object indicates the Idx of the Cnfg(1..255) 
       being accessed. "
      ::= { sysDclCopyDbEntry 1}

sysDclCopyDbCmd OBJECT-TYPE
      SYNTAX INTEGER {
   off(2),
   on (3)
   }
      MAX-ACCESS read-write
      STATUS current
      DESCRIPTION
      "When this command is sent to the agent, on(3), the Database
       specified (Db Idx), will be copied from the Offline Dcl 
       to the Online Dcl. Afterwards the value of this object will 
       automatically change to off(2). "
      ::= { sysDclCopyDbEntry 2}



--General System - General Status parameters 

sysSDateFormat  OBJECT-TYPE
      SYNTAX  INTEGER
       {
          ddMMYYYY (1),
          mmDDYYYY (2),
		  yyyyMMDD (4)
       }
      MAX-ACCESS  read-write
      STATUS  current
      DESCRIPTION
      "This object indicates the date and time format used for the
       sysSDateAndTimeCmd and for the alarm buffer report."
      ::= { sysStatus 1 }

sysSDateCmd  OBJECT-TYPE
      SYNTAX  DisplayString (SIZE (0..255))
      MAX-ACCESS  read-write
      STATUS  current
      DESCRIPTION
      "This object indicates the current date as it is known by the
       agent using its own real-time clock. The format would be as
       specified by the sysSDateFormat.
       This  parameter can be set for time synchronization between
       the NMS and the Agent.
       * For KM-2100 V1 and FCD-T1/E1 - the string should contain 
         '/' signs between day, month and year. Example: 12/08/1998.
       * For DXC and rest of the products - the string should contain 
         '-' signs between day, month and year. Example: 12-08-1998.
       The day value will be in the range: 1..31.
       The month value will be in the range: 1..12.
       The year value will be in the range: 1996..2050 for products
       supporting the '-' format."
      ::= { sysStatus 2 }

sysSTimeCmd  OBJECT-TYPE
      SYNTAX  DisplayString (SIZE (0..255))
      MAX-ACCESS  read-write
      STATUS  current
      DESCRIPTION
      "This object indicates the current time as it is known by the
       agent using its own real-time clock.
       This  parameter can be set for time synchronization between
       the NMS and the Agent.
       The string should contain ':' signs between hour, minute 
       and second. Example: 11:05:58."
      ::= { sysStatus 3 }

sysSActiveCnfg  OBJECT-TYPE
      SYNTAX  Integer32
      MAX-ACCESS  read-only
      STATUS  current
      DESCRIPTION
      "This object specifies the configuration number,
       that is currently  active and running."
      ::= { sysStatus 4 }
-- return 1 (db1) in phase I

sysSEditCnfg OBJECT-TYPE
      SYNTAX  Integer32
      MAX-ACCESS  read-only
      STATUS  current
      DESCRIPTION
      "This object indicates the  unique configuration number that
       is currently loaded into the tmp working space  for 
       manipulation and update operations. Value of 255 means no 
       config. is under editing process."
      ::= { sysStatus 5 }
-- return 1 (db1) in phase I


sysSEditBy OBJECT-TYPE
      SYNTAX  INTEGER
       {
           none            (1),
           snmp            (2),
           terCon1         (3),
           terCon2         (4),
           terInbandCon1   (5),
           terInbandCon2   (6),
           lcd             (7)
       }
      MAX-ACCESS  read-only
      STATUS  current
      DESCRIPTION
      "This entry indicates which MMI application is working on  
       the edited config.
       The editing phase starts at the first modify operation and 
       ends after a load operation."
      ::= { sysStatus 6 }

sysSClkSrc  OBJECT-TYPE
      SYNTAX  INTEGER
    {
        master  (1),
        fallback(2),
        internal(3),
        ml      (4) 
    }
      MAX-ACCESS  read-only
      STATUS  current
      DESCRIPTION
     "This entry indicates the source of the system clock."
      ::= { sysStatus 7 }

sysSAlrStatus OBJECT-TYPE
      SYNTAX  INTEGER
       {
  off      (2),
  major    (3),
  minor    (4),
  event    (5),
  warning  (6),
  critical (7)
       }
      MAX-ACCESS  read-only
      STATUS  current
      DESCRIPTION
      "Indicates the current alarm state only for system level.
       This object will be : 
       - critical(7): when there is at least one active (ON) critical 
                    alarm .
       - major (3): when there is no active critical alarm, but there is
                    at least one active (ON) major alarm .
       - minor (4): when there is no active major or critical alarm, but 
                    there is at least one active minor alarm.
       - warning (6): when there is no active major, critical or minor alarm, but 
                    there is at least one active warning alarm.
       - event (5): when there is no active alarm of another type, but 
                    there is at least one active event alarm.
       - off(2): when there is no active (ON) alarm (since last clear operation)."
      ::= { sysStatus 8 }

sysSAlrStatusAll OBJECT-TYPE
      SYNTAX  INTEGER
       {
  off      (2),
  major    (3),
  minor    (4),
  event    (5),
  warning  (6),
  critical (7)
       }
      MAX-ACCESS  read-only
      STATUS  current
      DESCRIPTION
      "Indicates the current alarm state including all levels: 
       system, card, port.
       - critical(7): when there is at least one active (ON) critical 
                    alarm .
       - major (3): when there is no active critical alarm, but there is
                    at least one active (ON) major alarm .
       - minor (4): when there is no active major or critical alarm, but 
                    there is at least one active minor alarm.
       - warning (6): when there is no active major, critical or minor alarm, but 
                    there is at least one active warning alarm.
       - event (5): when there is no active alarm of another type, but 
                    there is at least one active event alarm.
       - off(2): when there is no active (ON) alarm (since last clear operation)."
      ::= { sysStatus 9 }

sysSTestStatus OBJECT-TYPE
      SYNTAX  INTEGER
       {
  off(2),
  on (3)
       }
      MAX-ACCESS  read-only
      STATUS  current
      DESCRIPTION
      "Indicates the current test status (for all levels: system,
       card, port).
       This attribute will be set to: 
       - on(3): when there is at least one test in progress on the
                system/card/port
         otherwise the value will be off(2)."
      ::= { sysStatus 10 }


sysSSanityCheckStatus OBJECT-TYPE
      SYNTAX  INTEGER
       {
  unknown (1),
  fail    (2),
  warning (3),
  ok      (4)
       }
      MAX-ACCESS  read-only
      STATUS  current
      DESCRIPTION
      "Upon completion of the Sanity Check process on the TmpCnfg 
       this object will be set to:
       - fail(2): when there is at least one error (which is 
                  not just a warning) encountered
                  otherwise,
       - warning(3): when there are only warnings
                  otherwise,
       - ok(4).
       The value should be unknown(1), if the TmpCnfg was changed 
       after the last Sanity check."
      ::= { sysStatus 11 }

sysSNoOfSanityCheckErr OBJECT-TYPE
      SYNTAX  Integer32
      MAX-ACCESS  read-only
      STATUS  current
      DESCRIPTION
      "This object indicates the number of errors/warnings 
       discovered by the last Sanity Check process."
      ::= { sysStatus 12 }

sysSErrListTable OBJECT-TYPE
      SYNTAX SEQUENCE OF SysSErrListEntry
      MAX-ACCESS not-accessible
      STATUS current
	DESCRIPTION  "A table."
	::=  { sysStatus 13 }

sysSErrListEntry OBJECT-TYPE
      SYNTAX SysSErrListEntry
      MAX-ACCESS not-accessible
      STATUS current
	DESCRIPTION  "An entry in table."
	INDEX { sysSErrType, sysSErrIdx}
      ::= { sysSErrListTable 1}

SysSErrListEntry ::=
      SEQUENCE {
  sysSErrType         INTEGER,
  sysSErrIdx          Integer32,
  sysSErrDescription  DisplayString (SIZE (0..255))
      }

sysSErrType OBJECT-TYPE
      SYNTAX  INTEGER
   {
   error    (1),
   warning  (2)
   }
      MAX-ACCESS  read-only
      STATUS  current
      DESCRIPTION
      "The errors are recorded in the agent, in two separate lists, 
       according to their type:  error or warning."
    ::= { sysSErrListEntry 1}

sysSErrIdx OBJECT-TYPE
      SYNTAX  Integer32
      MAX-ACCESS  read-only
      STATUS  current
      DESCRIPTION
      "Unique index number to identify an entry in the error 
       or warning list .
       The maximum value  cannot exceed the value of
       'sysSNoOfSanityCheckErr' (actually, the sum of the Errors
       list max. index and the Warning list max. index should
       equal the value of'sysSNoOfSanityCheckErr')."
    ::= { sysSErrListEntry 2}

sysSErrDescription OBJECT-TYPE
      SYNTAX  DisplayString (SIZE (0..255))
      MAX-ACCESS  read-only
      STATUS  current
      DESCRIPTION
      "This object is a full text description of the sanity check
       error including error code, IO slot and port numbers related to
       the code ."
  ::= { sysSErrListEntry 3}

sysSMaxNoOfCnfg OBJECT-TYPE
      SYNTAX  Integer32
      MAX-ACCESS  read-only
      STATUS  current
      DESCRIPTION
      "Maximum number of configurations that can be defined and 
       stored in the DACS agent.
       If the DACS agent has a large capacity, the maximum will be 
       limited to 254."
      ::= { sysStatus 14 }
-- return 1 (db1) in phase I

sysSSelfTestResult OBJECT-TYPE
      SYNTAX  Integer32
      MAX-ACCESS  read-only
      STATUS  current
      DESCRIPTION
      "The test is performed by the active Common Logic card.
       The result will be a sum of 2**n according to the following
       bit convention:
    For DXC:
    bit 0   Database 1 Checksum Error (LSB)
    bit 1   Database 2 Checksum Error
    bit 2   I/O Expander Error
    bit 3   Counter Error
    bit 4   Matrix DPR Error
    bit 5   PS-A  5 Volt Error
    bit 6   PS-A 12 Volt Error
    bit 7   PS-B  5 Volt Error
    bit 8   PS-B 12 Volt Error
    bit 9   EPROM Failure

    For FCD:
    bit 0   I/O Expander Error (LSB)
    bit 1   Counter Error
    bit 2   EPROM Failure
    bit 3   Illegal Sys Config
    bit 4   SFIFO
    bit 5   EPIC Failure (ISDN)
    bit 6   XL Flash Fail  -- for MSDSL interface
    bit 7   XL MITEL Fail  -- for MSDSL interface 
    bit 8   XL Framer Fail -- for MSDSL interface
    bit 9   XL DSP Fail    -- for MSDSL interface 

	For LRS52  - refer to product's spec
     
    When a bit is ('1'), the error exists.
    When NO ERROR is encountered, this object's value will be 0."
      ::= { sysStatus 15 }

sysSRelayState OBJECT-TYPE
      SYNTAX  INTEGER
       {
  notApplicable (1),
  off(2),
  on (3)
       }
      MAX-ACCESS  read-only
      STATUS  current
      DESCRIPTION
      "Indicates the current state of the alarm relay.
       notApplicable - for agents that do not support this object."
      ::= { sysStatus 16 }

sysSInvertedAlr OBJECT-TYPE
      SYNTAX  INTEGER
       {
  notApplicable (1),
  no  (2),
  yes (3)
       }
      MAX-ACCESS  read-only
      STATUS  current
      DESCRIPTION
      "Indicates if there is any Inverted alarm at any level of the 
       system (sys, card, port).
       notApplicable - for agents that do not support this object."
      ::= { sysStatus 17 }

--The following table reports all the Flip events due to I/O Redundancy
--since last Clear command of the table. 

sysSRdnFlipTable OBJECT-TYPE
      SYNTAX SEQUENCE OF SysSRdnFlipEntry
      MAX-ACCESS not-accessible
      STATUS current
      DESCRIPTION
      "This table includes all the Flip events due to I/O Redundancy since
       last Clear command of this table."
      ::= { sysStatus 18 }

sysSRdnFlipEntry OBJECT-TYPE
      SYNTAX SysSRdnFlipEntry
      MAX-ACCESS not-accessible
      STATUS current
	DESCRIPTION  "An entry in table."
	INDEX { sysSRdnFlipIdx}
      ::= { sysSRdnFlipTable 1}

SysSRdnFlipEntry ::=
      SEQUENCE {
     sysSRdnFlipIdx   Integer32,
     sysSRdnFlipSlot  INTEGER,
     sysSRdnFlipPort  Integer32,
     sysSRdnFlipCause DisplayString,
     sysSRdnFlipDate  DisplayString,
     sysSRdnFlipTime  DisplayString
      }

sysSRdnFlipIdx OBJECT-TYPE
      SYNTAX  Integer32
      MAX-ACCESS  read-only
      STATUS  current
      DESCRIPTION
      "Unique index number to identify an entry in the Redundancy Flip list."
      ::= { sysSRdnFlipEntry 1}

sysSRdnFlipSlot OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       io13 (17),
       io14 (18),
       io15 (19),
       notApplicable (255)
       }
      MAX-ACCESS  read-only
      STATUS  current
      DESCRIPTION
      "The slot number from which Flip was performed."      
      ::= { sysSRdnFlipEntry 2}

sysSRdnFlipPort OBJECT-TYPE
      SYNTAX  Integer32 
      MAX-ACCESS  read-only
      STATUS  current
      DESCRIPTION
      "The port number from which Flip was performed.
	   For DXC:
	   For external ports the convention used will be:
         - first two digits will be: (IO slot number+10)
         - last one/two digits will be the port number within the 
           card, in odd numbers:
           port1 = 1
           port2 = 3
           port3 = 5 
           etc...
           Example: port2 of IO slot 11 will be: 213 .
       For internal ports the convention used will be:
         - first two digits will be: (IO slot number+10)
         - last one/two digits will be the port number within the 
           card, in even numbers:
           port1 = 2
           port2 = 4
           port3 = 6 
           etc...
           Example: port2 of IO slot 11 will be: 214 .

       For MP:
	   For external ports, the value will be as that of the port in the
	       card. Example: external-3 -> 3
                          external-4 -> 4
	   For internal ports, the value will be 100 + the port in the
	       card. Example: internal-1 -> 101
                          internal-4 -> 104	       
    
       100=notApplicable (when Redundancy is at card level)."      
      ::= { sysSRdnFlipEntry 3 }

sysSRdnFlipCause OBJECT-TYPE
      SYNTAX  DisplayString 
      MAX-ACCESS  read-only
      STATUS  current
      DESCRIPTION
      "The last cause that caused the Flip from the Slot (Port)
       of sysSRdnSlot, sysSRdnPort."
      ::= { sysSRdnFlipEntry 4}

sysSRdnFlipDate OBJECT-TYPE
      SYNTAX  DisplayString 
      MAX-ACCESS  read-only
      STATUS  current
      DESCRIPTION
      "Flip event Date. The format will be the one selected by user for 
       sysSDateFormat."
      ::= { sysSRdnFlipEntry 5}

sysSRdnFlipTime OBJECT-TYPE
      SYNTAX  DisplayString 
      MAX-ACCESS  read-only
      STATUS  current
      DESCRIPTION
      "Flip event Time. The format will be hh:mm:ss."
      ::= { sysSRdnFlipEntry 6}

sysSRdnFlipTableClearCmd OBJECT-TYPE
      SYNTAX  INTEGER
       {
         off  (2),
         on   (3)
       }
      MAX-ACCESS  read-write
      STATUS  current
      DESCRIPTION
      "This command, when Set to 'on', clears the Redundancy  Flip 
       table (sysSRdnFlipTable).
       After clear is performed, the agent will turn the value to 'off'
       automatically."
      ::= { sysStatus 19 }

sysSRdnFlipCmd OBJECT-TYPE
      SYNTAX  OBJECT IDENTIFIER
      MAX-ACCESS  read-write
      STATUS  current
      DESCRIPTION
      "This object enables the user to send a command to the Agent, to Flip
       from a current Online IO card to its Redundant card.  
       The value sent will be an Object Identifier of an entry in the sysCRdnTable.
       This entry defines the Redundant couple of Slots on which the Flip
       is applied.
       Setting this object, will cause the Agent to Flip from current Online
       card to its Redundant card.
       This manual flip command is applicable only for entries having 
       Redundancy Mode=Y Cable. 
       Agent will send the value 0 for Get."
      ::= { sysStatus 20}

sysSBusTable OBJECT-TYPE
      SYNTAX SEQUENCE OF SysSBusEntry
      MAX-ACCESS not-accessible
      STATUS current
      DESCRIPTION
      "This table includes data and status about the internal DXC BUS."
      ::= { sysStatus 21 }

sysSBusEntry OBJECT-TYPE
      SYNTAX SysSBusEntry
      MAX-ACCESS not-accessible
      STATUS current
	DESCRIPTION  "An entry in table."
	INDEX { sysSBusPortIdx}
      ::= { sysSBusTable 1}

SysSBusEntry ::=
      SEQUENCE {
     sysSBusPortIdx     Integer32,
     sysSBusStatus      INTEGER,
     sysSBusCapturePort Integer32,
	 sysSBusUtilization Integer32 
	}

sysSBusPortIdx OBJECT-TYPE
      SYNTAX  Integer32 
      MAX-ACCESS  read-only
      STATUS  current
      DESCRIPTION
      "The DXC BUS port number:
         - first two digits will be: (IO slot number+10)
         - last one/two digits will be the Bus port number, in odd numbers:
           port1 = 1
           port2 = 3
           Example: port2 of IO slot 11 will be: 213."
      ::= { sysSBusEntry 1 }

sysSBusStatus OBJECT-TYPE
      SYNTAX  INTEGER 
       {
		 free    (1),
         physical(2),
         virtual (3)
       }
      MAX-ACCESS  read-only
      STATUS  current
      DESCRIPTION
      "The Status of sysSBusPortIdx.
       free    - not used
       physical - captured by the port of the card physically installed
       virtual  - captured virtually by another port. Example: DIM port 
                 (by Destination) or by Transparent T3/E3  port."
      ::= { sysSBusEntry 2}

sysSBusCapturePort OBJECT-TYPE
      SYNTAX  Integer32 
      MAX-ACCESS  read-only
      STATUS  current
      DESCRIPTION
      "The Port that Captured the sysSBusPortIdx.
       - if sysSBusStatus=free, the value will be 'none'=0
	   - else, if sysSBusStatus=fixed, the value will be: sysSBusPortIdx
       - else, the value will be according to the port index that captured
         this Bus Port (according to DXC port index convention):
         - xx1, xx3, xx11, xx13, xx31, xx33, xx2..xx56(even numbers)
         - xx = (IO slot number+10) "
      ::= { sysSBusEntry 3}

sysSBusUtilization OBJECT-TYPE
      SYNTAX  Integer32 
      MAX-ACCESS  read-only
      STATUS  current
      DESCRIPTION
      "Utilization of sysSBusPortIdx resources, in percent [%]."
      ::= { sysSBusEntry 4}

--IO Redundancy - Commands

sysSRdnCmdTable OBJECT-TYPE
      SYNTAX SEQUENCE OF SysSRdnCmdEntry
      MAX-ACCESS not-accessible
      STATUS current
      DESCRIPTION
      "This table includes commands used for IO Redundancy."
      ::= { sysStatus 22 }

sysSRdnCmdEntry OBJECT-TYPE
      SYNTAX SysSRdnCmdEntry
      MAX-ACCESS not-accessible
      STATUS current
	  DESCRIPTION  "An entry in table."
	  INDEX {sysCRdnPrimeSlot, sysCRdnPrimePort }
      ::= { sysSRdnCmdTable 1}

SysSRdnCmdEntry ::=
     SEQUENCE {
     sysSRdnEnforcedChannel      INTEGER
	}

sysSRdnEnforcedChannel OBJECT-TYPE
     SYNTAX       INTEGER {
     notApplicable 	(1),
     noEnforcement 	(2),
     primary	    (3),
	 secondary		(4)
        }
     MAX-ACCESS    read-write
     STATUS        current
     DESCRIPTION
     "This is a command to override all switching considerations
      and enforce use of primary/ secondary connection only.
	  noEnforcement - cancels the state of override and goes back to
	                  usual switching considerations.
      Default = noEnforcement(2)."
     ::= {sysSRdnCmdEntry 1 }


--System Current Alarm Table
--
--This table contains all Events and only the major/minor alarms
--whose status is ON.

sysSAlrTable OBJECT-TYPE
      SYNTAX SEQUENCE OF SysSAlrEntry
      MAX-ACCESS not-accessible
      STATUS current
      DESCRIPTION
      "List of system level current existing alarms ."
      ::= { sysCurrentAlr 1 }

sysSAlrEntry OBJECT-TYPE
      SYNTAX SysSAlrEntry
      MAX-ACCESS not-accessible
      STATUS current
	DESCRIPTION  "An entry in table."
	INDEX { sysSAlrIdx}
      ::= { sysSAlrTable 1}

SysSAlrEntry ::=
      SEQUENCE {
     	sysSAlrIdx       Integer32,
     	sysSAlrCode      Integer32,
     	sysSAlrState     INTEGER, --Severity
     	sysSAlarmMask    INTEGER,
     	sysSAlarmInvert  INTEGER,
		sysSAlarmOnOff   INTEGER,
		sysSAlarmCounter Integer32 
	}

sysSAlrIdx OBJECT-TYPE
      SYNTAX  Integer32
      MAX-ACCESS  read-only
      STATUS  current
      DESCRIPTION
      "An index number of the current system alarms."
      ::= { sysSAlrEntry 1 }

sysSAlrCode OBJECT-TYPE
      SYNTAX  Integer32
      MAX-ACCESS  read-only
      STATUS  current
      DESCRIPTION
      "This object indicates a code related to a specific
       alarm description. The list of codes and their related
       descriptions will be sent to NMS request (for display purpose)
       by alrGenTable."
      ::= { sysSAlrEntry 2 }

sysSAlrState OBJECT-TYPE
      SYNTAX  INTEGER {
   event    (3),
   minor    (4),
   major    (5),
   warning  (6),
   critical (7)
       }
      MAX-ACCESS  read-only
      STATUS  current
      DESCRIPTION
      "This object indicates the alarm Severity."      
      ::= { sysSAlrEntry 3 }

sysSAlarmMask OBJECT-TYPE
      SYNTAX  INTEGER {
  off(2),
  on (3)
       }
      MAX-ACCESS  read-only
      STATUS  current
      DESCRIPTION
      "Alarm Mask is : on/off."
      ::= { sysSAlrEntry 4 }

sysSAlarmInvert OBJECT-TYPE
      SYNTAX  INTEGER {
  off(2),
  on (3)
       }
      MAX-ACCESS  read-only
      STATUS  current
      DESCRIPTION
      "Alarm Invert is : on/off."
      ::= { sysSAlrEntry 5 }

sysSAlarmOnOff OBJECT-TYPE
      SYNTAX  INTEGER {
  off(2),
  on (3)
       }
      MAX-ACCESS  read-only
      STATUS  current
      DESCRIPTION
      "Alarm state is : on/off."
      ::= { sysSAlrEntry 6 }

sysSAlarmCounter OBJECT-TYPE
      SYNTAX  Integer32
      MAX-ACCESS  read-only
      STATUS  current
      DESCRIPTION
      "A counter - how many times the alarm occured (ON) since last
       clear operation or since last Reset."
      ::= { sysSAlrEntry 7 }

sysSAlrClearCmd  OBJECT-TYPE
      SYNTAX  INTEGER
       {
  off(2),
  on (3)
       }
      MAX-ACCESS  read-write
      STATUS  current
      DESCRIPTION
      "Setting this attribute to ON, will enforce a  clear 
       operation on the system level alarms . Upon completion, 
       the value will automatically change to off(2)."
      ::= { sysCurrentAlr 2 }


sysSAlrClearAllCmd  OBJECT-TYPE
      SYNTAX  INTEGER
       {
  off(2),
  on (3)
       }
      MAX-ACCESS  read-write
      STATUS  current
      DESCRIPTION
      "Setting this attribute to ON, will enforce a  clear 
       operation on all levels alarms . Upon completion, 
       the value will automatically change to off(2)."
      ::= { sysCurrentAlr 3 }

sysSAlrMaskAll  OBJECT-TYPE
      SYNTAX  INTEGER
       {
  off(2),
  on (3)
       }
      MAX-ACCESS  read-write
      STATUS  current
      DESCRIPTION
      "on(3)  - will cause masking of all the system level alarms.
                These alarms will not be sent to NMS and will not 
                be taken into account for Alarms Status.
       off(2) - will unmask all system level alarms except those 
                masked via the sysSAlrMask. "
      ::= { sysCurrentAlr 4 }

sysSAlrMask OBJECT-TYPE
      SYNTAX OCTET STRING  (SIZE (8))
      MAX-ACCESS read-write
      STATUS current
   DESCRIPTION
   "This object is a mask that indicates which system level 
    alarms are masked. The masked alarms (their bit is set to 
    '1') are neither sent to the manager, nor taken into account
    for alarm status and LEDs.
    Bit no. = Alarm code
    The bits that do not belong to the system level will be 0.
    This object is applicable only when sysSAlrMaskAll=off 
    (otherwise all system alarms are masked).
    Example: When Alarms having the codes 6 and 11 are masked,
             the value of this object will be 840 (hex)."
      ::= { sysCurrentAlr 5 }

sysSAlrDataUpdateCmd  OBJECT-TYPE
      SYNTAX  INTEGER
       {
        off(2),
        on (3)
       }
      MAX-ACCESS  read-write
      STATUS  current
      DESCRIPTION
      "on(3)  - will cause Update of the Alarms Severity, Attributes and Report
                tables.
       off(2) - Upon completion, the value will automatically change to off(2)."
      ::= { sysCurrentAlr 6 }


--System Buffer Alarm Table
--
--This table contains all Events and all the major/minor alarms
--The buffer is cyclic and contains the most recent alarms.
--Since this table contains also the alarms occurence time,
--(appearance/disappearance for major/minor alarms), an alarm may 
--appear several times in this table, with alternate state: major, 
--off, major, etc.. 

sysBufferAlrTable OBJECT-TYPE
      SYNTAX SEQUENCE OF SysBufferAlrEntry
      MAX-ACCESS not-accessible
      STATUS current
      DESCRIPTION
      "List of current existing alarms (of all levels)."
      ::= { sysBufferAlr 1 }

sysBufferAlrEntry OBJECT-TYPE
      SYNTAX SysBufferAlrEntry
      MAX-ACCESS not-accessible
      STATUS current
	DESCRIPTION  "An entry in table."
	INDEX { sysBufferAlrIdx}
      ::= { sysBufferAlrTable 1}

SysBufferAlrEntry ::=
      SEQUENCE {
     	sysBufferAlrIdx   Integer32,
     	sysBufferAlrCode  Integer32,
     	sysBufferAlrState INTEGER,
     	sysBufferAlrSlot  INTEGER,
     	sysBufferAlrPort  Integer32,
     	sysBufferAlrDate  DisplayString,
     	sysBufferAlrTime  DisplayString
      }

sysBufferAlrIdx OBJECT-TYPE
      SYNTAX  Integer32
      MAX-ACCESS  read-only
      STATUS  current
      DESCRIPTION
      "An index number of the current alarms."
      ::= { sysBufferAlrEntry 1 }

sysBufferAlrCode OBJECT-TYPE
      SYNTAX  Integer32
      MAX-ACCESS  read-only
      STATUS  current
      DESCRIPTION
      "This object indicates a code related to a specific
       alarm description. The list of codes and thir related
       descriptions will be known by the NMS (for display purpose)
       and will appear in the unit's user manual."
      ::= { sysBufferAlrEntry 2 }

sysBufferAlrState OBJECT-TYPE
      SYNTAX  INTEGER {
     off      (2),
     event    (3),
     minor    (4),
     major    (5),
	 warning  (6),
     critical (7)
       }
      MAX-ACCESS  read-only
      STATUS  current
      DESCRIPTION
      "This object indicates the alarm type.
       minor/major/warning/critical - indicates appearance of the problem 
                     and the type.
       event       - indicates occurence of an event.
       off         - indicates disappearance of an alarm. "      
      ::= { sysBufferAlrEntry 3 }


sysBufferAlrSlot OBJECT-TYPE
      SYNTAX  INTEGER 
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
    kmxPsA (101),
    kmxPsB (102),
    kmxMlA (103),
    kmxMlB (104),
    kmxCl  (105),
    kmxOpt (106),
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118),
    notApplicable (255)
       }
      MAX-ACCESS  read-only
      STATUS  current
      DESCRIPTION
      "The slot number this alarm refers to.
       When the alarm refers to a system function OR the DACS agent 
       is a stand-alone unit, the value will be 'notApplicable(255)'."      
      ::= { sysBufferAlrEntry 4 }

sysBufferAlrPort OBJECT-TYPE
      SYNTAX  Integer32 
      MAX-ACCESS  read-only
      STATUS  current
      DESCRIPTION
      "The port number this alarm refers to.
       If the port number is irrelevant to this alarm (if it is
       a system/card level alarm) the value will be 9999."     
      ::= { sysBufferAlrEntry 5 }

sysBufferAlrDate OBJECT-TYPE
      SYNTAX  DisplayString (SIZE (0..255))
      MAX-ACCESS  read-only
      STATUS  current
      DESCRIPTION
      "The date when the alarm occured. The format will be according
       to sysSDateFormat."     
      ::= { sysBufferAlrEntry 6 }


sysBufferAlrTime OBJECT-TYPE
      SYNTAX  DisplayString (SIZE (0..255))
      MAX-ACCESS  read-only
      STATUS  current
      DESCRIPTION
      "The time when the alarm occured." 
      ::= { sysBufferAlrEntry 7 }


sysBufferAlrClearCmd OBJECT-TYPE
      SYNTAX  INTEGER
       {
  off(2),
  on (3)
       }
      MAX-ACCESS  read-write
      STATUS  current
      DESCRIPTION
      "Setting this attribute to ON, will enforce a  clear 
       operation on the Alarms Buffer. Upon completion, 
       the value will automatically change to off(2)."
      ::= { sysBufferAlr 2 }


--System Configuration Parameters

sysCClkSrcTable  OBJECT-TYPE
      SYNTAX SEQUENCE OF SysCClkSrcEntry
      MAX-ACCESS not-accessible
      STATUS  current
      DESCRIPTION
      "All the entries of this table are identical (have the 
       same value) for all the configurations (1..255) except 
       the TmpCnfg.
       The write operation into the Table Objects is valid only
       for the TmpCnfg entry."
       ::= { sysConfig 1}

sysCClkSrcEntry OBJECT-TYPE
      SYNTAX SysCClkSrcEntry
      MAX-ACCESS not-accessible
      STATUS current
	DESCRIPTION  "An entry in table."
	INDEX {sysCClkCnfgIdx, sysCClkSrcIdx}
      ::= { sysCClkSrcTable 1}

SysCClkSrcEntry ::=
      SEQUENCE {
   sysCClkCnfgIdx      Integer32,
   sysCClkSrcIdx       INTEGER,
   sysCClkSrcMode      INTEGER,
   sysCClkSrcPrt       Integer32,
   sysCClkStationFreq  INTEGER,
   sysCClkRevertiveTimeout  Integer32,
   sysCClkStationIf    INTEGER 
	}

sysCClkCnfgIdx OBJECT-TYPE
      SYNTAX Integer32 (1..255)
      MAX-ACCESS read-only
      STATUS current
      DESCRIPTION
      "This attribute indicates the Idx of the Cnfg(1..255) being 
       accessed ; Idx of 255 relates to the TmpCnfg."
      ::= { sysCClkSrcEntry 1}
-- In phase I of DXC and FCD, only the values 1 (Cnfg1) and 255 
-- (temp) are valid.

sysCClkSrcIdx OBJECT-TYPE
      SYNTAX  INTEGER 
       {
     master    (1),
     fallback  (2)
    }
      MAX-ACCESS  read-only
      STATUS  current
      DESCRIPTION
      "An index in the table. There are only two entries in the 
       table. 
       master   - refers Master clock parameters 
       fallback - refers Fallback clock parameters"
      ::= { sysCClkSrcEntry 2}

sysCClkSrcMode OBJECT-TYPE
      SYNTAX  INTEGER
       {
     none            (1),
     internal        (2),
     rxClk           (3),
     station         (4),
     lbt             (5),
	 ntr             (6),
	 adaptive        (7),  
     notApplicable (255)
       }
      MAX-ACCESS  read-write
      STATUS  current
      DESCRIPTION
      "This entry indicates the source the nodal timing is 
       locked to.
       none     - is an invalid option for Master clock.
       internal - is an invalid option for Fallback clock .
       station  - is an invalid option for a stand-alone unit. 
       lbt      - loop-back timing
	   ntr      - A system locked reference clock
	   adaptive - clcok locking is achieved by altering the clock 
	              according to the data load
       notApplicable - for ML source of Kmux or ML Timing 
                       combinations when Master/Fallback clock are
                       not applicable."
      ::= { sysCClkSrcEntry 3}


sysCClkSrcPrt OBJECT-TYPE
      SYNTAX  Integer32
      MAX-ACCESS  read-write
      STATUS  current
      DESCRIPTION
      "This entry is valid only when working in rxClk mode.
       
       For ACE2002 in case of invalid entry the return value 
       will be 0. 
       For other products in case of invalid entry the return 
       value will be 9999.

       The valid port number depends on the IO slot no.,  the 
       installed card type and the port type: outside, inside, 
       SP.
    * The SP ports will be numbered as follows:
     - SP port 1 :  1
     - SP port 2 :  2
	   For external ports the convention used will be (for DXC):
         - first two digits will be: (IO slot number+10)
         - last one/two digits will be the port number within the 
           card, in odd numbers:
           port1 = 1
           port2 = 3
           port3 = 5 
           etc...
           Example: port2 of IO slot 11 will be: 213 .
       For internal ports the convention used will be (for DXC):
         - first two digits will be: (IO slot number+10)
         - last one/two digits will be the port number within the 
           card, in even numbers:
           port1 = 2
           port2 = 4
           port3 = 6 
           etc...
           Example: port2 of IO slot 11 will be: 214 .

      For Kmux, the port will be according to : Slot*100+Ch.
      
      For ACE2002 and LA140, the port will be ifIndex."
      ::= { sysCClkSrcEntry 4}

sysCClkStationFreq OBJECT-TYPE
      SYNTAX  INTEGER
       {
     notApplicable   (1),
     f1544Khz        (2),
     f2048Khz        (3)
       }
      MAX-ACCESS  read-write
      STATUS  current
      DESCRIPTION
      "This entry indicates the frequency of the station clock 
       when the source is 'station'.  
       The value will be applicable only when the sysCClkSrcMode is 
       'station'. "
      ::= { sysCClkSrcEntry 5}

sysCClkRevertiveTimeout OBJECT-TYPE
      SYNTAX  Integer32
      MAX-ACCESS  read-write
      STATUS  current
      DESCRIPTION
      "The time in seconds in which the system will monitor the higher
       level clock source, before decision to revert to that clock.
       In case the time is zero, revertive mode will be disabled."
      ::= { sysCClkSrcEntry 6}

sysCClkStationIf OBJECT-TYPE
      SYNTAX  INTEGER
       {
       notApplicable (1),
       g703          (2),
       rs422         (3)
       }
      MAX-ACCESS  read-write
      STATUS  current
      DESCRIPTION
      "This entry indicates the electrical interface connected to the
       station clock, when the source is 'station'.  
       The value will be applicable only when the sysCClkSrcMode is 
       'station'. "
      ::= { sysCClkSrcEntry 7}


sysCnfgTable  OBJECT-TYPE
      SYNTAX SEQUENCE OF SysCnfgEntry
      MAX-ACCESS not-accessible
      STATUS  current
      DESCRIPTION
      "All the entries of this table are identical (have the 
       same value) for all the configurations (1..255) except 
       the TmpCnfg.
       The write operation into the Table Objects is valid only
       for the TmpCnfg entry."
       ::= { sysConfig 2}

sysCnfgEntry OBJECT-TYPE
      SYNTAX SysCnfgEntry
      MAX-ACCESS not-accessible
      STATUS current
	DESCRIPTION  "An entry in table."
	INDEX {sysCnfgIdx}
      ::= { sysCnfgTable 1}

SysCnfgEntry ::=
      SEQUENCE {
   sysCnfgIdx       Integer32,
   sysCMatrixMode   INTEGER,
   sysCIsdnFormat   INTEGER,
   sysCRoutingOnEth INTEGER,
   sysCAutoConfigEnable INTEGER,
   sysCIntTsAllocMode   INTEGER
      }

sysCnfgIdx OBJECT-TYPE
      SYNTAX Integer32 (1..255)
      MAX-ACCESS read-only
      STATUS current
      DESCRIPTION
      "This attribute indicates the Idx of the Cnfg(1..255) being 
       accessed ; Idx of 255 relates to the TmpCnfg."
      ::= { sysCnfgEntry 1}

sysCMatrixMode OBJECT-TYPE
      SYNTAX  INTEGER
       {
  notApplicable  (1),
  bidirectional  (2),
  unidirectional (3)
       }
      MAX-ACCESS  read-write
      STATUS  current
      DESCRIPTION
      "Indicates the TS Matrix Mode:
    bidirectional  - TS Assignment Matrix is symmetric.
    unidirectional - TS Assignment Matrix can be asymmetric.
       notApplicable - for agents that do not support this feature."
      ::= { sysCnfgEntry 2}

sysCIsdnFormat OBJECT-TYPE
      SYNTAX  INTEGER
       {
  notApplicable (1),
  te  (2),
  nt  (3)
       }
      MAX-ACCESS  read-write
      STATUS  current
      DESCRIPTION
      "ISDN format. This parameter controls the operation mode of
    the ISDN ports.
    te - ISDN timing is derived from the signal received
         from the equipment it is connected to.
    nt - timing of the transmit path is locked to the nodal 
         timing source.
       notApplicable - for agents that do not support this feature."
      ::= { sysCnfgEntry 3}

sysCRoutingOnEth OBJECT-TYPE
      SYNTAX  INTEGER
       {
      notApplicable (1),
      none          (2),  
      proprietary   (3),
      rip2          (4)
       }
      MAX-ACCESS  read-write
      STATUS  current
      DESCRIPTION
      "Mng Routing Protocol on the online CL Ethernet port."
      ::= { sysCnfgEntry 4}

sysCAutoConfigEnable OBJECT-TYPE
      SYNTAX  INTEGER
       {
      notApplicable (1),
      disable       (2),  
      enable        (3)
       }
      MAX-ACCESS  read-write
      STATUS  current
      DESCRIPTION
      "This object enables user to enable/disable activating
       the Auto Configuration. When Auto Configuration is activated,
       the device learns its configuration Automatically from the Net 
       it is connected to."
      ::= { sysCnfgEntry 5}

sysCIntTsAllocMode OBJECT-TYPE
      SYNTAX  INTEGER
       {
      notApplicable (1),
      static        (2),  
      dynamic       (3)
       }
      MAX-ACCESS  read-write
      STATUS  current
      DESCRIPTION
      "This object enables user to select the mode of Internal TS 
       Allocation.
       static - user has to select for each Dynamic card port, the 
                Maximum TSs expected to be connected (including future
                growth). This number will be allocated to the ports,
                so that if number of connected TSs will grow within
                the limits of this Maximum TS limit, no disruption
                of data flow will occur for other ports.
       dynamic- TS allocation is done dynamically according to the 
                connected TSs. No future reservations are done. This mode
                may cause data disruption on other ports/slots if user
                will want to change the number of connected TSs for a
                Dynamic card port.
       Default=static(2).         "
      ::= { sysCnfgEntry 6}


--System I/O Redundacy Table
--
--This table contains all I/O cards/ports that have redundancy,
--data about the redundant card/port and parameters regarding the
--redundancy operation.
--The table indexes are Cnfg and the Primary card&port 


sysCRdnTable OBJECT-TYPE
      SYNTAX SEQUENCE OF SysCRdnEntry
      MAX-ACCESS not-accessible
      STATUS current
      DESCRIPTION
      "Configuration of all Redundant I/O cards and ports.
       The write operation into the table objects is valid only
       for the TmpCnfg.
       A Slot/Port that have no Redundancy, will not exist in this
       table."
      ::= { sysConfig 3 }

sysCRdnEntry OBJECT-TYPE
      SYNTAX SysCRdnEntry
      MAX-ACCESS not-accessible
      STATUS current
	DESCRIPTION  "An entry in table."
	INDEX { sysCRdnCnfgIdx, sysCRdnPrimeSlot, sysCRdnPrimePort}
      ::= { sysCRdnTable 1}

SysCRdnEntry ::=
      SEQUENCE {
     sysCRdnCnfgIdx       				Integer32,
     sysCRdnPrimeSlot     				INTEGER,
     sysCRdnPrimePort     				Integer32,
     sysCRdnSecSlot       				INTEGER,
     sysCRdnSecPort       				Integer32,
     sysCRdnMode          				INTEGER,
     sysCRdnRecMode       				INTEGER,
     sysCRdnRecTime       				Integer32,
     sysCRdnHwSwFlip      				INTEGER,
     sysCRdnRowStatus     				RowStatus,
	 sysCRdnOnline        				INTEGER,
	 sysCRdnSwitchingMode 				INTEGER,
	 sysCRdnFlipUponEvent 				Integer32,
	 sysCRdnLosOrLofTime  				Integer32,
	 sysCRdnEventsTimeWindow			Integer32,
	 sysCRdnSequenceNumberThreshold		Integer32,
	 sysCRdnBufferErrorsThreshold		Integer32,
	 sysCRdnBuffUnderrunTime			Integer32
	 	 
      }

sysCRdnCnfgIdx OBJECT-TYPE
      SYNTAX  Integer32
      MAX-ACCESS  read-only
      STATUS  current
      DESCRIPTION
      "This object indicates the Idx of the Cnfg(1..255) being 
       accessed ; Idx of 255 relates to the TmpCnfg."
      ::= { sysCRdnEntry 1 }

sysCRdnPrimeSlot OBJECT-TYPE
      SYNTAX  INTEGER 
       {
       io1   (5),
       io2   (6),
       io3   (7),
       io4   (8),
       io5   (9),
       io6  (10),
       io7  (11),
       io8  (12),
       io9  (13),
       io10 (14),
       io11 (15),
       io12 (16),
       io13 (17),
       io14 (18),
       io15 (19),
       notApplicable (255)
       }
      MAX-ACCESS  read-only
      STATUS  current
      DESCRIPTION
      "The slot number of the Primary card of Redundancy.
       The Primary card should be the card that user wishes to be
       the online card (usually the more important one).
       For some Redundancy modes the importance of the redundant 
       cards/ports is the same. "      
      ::= { sysCRdnEntry 2 }

sysCRdnPrimePort OBJECT-TYPE
      SYNTAX  Integer32 
      MAX-ACCESS  read-only
      STATUS  current
      DESCRIPTION
      "The port number.
	   For DXC:
	   For external ports the convention used will be:
         - first two digits will be: (IO slot number+10)
         - last one/two digits will be the port number within the 
           card, in odd numbers:
           port1 = 1
           port2 = 3
           port3 = 5 
           etc...
           Example: port2 of IO slot 11 will be: 213 .
       For internal ports the convention used will be:
         - first two digits will be: (IO slot number+10)
         - last one/two digits will be the port number within the 
           card, in even numbers:
           port1 = 2
           port2 = 4
           port3 = 6 
           etc...
           Example: port2 of IO slot 11 will be: 214 .

       For MP:
	   For external ports, the value will be as that of the port in the
	       card. Example: external-3 -> 3
                          external-4 -> 4
	   For internal ports, the value will be 100 + the port in the
	       card. Example: internal-1 -> 101
                          internal-4 -> 104
       For IP Bundles, the value will be the Bundle ifIndex.                   	       

       For other products - refer to product specification.

       100=notApplicable (when Redundancy is at card level)."      
      ::= { sysCRdnEntry 3 }

sysCRdnSecSlot OBJECT-TYPE
      SYNTAX  INTEGER 
       {
       io1   (5),
       io2   (6),
       io3   (7),
       io4   (8),
       io5   (9),
       io6  (10),
       io7  (11),
       io8  (12),
       io9  (13),
       io10 (14),
       io11 (15),
       io12 (16),
       io13 (17),
       io14 (18),
       io15 (19),
       notApplicable (255)
       }
      MAX-ACCESS  read-create
      STATUS  current
      DESCRIPTION
      "The slot number of the Secondary card of Redundancy matching
       the Primary slot."      
      ::= { sysCRdnEntry 4 }

sysCRdnSecPort OBJECT-TYPE
      SYNTAX  Integer32 
      MAX-ACCESS  read-create
      STATUS  current
      DESCRIPTION
      "The port number.
	   For DXC:
	   For external ports the convention used will be:
         - first two digits will be: (IO slot number+10)
         - last one/two digits will be the port number within the 
           card, in odd numbers:
           port1 = 1
           port2 = 3
           port3 = 5 
           etc...
           Example: port2 of IO slot 11 will be: 213 .
       For internal ports the convention used will be:
         - first two digits will be: (IO slot number+10)
         - last one/two digits will be the port number within the 
           card, in even numbers:
           port1 = 2
           port2 = 4
           port3 = 6 
           etc...
           Example: port2 of IO slot 11 will be: 214 .

       For MP:
	   For external ports, the value will be as that of the port in the
	       card. Example: external-3 -> 3
                          external-4 -> 4
	   For internal ports, the value will be 100 + the port in the
	       card. Example: internal-1 -> 101
                          internal-4 -> 104	       
       For IP Bundles, the value will be the Bundle ifIndex.                   	       

       For other products - refer to product specification.

       100=notApplicable (when Redundancy is at card level)."      
      ::= { sysCRdnEntry 5 }

sysCRdnMode OBJECT-TYPE
      SYNTAX  INTEGER
       {
          dualCableAIS        (2),
          yCable              (3),
          dualCableParallelTx (4),
          backup              (5),
          singleSlotProtection(6),
		  onePlusOne		  (7),
		  oneToOne			  (8)
       }
      MAX-ACCESS  read-create
      STATUS  current
      DESCRIPTION
      "Redundancy Mode.
       DXC supports: yCable(3), singleSlotProtection(6) and dualCableParallelTx(4)
       MP  supports: dualCableAIS(2), yCable(3), dualCableParallelTx(4) and
                     backup(5).
       backup - will be used when a port is backup of more than one port.
       IPmux: onePlusOne(7) and oneToOne(8) use for Bundle redundancy."
      ::= { sysCRdnEntry 6 }

sysCRdnRecMode OBJECT-TYPE
      SYNTAX  INTEGER
       {
          auto        (2),
          manual      (3)
       }
      MAX-ACCESS  read-create
      STATUS  current
      DESCRIPTION
      "Recovery Mode. This object determines if after recovery
       of the failed card/port it will become on-line again or not:
       auto - automatic . In this case, the failed card/port will become
           on-line again after recovery, automatically.
       manual - In this case, the failed card/port will not become
             on-line again after recovery."
      ::= { sysCRdnEntry 7 }

sysCRdnRecTime OBJECT-TYPE
      SYNTAX  Integer32 (1..99)
      MAX-ACCESS  read-create
      STATUS  current
      DESCRIPTION
      "Redundancy Recovery Time (sec). After switching to the current 
       online card, the next switch can be performed only after a 
       minimum time, indicated by this object.
       This object is applicable only when sysCRdnRecMode=auto."
      ::= { sysCRdnEntry 8 }

sysCRdnHwSwFlip OBJECT-TYPE
      SYNTAX  INTEGER
       {
          notApplicable(1),
          hw           (2),
          sw           (3)
       }
      MAX-ACCESS  read-create
      STATUS  current
      DESCRIPTION
      "HW or SW decision for Redundancy Flip. 
       This object is applicable only for sysCRdnMode=singleSlotProtection.
       HW - decision is by I/O card
       SW - decision is by CL SW."
      ::= { sysCRdnEntry 9 }

sysCRdnRowStatus  OBJECT-TYPE
     SYNTAX  RowStatus
     MAX-ACCESS   read-create
     STATUS   current
     DESCRIPTION
     "This parameter allows NMS to create/delete entries of this table.
      The only possible supported RowStatus vaules are
      active (1) and destroy (6)."
     ::= { sysCRdnEntry 10 }

sysCRdnOnline OBJECT-TYPE
      SYNTAX  INTEGER
       {
          notApplicable (1),
          primary       (2),
          secondary     (3)
       }
      MAX-ACCESS  read-only
      STATUS  current
      DESCRIPTION
      "Status - who is the Online (current) Redundancy Slot/Port. 
       This object shows only the Online Slot/Port regarding the Redundancy. 
       mdlSActivity or prtGenActiveStatus of the same Slot/Port may be Offline."
      ::= { sysCRdnEntry 11 }

sysCRdnSwitchingMode  OBJECT-TYPE
      SYNTAX  INTEGER
       {
          notApplicable    (1),
          biDirectional    (2),	--1+1
          uniDirectional   (3)	--1:1
       }
      MAX-ACCESS  read-create
      STATUS  current
      DESCRIPTION
      "This object defines which Self Healing Ring (SHR) SDH ring is used: 
       Uni Directional or BiDirectional. The type of the ring
       is defined according to the direction of traffic flow under 
       normal working conditions. 

       In Bi Directional ring, the duplex traffic is on the same path 
       and transverses the same set of nodes for both directions of transmission. 
       In Uni Directional ring, the duplex traffic travels over opposite path 
       (per direction) and all the node of the ring are involved.

       For Uni Directional  SHR Protection Switching (Single Ended Switching) 
       is controlled by one node of the SDH ring, and does not require a protocol.
       For Bi Directional SHR Protection Switching (Dual Ended switching) 
       is controlled by some nodes of  the ring and requires a protocol"
      ::= { sysCRdnEntry 12 }

sysCRdnFlipUponEvent  OBJECT-TYPE
     SYNTAX  Integer32
     MAX-ACCESS   read-create
     STATUS   current
     DESCRIPTION
     "This object allows user to define if Flip to the other port will
      be performed (or not), for certain possible events.
      Each event is represented by a bit. The value of the object is a sum
      of 2**n, according to the bits having '1' value.
	  '1' - means that Flip should occur due to this event.
      Bit 0 (LSB) = SD (Signal Degraded).
      For IPmux:
      Bit 0 (LSB) = TDM Line LOS/LOF.
      Bit 1       = Sequence Number.
      Bit 2		  = Jitter Buffer errors."
     ::= { sysCRdnEntry 13 }

sysCRdnLosOrLofTime OBJECT-TYPE
    SYNTAX  Integer32 
    MAX-ACCESS  read-create
    STATUS  current
    DESCRIPTION
    "This parameter determines how much time to wait before switching,
     after LOF or LOS are detected on the TDM Line.
     For Ipmux time is counted in msec."
    ::= { sysCRdnEntry 14 }

sysCRdnEventsTimeWindow OBJECT-TYPE
    SYNTAX  Integer32 
    MAX-ACCESS  read-create
    STATUS  current
    DESCRIPTION
    "This parameter determines the time window in which 
    to count events to trigger protection switching.
     For Ipmux time is counted in seconds."
    ::= { sysCRdnEntry 15 }

sysCRdnSequenceNumberThreshold OBJECT-TYPE
    SYNTAX  Integer32 
    MAX-ACCESS  read-create
    STATUS  current
    DESCRIPTION
    "This parameter determines the number of Sequence Number errors
     that should occur in the time window in order to cause switching."
    ::= { sysCRdnEntry 16 }

sysCRdnBufferErrorsThreshold OBJECT-TYPE
    SYNTAX  Integer32 
    MAX-ACCESS  read-create
    STATUS  current
    DESCRIPTION
    "This parameter determines the number of Buffer undeflow/ overflow events
     occured in the time window that cause switching."
    ::= { sysCRdnEntry 17 }

sysCRdnBuffUnderrunTime OBJECT-TYPE
    SYNTAX  Integer32 
    MAX-ACCESS  read-create
    STATUS  current
    DESCRIPTION
    "This parameter determines how much time to wait before switching,
     after jitter buffer underrun.
	 Switching occurs if no frame arrives within that time.
     For Ipmux time is counted in msec."
    ::= { sysCRdnEntry 18 }






--System Database operations

sysDbaseSanityCheckCmd OBJECT-TYPE
      SYNTAX  INTEGER
       {
       off(2),
       on (3)
       }
      MAX-ACCESS  read-write
      STATUS  current
      DESCRIPTION
      "Setting this attribute to on(3) will initiate the process 
       of Sanity check on the TmpCnfg. Upon completion, the value 
       will automatically change to off(2)."
      ::= { sysDbase 1 }

sysDbaseDownloadCnfgIdxCmd OBJECT-TYPE
      SYNTAX  Integer32   (1..255)
      MAX-ACCESS  read-write
      STATUS  current
      DESCRIPTION
      "This attribute specifies the Id of the target RealCnfg to 
       which the TmpCnfg should be transferred. Upon set command, 
       the DACS agent will initiate the Sanity-Check  process.  
       If successful, the actual transfer will be performed. 
       If there will be errors, the user will have to perform
       the command again after errors correction.       
       The operation is valid only on configuration numbers
       that do not exceed sysSMaxNoOfCnfg."
      ::= { sysDbase 2 }
-- In phase I of DXC and FCD only the value 1 (Cnfg1) is valid.

sysDbaseUploadCnfgIdxCmd OBJECT-TYPE
      SYNTAX  Integer32  (1..255)
      MAX-ACCESS  read-write
      STATUS  current
      DESCRIPTION
      "This attribute specifies the Id of the source Cnfg to be 
       loaded into the TmpCnfg. Upon set operation the actual 
       transfer will be initiated.
       The operation is valid only on configuration numbers
       that do not exceed sysSMaxNoOfCnfg."
      ::= { sysDbase 3 }
-- In phase I of DXC and FCD only the value 1 (Cnfg1) is valid.

sysDbaseFlipTable  OBJECT-TYPE
      SYNTAX SEQUENCE OF SysDbaseFlipEntry
      MAX-ACCESS not-accessible
      STATUS  current
      DESCRIPTION
      "Dbase Flip time and activation for every configuration."
       ::= { sysDbase 4 }

sysDbaseFlipEntry OBJECT-TYPE
      SYNTAX SysDbaseFlipEntry
      MAX-ACCESS not-accessible
      STATUS current
	DESCRIPTION  "An entry in table."
	INDEX {sysDbaseFlipIdx}
      ::= { sysDbaseFlipTable 1}

SysDbaseFlipEntry ::=
      SEQUENCE {
   sysDbaseFlipIdx        Integer32,
   sysDbaseFlipTime       DisplayString,
   sysDbaseFlipActivation INTEGER      }

sysDbaseFlipIdx OBJECT-TYPE
      SYNTAX Integer32 (1..255)
      MAX-ACCESS read-only
      STATUS current
      DESCRIPTION
      "This attribute indicates the Idx of the Cnfg being 
       the target Configuration."
      ::= { sysDbaseFlipEntry 1}

sysDbaseFlipTime OBJECT-TYPE
      SYNTAX DisplayString (SIZE(0..255))
      MAX-ACCESS read-write
      STATUS current
      DESCRIPTION
      "This attribute indicates the time (HH:MM) when this data 
       base will start being used by the Tmp config."
      ::= { sysDbaseFlipEntry 2}

sysDbaseFlipActivation OBJECT-TYPE
      SYNTAX INTEGER {
      disable (1),
      enable  (2)
   }
      MAX-ACCESS read-write
      STATUS current
      DESCRIPTION
      "This attribute indicates if the Dbase flip will be 
       activated at the time specified for this configuration 
       (enable) or not (disable). 
       No more than one flip should be enabled for the same time."
      ::= { sysDbaseFlipEntry 3}


--Module (card) level of DACS MIB

mdlGen   OBJECT IDENTIFIER ::= {mdlDacsMux 1}
mdlCl   OBJECT IDENTIFIER ::=  {mdlDacsMux 2}
mdlPs   OBJECT IDENTIFIER ::=  {mdlDacsMux 3}

--DACS module (card) general parameters (common to all cards 
--type)

--General Card - Status information table 
--This table is NOT-APPLICABLE for a stand-alone unit  

mdlSTable  OBJECT-TYPE
      SYNTAX SEQUENCE OF MdlSEntry
      MAX-ACCESS not-accessible
      STATUS current
	DESCRIPTION  "A table."
	::=  { mdlGen 1 }

mdlSEntry OBJECT-TYPE
      SYNTAX MdlSEntry
      MAX-ACCESS not-accessible
      STATUS current
	DESCRIPTION  "An entry in table."
	INDEX { mdlSSltIdx }
      ::= { mdlSTable 1}

MdlSEntry ::=
      SEQUENCE {
  mdlSSltIdx            INTEGER,
  mdlSCardType          INTEGER,
  mdlSHwVer             DisplayString (SIZE (0..255)),
  mdlSSwVer             DisplayString (SIZE (0..255)),
  mdlSAlarmStatus       INTEGER,
  mdlSAlarmStatusAll    INTEGER,
  mdlSTestStatus        INTEGER,
  mdlSHwStatus          INTEGER,
  mdlSActivity          INTEGER,
  mdlSAlrClearCmd       INTEGER,
  mdlSAlrClearAllCmd    INTEGER,
  mdlSAlrMaskAll        INTEGER,
  mdlSCmd               Integer32,
  mdlSReset             INTEGER,
  mdlSRebuildFrame      INTEGER



      }

mdlSSltIdx OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
    kmxPsA (101),
    kmxPsB (102),
    kmxMlA (103),
    kmxMlB (104),
    kmxCl  (105),
    kmxOpt (106),
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118)
       }
      MAX-ACCESS  read-only
      STATUS  current
      DESCRIPTION
      "A unique number to identify a slot position in the DACS.
       The Kilomux should use enumerated values starting with kmx."
      ::= { mdlSEntry 1}


mdlSCardType OBJECT-TYPE
      SYNTAX  INTEGER
       {
  --
  -- General types
  --
  unknown        (1),
  empty          (2),


  -- Power Supply Modules
  --
        psAC           (10),
        psDC           (11),
        
  --
  -- Cl Modules
  --
        dCl            (20),
        kCl            (21),
        dcl2           (22),
		dcl2Eth        (23),
		kClEth         (24),
        dcl3           (25),
		dcl3Eth        (26),

  --
  -- T1/E1 Modules
  --
        d4T1		   (28),
		d8T1		   (29),
        dT1DSU         (30),
        dT1CSU         (31),
        dE1DSU         (32),
        dE1LTU         (33),
        dE1aDSU        (34),
        dE1aLTU        (35),
        dT1F           (36),
        dE1F           (37),
        d4E1		   (38),
		d8E1		   (39),
  
  --
  -- xDSL Modules
  
        dE1Hdsl        (40),  --Double Slot
        dT1Hdsl        (41),  --Double Slot   
        dE1HdslS       (42),  --Single Slot
        dT1HdslS       (43),  --Single Slot
        d16gsdsl       (44),  --Single Slot, for DXC3000 only
        d8sl           (45),  --Single Slot   

        -- KMUX Main Links
  --
  kML1           (50),
  kML2           (51),
  kML3           (52),
  kML4           (53),
  kML5           (54),
  kML6           (55),
  kML7           (56),
  kML8           (57),
  kML10          (59),
  kMLF           (60),
  kML10New       (61),
  kML11RJ45      (62),
  kML11FO        (63),
        --LS  Modules
  --
  kLS1           (70),
  kLS1New        (71),
  kLS2           (72),

        --LAN  Modules
  --
  kTRE           (80),
  kMBE           (81),
  kMBENew        (82),
  fLAN           (83), 	-- FCD STM LAN card

        --Optional  Modules
  --
  kai           (90),
  kdi           (91),
  kdiCH         (92),

  -- HS Modules
  --
  dHS2           (100),
  d8U            (101),
  d16U           (102),

  kHS1           (110),
  kHS2           (111),
  kHSU1          (112),
  kHSU2          (113),
  kHS703         (114),

  -- Voice Modules
  --
  kVC1EM         (130),
  kVC1FXO        (131),
  kVC1FXS        (132),
  kVC1MEM        (133),
  kVC1MFXO       (134),
  kVC1MFXS       (135),
  kVC1MFXSW      (136),
  kVC2EM         (137),
  kVC2FXO        (138),
  kVC2FXS        (139),
  kVC2s1EM       (140), --KVC2/1/E&M
  kVC2s1FXO      (141), --KVC2/1/FXO
  kVC2s1FXS      (142), --KVC2/1/FXS
  kVC3EM         (143),
  kVC3FXO        (144),
  kVC3FXS        (145),
  kVC3S0         (146),

  -- Fax Modules
  --     
  kVF1EM            (170),
  kVF1FXO           (171),
  kVF1FXS           (172),
  kVF3EM            (173),
  kVF3FXO           (174),
  kVF3FXS           (175),
  kVF4EM            (176),
  kVF4FXO           (177),
  kVF4FXS           (178),
  kVF4FXSW          (179),
  kVF4S0            (180),
  kVF5PbxE1         (181),
  kVF5E1PbxSlave    (182),
  kVF5PbxT1         (183),
  kVF5T1PbxSlave    (184),
  kVF5PbxE1New      (185),
  kVF5E1PbxSlaveNew (186),
  kVF5PbxT1New      (187),
  kVF5T1PbxSlaveNew (188),
  kVF4FXO3          (189), 
  kVF4FXS3          (190), 
  kVF4NS0           (191),
  kVF6E1s16         (192), --KVF.6/E1/16
  kVF6E1s31         (193), --KVF.6/E1/31
  kVF6T1s12         (194), --KVF.6/T1/12
  kVF6T1s24         (195), --KVF.6/T1/24
  kVF8EM            (196),
  kVF8FXO           (197),
  kVF8FXS           (198),


  -- DIM Modules
  --
  dimV35         (201),
  dimRS422       (202),
  dimRS530       (203),
  dimHssi        (204),
  dimX21         (205),
  dim10BaseT     (206),
  dimE1          (207),
  dim100         (208), 

  --DACS T3/E3 Modules
  --
  dt3G747        (209),
  dt3            (210),
  dt3f           (211),
  de3            (212),
  de3f           (213),

  -- STM-1 Modules
  --
  dstm1s1        (214),	 --DSTM1/1 Fractional
  dstm1s2        (215),  --DSTM1/2 Fractional + Redundancy
  fSTM1          (216),  -- FCD STM STM1 card
  dstm1          (217),  --DSTM1 Full
  dstm1R         (218),  --DSTM1 Full + Redundancy
  f2stm1		 (219),   -- FCD STM 2 STM1 ports card 
  
  -- LA Modules 
  --
  laSUB          (230),	 -- La-240
  laVEM          (231),	 -- LA-140 & La-240
  laVFXO         (232),	 -- LA-140 & La-240
  laVFXS         (233),	 -- LA-140 & La-240
  laV11          (234),	 -- LA-140 & La-240
  laV24          (235),	 -- LA-140 & La-240
  laV35          (236),	 -- LA-140 & La-240
  laT1           (237),	 -- LA-140
  laT1Vxx        (238),	 -- LA-140
  laE1           (239),	 -- LA-140
  laE1Vxx        (240),	 -- LA-140
  laISDN         (241),  -- LA-140 & La-240i
  laVxx          (242),  -- LA-140 
  laEth          (243),  -- LA-140
  laISDNwBU      (244),  --	LA-140  with backup  (lifeline bottom connector)	  
  laIsdnNT		 (245),  -- LA-140 ISDN NT
  laIsdnNTwBU	 (246),  -- LA-140 ISDN NT with backup (lifeline bottom connector)
  laIsdnTE		 (247),  --	LA-140 ISDN TE
  laFXSwBU		 (248),  -- LA-140 FXS with backup (lifeline bottom connector) 
  laFXSs		 (249),  -- LA-140 bottom row FXS 
  laFXSwBUs		 (250),  -- LA-140 bottom row FXS with backup (lifeline Top port) 
  laIsdnNTs		 (251),  -- LA-140 bottom row ISDN NT
  laIsdnNTwBUs	 (252),  -- LA-140 bottom row ISDN NT with backup (lifeline Top port)
  laIsdnTEs		 (253),  --	LA-140 bottom row ISDN TE
  laDp           (254),  -- LA-140 bottom single data port X21/V35/RS50 
  laSdsl         (255),	 -- LA-140 top SDSL port 
  laSdslDp		 (256),	 -- LA-140 top SDSL port with bottom X21 or V35 Data Port 
  laAdslA		 (257),  -- LA-140 bottom ADSLA port
  laAdslADp  	 (258),  -- LA-140 bottom ADSLA port with top X21 or V35 Data Port 
  laAdslB		 (259),	 -- LA-140 bottom ADSLB port
  laAdslBDp	     (260),	 -- LA-140 bottom ADSLB port with top X21 or V35 Data Port 
  laShdsl		 (261),	 -- LA-140 bottom SHDSL port
  laShdslDp 	 (262),	 -- LA-140 bottom SHDSL port with top X21 or V35 Data Port
  laT1b   		 (263),  -- LA-140 bottom T1 port
  laT1bDp        (264),  -- LA-140 bottom T1 port with top data port  
  laIsdnTEwBU    (265),  --	LA-140 ISDN TE with backup 
  laIsdnTEwBUs	 (266)   --	LA-140 bottom row ISDN TE with backup 





        }
      MAX-ACCESS  read-only
      STATUS  current
      DESCRIPTION
      "This attribute indicates the type of  the card installed
       in the specific slot position.
       Only PS's are possible in the PS slots.
       Only CL's are possible in the CL slots.
       Only IO modules are possible in the IO slots.
       Kmux card type start with the letter k.
       LA card type start with the letters la."
      ::= { mdlSEntry 2}

mdlSHwVer OBJECT-TYPE
      SYNTAX  DisplayString (SIZE (0..255))
      MAX-ACCESS  read-only
      STATUS  current
      DESCRIPTION
      "This attribute indicates the Hardware version of the 
       card installed in the specific slot position."
      ::= { mdlSEntry 3 }

mdlSSwVer OBJECT-TYPE
      SYNTAX  DisplayString (SIZE (0..255))
      MAX-ACCESS  read-only
      STATUS  current
      DESCRIPTION
      "This attribute indicates the Software version of the 
       card installed in the specific slot position."
      ::= {mdlSEntry 4}


mdlSAlarmStatus OBJECT-TYPE
      SYNTAX  INTEGER
       {
  off      (2),
  major    (3),
  minor    (4),
  event    (5),
  warning  (6),
  critical (7)
       }
      MAX-ACCESS  read-only
      STATUS  current
      DESCRIPTION
      "Indicates the current alarm state only for card level.
       This object will be set to: 
       - critical(7): when there is at least one active (ON) critical 
                    alarm .
       - major (3): when there is no active critical alarm, but there is
                    at least one active (ON) major alarm .
       - minor (4): when there is no active major or critical alarm, but 
                    there is at least one active minor alarm.
       - warning (6): when there is no active major, critical or minor alarm, but 
                    there is at least one active warning alarm.
       - event (5): when there is no active alarm of another type, but 
                    there is at least one active event alarm.
       - off(2): when there is no active (ON) alarm (since last clear operation)."
      ::= { mdlSEntry 5 }

mdlSAlarmStatusAll OBJECT-TYPE
      SYNTAX  INTEGER
       {
  off      (2),
  major    (3),
  minor    (4),
  event    (5),
  warning  (6),
  critical (7)
       }
      MAX-ACCESS  read-only
      STATUS  current
      DESCRIPTION
      "Indicates the current card alarm state including the 
       lower level:  card, port.
       This object will be set to: 
       - critical(7): when there is at least one active (ON) critical 
                    alarm .
       - major (3): when there is no active critical alarm, but there is
                    at least one active (ON) major alarm .
       - minor (4): when there is no active major or critical alarm, but 
                    there is at least one active minor alarm.
       - warning (6): when there is no active major, critical or minor alarm, but 
                    there is at least one active warning alarm.
       - event (5): when there is no active alarm of another type, but 
                    there is at least one active event alarm.
       - off(2): when there is no active (ON) alarm (since last clear operation)."
      ::= { mdlSEntry 6 }

mdlSTestStatus OBJECT-TYPE
      SYNTAX  INTEGER
       {
  off(2),
  on (3)
       }
      MAX-ACCESS  read-only
      STATUS  current
      DESCRIPTION
      "This attribute will be on(3) when there is at least 
       one test running on a port of the module; otherwise the value 
       will be off(2)."
      ::= { mdlSEntry 7 }

mdlSHwStatus OBJECT-TYPE
      SYNTAX  INTEGER
       {
  fail(2),
  ok  (3)
       }
      MAX-ACCESS  read-only
      STATUS  current
      DESCRIPTION
      "This attribute will be fail(2) when a HW FAIL exists
       on this module (discovered by periodic self test); 
       otherwise the value will be ok(3)."
      ::= { mdlSEntry 8 }

mdlSActivity OBJECT-TYPE
      SYNTAX  INTEGER
       {
  notApplicable (1),
  offline       (2),
  online        (3)
       }
      MAX-ACCESS  read-only
      STATUS  current
      DESCRIPTION
      "notApplicable - when the slot is empty (no module)
       offline(1) - when the module is not active (redundant) 
       online (2) - when the module is active ."
      ::= { mdlSEntry 9 }

mdlSAlrClearCmd  OBJECT-TYPE
      SYNTAX  INTEGER
       {
  off(2),
  on (3)
       }
      MAX-ACCESS  read-write
      STATUS  current
      DESCRIPTION
      "Setting this attribute to ON, will enforce a  clear 
       operation on the card level alarms . Upon completion, 
       the value will automatically change to off(2)."
      ::= { mdlSEntry 10 }


mdlSAlrClearAllCmd  OBJECT-TYPE
      SYNTAX  INTEGER
       {
  off(2),
  on (3)
       }
      MAX-ACCESS  read-write
      STATUS  current
      DESCRIPTION
      "Setting this attribute to ON, will enforce a  clear 
       operation on card and port level alarms . Upon completion, 
       the value will automatically change to off(2)."
      ::= { mdlSEntry 11 }

mdlSAlrMaskAll  OBJECT-TYPE
      SYNTAX  INTEGER
       {
  off(2),
  on (3)
       }
      MAX-ACCESS  read-write
      STATUS  current
      DESCRIPTION
      "on(3)  - will cause masking of all the card level alarms.
                These alarms will not be sent to NMS and will not 
                be taken into account for Alarms Status.
       off(2) - will unmask all card level alarms except those 
                masked via the mdlAlrMaskTable. "
      ::= { mdlSEntry 12 }

mdlSCmd  OBJECT-TYPE
      SYNTAX  Integer32
      MAX-ACCESS  read-write
      STATUS  current
      DESCRIPTION
      "General object for any special command at card level.
       0=NotApplicable, for cards that don't support this object.

       For KML.10(ISDN) card of KM-2100,  the object will indicate 
       Manual Call Command in Switch mode. It is applicable only when
       for KML.10, prtIsdnSwitchMode=manual.
       KML.10 valid values:
       '1' =  noOp, will be used by agents that do not support this 
              feature or object (old KM agents)
       '2' = off, Set call command mode to disconnect state. Disconnects the call.
       '3' = on,  Set call command mode to connect state. Connects the call.
       
       For DXC IO cards, the object will be used for IO Card Reset HW command:
       '2' = off, this will be always the Get value for these cards.
       '3' = on,  this is the Set command used to Reset the IO card. Upon 
             completing the operation, the value will automatically change to off(2),
             by Agent.
       For Slots that are NOT IO Slots and for empty IO Slots, the Get value will
       be always '0' (NotApplicable). "
      ::= { mdlSEntry 13 } 
      

mdlSReset  OBJECT-TYPE
      SYNTAX  INTEGER {
	                   off (2),
					   on  (3)   --HW
					  }
      MAX-ACCESS  read-write
      STATUS  current
      DESCRIPTION
            	"Reset action to be performed on the module."
      ::= { mdlSEntry 14 } 

mdlSRebuildFrame OBJECT-TYPE
      SYNTAX  INTEGER {notApplicable(1),
                       off          (2),
                       on           (3)
                              } 
      MAX-ACCESS  read-write
      STATUS  current
      DESCRIPTION
      "Applicable only for KiloMux Main Link cards only.
	   '2' = off, this will be always the Get value.
       '3' = on,  this is the Set command used to Rebuild the Frame. 
       Upon completing the operation, the value will automatically change 
       to off(2), by Agent."
      ::= { mdlSEntry 15}



--General Card - Configuration table 
--This table is NOT-APPLICABLE for a stand-alone unit  

mdlCTable  OBJECT-TYPE
      SYNTAX SEQUENCE OF MdlCEntry
      MAX-ACCESS not-accessible
      STATUS current
	DESCRIPTION  "A table."
	::=  { mdlGen 2 }

mdlCEntry OBJECT-TYPE
      SYNTAX MdlCEntry
      MAX-ACCESS not-accessible
      STATUS current
	DESCRIPTION  "An entry in table."
	INDEX { mdlCConfigIdx, mdlCSlotIdx  }
      ::= { mdlCTable 1}

MdlCEntry ::=
      SEQUENCE {
   mdlCConfigIdx         Integer32,
   mdlCSlotIdx           INTEGER,
   mdlCProgCardType      INTEGER,
   mdlCNoOfExtPrt        Integer32,   -- RO
   mdlCNoOfIntPrt        Integer32,    -- RO
   mdlCParam             Integer32 
	}

mdlCConfigIdx OBJECT-TYPE
      SYNTAX  Integer32 (1..255)
      MAX-ACCESS  read-only
      STATUS  current
      DESCRIPTION
      "This object indicates the Configuration number (1..255) 
       referred.
       Value of  255 specifies the TmpCnfg (Scratch)."
      ::= { mdlCEntry 1}
-- In phase 1 only the values 1 (Cnfg1) and 255 (temp) are valid.

mdlCSlotIdx OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
    kmxPsA (101),
    kmxPsB (102),
    kmxMlA (103),
    kmxMlB (104),
    kmxCl  (105),
    kmxOpt (106),
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118)
       }
      MAX-ACCESS  read-only
      STATUS  current
      DESCRIPTION
      "This object indicates a unique number of the slot position 
       in which the module is inserted.
       The Kilomux should use enumerated values starting with kmx."
      ::= { mdlCEntry 2}

mdlCProgCardType OBJECT-TYPE
      SYNTAX  INTEGER
       {
  --
  -- General types
  --
  unknown        (1),
  empty          (2),


  -- Power Supply Modules
  --
  psAC           (10),
  psDC           (11),
        
  --
  -- Cl Modules
  --
        dCl            (20),
        kCl            (21),
        dcl2           (22),
		dcl2Eth        (23),
		kClEth         (24),
        dcl3           (25),
		dcl3Eth        (26),

  --
  -- T1/E1 Modules
  --
        d4T1		   (28),
		d8T1		   (29),
        dT1DSU         (30),
        dT1CSU         (31),
        dE1DSU         (32),
        dE1LTU         (33),
        dE1aDSU        (34),
        dE1aLTU        (35),
        dT1F           (36),
        dE1F           (37),
        d4E1		   (38),
		d8E1		   (39),

  --
  -- xDSL Modules
  
        dE1Hdsl        (40),  --Double Slot
        dT1Hdsl        (41),  --Double Slot   
        dE1HdslS       (42),  --Single Slot
        dT1HdslS       (43),  --Single Slot   
        d16gsdsl       (44),  --Single Slot, for DXC3000 only   
        d8sl           (45),  --Single Slot   

        -- KMUX Main Links
  --
  kML1           (50),
  kML2           (51),
  kML3           (52),
  kML4           (53),
  kML5           (54),
  kML6           (55),
  kML7           (56),
  kML8           (57),
  kML10          (59),
  kMLF           (60),
  kML10New       (61),
  kML11RJ45      (62),
  kML11FO        (63),

        --LS  Modules
  --
  kLS1           (70),
  kLS1New        (71),
  kLS2           (72),

        --LAN  Modules
  --
  kTRE           (80),
  kMBE           (81),
  kMBENew        (82),
  fLAN           (83), -- FCD STM LAN moudle

        --Optional  Modules
  --
  kai           (90),
  kdi           (91),
  kdiCH         (92),

  -- HS Modules
  --
  dHS2           (100),
  d8U            (101),
  d16U           (102),

  kHS1           (110),
  kHS2           (111),
  kHSU1          (112),
  kHSU2          (113),
  kHS703         (114),


  -- Voice Modules
  --
  kVC1EM         (130),
  kVC1FXO        (131),
  kVC1FXS        (132),
  kVC1MEM        (133),
  kVC1MFXO       (134),
  kVC1MFXS       (135),
  kVC1MFXSW      (136),
  kVC2EM         (137),
  kVC2FXO        (138),
  kVC2FXS        (139),
  kVC2s1EM       (140), --KVC2/1/E&M
  kVC2s1FXO      (141), --KVC2/1/FXO
  kVC2s1FXS      (142), --KVC2/1/FXS
  kVC3EM         (143),
  kVC3FXO        (144),
  kVC3FXS        (145),
  kVC3S0         (146),

  -- Fax Modules
  --
  kVF1EM            (170),
  kVF1FXO           (171),
  kVF1FXS           (172),
  kVF3EM            (173),
  kVF3FXO           (174),
  kVF3FXS           (175),
  kVF4EM            (176),
  kVF4FXO           (177),
  kVF4FXS           (178),
  kVF4FXSW          (179),
  kVF4S0            (180),
  kVF5PbxE1         (181),
  kVF5E1PbxSlave    (182),
  kVF5PbxT1         (183),
  kVF5T1PbxSlave    (184),
  kVF5PbxE1New      (185),
  kVF5E1PbxSlaveNew (186),
  kVF5PbxT1New      (187),
  kVF5T1PbxSlaveNew (188),
  kVF4FXO3          (189), 
  kVF4FXS3          (190), 
  kVF4NS0           (191), 
  kVF6E1s16         (192), --KVF.6/E1/16
  kVF6E1s31         (193), --KVF.6/E1/31
  kVF6T1s12         (194), --KVF.6/T1/12
  kVF6T1s24         (195), --KVF.6/T1/24
  kVF8EM            (196),
  kVF8FXO           (197),
  kVF8FXS           (198),


  -- DIM Modules
  --
  dimV35         (201),
  dimRS422       (202),
  dimRS530       (203),
  dimHssi        (204),
  dimX21         (205),
  dim10BaseT     (206),
  dimE1          (207),
  dim100         (208), 

  --DACS T3/E3 Modules
  --
  dt3G747        (209),
  dt3            (210),
  dt3f           (211),
  de3            (212),
  de3f           (213),

  -- STM-1 Modules
  --
  dstm1s1        (214),	 --DSTM1/1 Fractional
  dstm1s2        (215),  --DSTM1/2 Fractional + Redundancy
  fstm1          (216),	 --FCD STM STM1 card
  dstm1          (217),  --DSTM1 Full
  dstm1R         (218),   --DSTM1 Full + Redundancy
  f2stm1		 (219)   -- FCD STM 2 STM1 ports card 

  -- The following numbers are used in mdlSCardType, for LA modules:
  --
  -- laSUB          (230)
  -- laVEM          (231)
  -- laVFXO         (232)
  -- laVFXS         (233)
  -- laV11          (234)
  -- laV24          (235)
  -- laV35          (236)
  -- laT1           (237),	
  -- laT1Vxx        (238),	
  -- laE1           (239),	
  -- laE1Vxx        (240),	
  -- laISDN         (241),  
  -- laVxx          (242),   
  -- laEth          (243),
  -- laISDNwBU      (244),
  -- laIsdnNT		(245), LA-140 ISDN NT
  -- laIsdnNTwBU	(246), LA-140 ISDN NT with backup (lifeline bottom connector)
  -- laIsdnTE		(247), LA-140 ISDN TE
  -- laFXSwBU		(248), LA-140 FXS with backup (lifeline bottom connector) 
  -- laFXSs		    (249), LA-140 bottom row FXS 
  -- laFXSwBUs	    (250), LA-140 bottom row FXS with backup (lifeline Top port) 
  -- laIsdnNTs	    (251), LA-140 bottom row ISDN NT
  -- laIsdnNTwBUs	(252), LA-140 bottom row ISDN NT with backup (lifeline Top port)
  -- laIsdnTEs	    (253), LA-140 bottom row ISDN TE
  -- laDp           (254), LA-140 bottom single data port X21/V35/RS50 
  -- laSdsl         (255), LA-140 top SDSL port 
  -- laSdslDp	    (256), LA-140 top SDSL port with bottom X21 or V35 Data Port 
  -- laAdslA	    (257), LA-140 bottom ADSLA port
  -- laAdslADp      (258), LA-140 bottom ADSLA port with top X21 or V35 Data Port 
  -- laAdslB	    (259), LA-140 bottom ADSLB port
  -- laAdslBDp	    (260), LA-140 bottom ADSLB port with top X21 or V35 Data Port 
  -- laShdsl	    (261), LA-140 bottom SHDSL port
  -- laShdslDp	    (262), LA-140 bottom SHDSL port with top X21 or V35 Data Port 
  -- laT1b   	    (263), LA-140 bottom T1 port
  -- laT1bDp        (264),  LA-140 bottom T1 port with top data port  
  -- laIsdnTEwBU    (265),  LA-140 ISDN TE with backup 
  -- laIsdnTEwBUs   (266)  LA-140 bottom row ISDN TE with backup 
 	 
       
       }
      MAX-ACCESS  read-write
      STATUS  current
      DESCRIPTION
      "This object indicates the card type assigned to the specific 
       slot in the common configuration.
       This object is identical for all the configurations (1..255).
       Only the TmpCnf(255) might have a  different value.
       The write operation is valid only for the TmpCnfg entry."
      ::= { mdlCEntry 3}

mdlCNoOfExtPrt OBJECT-TYPE
      SYNTAX  Integer32
      MAX-ACCESS  read-only
      STATUS  current
      DESCRIPTION
      "Number of external ports in the programmed module of 
       the specific slot position"
      ::= { mdlCEntry 4}

mdlCNoOfIntPrt OBJECT-TYPE
      SYNTAX  Integer32
      MAX-ACCESS  read-only
      STATUS  current
      DESCRIPTION
      "Number of internal ports in the programmed module of 
       the specific slot position."
      ::= { mdlCEntry 5}

mdlCParam  OBJECT-TYPE
      SYNTAX  Integer32
      MAX-ACCESS  read-write
      STATUS  current
      DESCRIPTION
      "General configuration object at card level (per configuration).
       NotApplicable=0, for cards that don't support this object.

       For D8U and D16U cards of DXC,  the object will indicate 
       the port on which BERT will be performed. The port can be
       one of the external ports, any of its associated B1, B2, D ports
       or no port of the card (None=0).
       For port indexes see DXC R6 spec."
      ::= {mdlCEntry 6 } 


--Module level current alarms

mdlAlr OBJECT IDENTIFIER ::= {mdlGen 3}

mdlAlrTable OBJECT-TYPE
      SYNTAX SEQUENCE OF MdlAlrEntry
      MAX-ACCESS not-accessible
      STATUS current
      DESCRIPTION
      "The list of card alarms. "
      ::= { mdlAlr 1 }

mdlAlrEntry OBJECT-TYPE
      SYNTAX MdlAlrEntry
      MAX-ACCESS not-accessible
      STATUS current
	DESCRIPTION  "An entry in table."
	INDEX {mdlAlrSltIdx , mdlAlrIdx}
      ::= { mdlAlrTable 1}

MdlAlrEntry ::=
      SEQUENCE {
  mdlAlrSltIdx           INTEGER,
  mdlAlrIdx              Integer32,
  mdlAlrCode             Integer32,
  mdlAlrState            INTEGER,  --severity
  mdlAlarmMask           INTEGER,
  mdlAlarmInvert         INTEGER,
  mdlAlarmOnOff          INTEGER,
  mdlAlarmCounter        Integer32 
	}

mdlAlrIdx OBJECT-TYPE
      SYNTAX  Integer32
      MAX-ACCESS  read-only
      STATUS  current
      DESCRIPTION
      "A unique number to identify an entry in the alarm status 
       table.
       Users should use the get next function to read this table 
       because the indexes are not consecutive"
      ::= { mdlAlrEntry 1}

mdlAlrSltIdx OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
    kmxPsA (101),
    kmxPsB (102),
    kmxMlA (103),
    kmxMlB (104),
    kmxCl  (105),
    kmxOpt (106),
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118)
       }
      MAX-ACCESS  read-only
      STATUS  current
      DESCRIPTION
      "This attribute indicates the  desired slot position. 
       The Kilomux should use enumerated values starting with kmx."
      ::= { mdlAlrEntry 2}

mdlAlrCode OBJECT-TYPE
      SYNTAX  Integer32
      MAX-ACCESS  read-only
      STATUS  current
      DESCRIPTION
      "This object indicates a code related to a specific
       alarm description. The list of codes and their related
       descriptions will be sent to NMS request (for display purpose)
       by alrGenTable."
      ::= { mdlAlrEntry 3 }

mdlAlrState OBJECT-TYPE
      SYNTAX  INTEGER {
   event    (3),
   minor    (4),
   major    (5),
   warning  (6),
   critical (7)
       }
      MAX-ACCESS  read-only
      STATUS  current
      DESCRIPTION
      "This object indicates the card alarm severity."      
      ::= { mdlAlrEntry 4 }

mdlAlarmMask OBJECT-TYPE
      SYNTAX  INTEGER {
  off(2),
  on (3)
       }
      MAX-ACCESS  read-only
      STATUS  current
      DESCRIPTION
      "Alarm Mask is : on/off."
      ::= { mdlAlrEntry 5 }

mdlAlarmInvert OBJECT-TYPE
      SYNTAX  INTEGER {
  off(2),
  on (3)
       }
      MAX-ACCESS  read-only
      STATUS  current
      DESCRIPTION
      "Alarm Invert is : on/off."
      ::= { mdlAlrEntry 6 }

mdlAlarmOnOff OBJECT-TYPE
      SYNTAX  INTEGER {
  off(2),
  on (3)
       }
      MAX-ACCESS  read-only
      STATUS  current
      DESCRIPTION
      "Alarm state is : on/off."
      ::= { mdlAlrEntry 7}

mdlAlarmCounter OBJECT-TYPE
      SYNTAX  Integer32
      MAX-ACCESS  read-only
      STATUS  current
      DESCRIPTION
      "A counter - how many times the alarm occured (ON) since last
       clear operation or since last Reset."
      ::= { mdlAlrEntry 8 }

mdlAlrMaskTable OBJECT-TYPE
      SYNTAX SEQUENCE OF MdlAlrMaskEntry
      MAX-ACCESS not-accessible
      STATUS current
      DESCRIPTION
      "The list of card masked alarms. "
      ::= { mdlAlr 2 }

mdlAlrMaskEntry OBJECT-TYPE
      SYNTAX MdlAlrMaskEntry
      MAX-ACCESS not-accessible
      STATUS current
	DESCRIPTION  "An entry in table."
	INDEX {mdlAlrMaskSltIdx}
      ::= { mdlAlrMaskTable 1}

MdlAlrMaskEntry ::=
      SEQUENCE {
     mdlAlrMaskSltIdx           INTEGER,
     mdlAlrMask            OCTET STRING    
      }

mdlAlrMaskSltIdx OBJECT-TYPE
      SYNTAX  INTEGER
       {
       psA   (1),
       psB   (2),
       clA   (3),
       clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
    kmxPsA (101),
    kmxPsB (102),
    kmxMlA (103),
    kmxMlB (104),
    kmxCl  (105),
    kmxOpt (106),
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118)
       }
      MAX-ACCESS  read-only
      STATUS  current
      DESCRIPTION
      "This attribute indicates the  desired slot position.
       The Kilomux should use enumerated values starting with kmx."
      ::= { mdlAlrMaskEntry 1}

mdlAlrMask OBJECT-TYPE
      SYNTAX OCTET STRING  (SIZE (8..10))
      MAX-ACCESS read-write
      STATUS current
   DESCRIPTION
   "This object is a mask that indicates which card level 
    alarms are masked. The masked alarms (their bit is set to 
    '1') are neither sent to the manager, nor taken into account
    for alarm status and LEDs.
    Bit no. = Alarm code
    The bits that do not belong to the card level will be 0.
    This object is applicable only when mdlSAlrMaskAll=off 
    (otherwise all card alarms are masked).
    Example: When Alarm having the code 8 is masked,
             the value of this object will be 100 (hex)."
     ::= { mdlAlrMaskEntry 2 } 


--DACS dcl (Common Logic) card specific parameters  

mdlClTable  OBJECT-TYPE
      SYNTAX SEQUENCE OF MdlClEntry
      MAX-ACCESS not-accessible
      STATUS current
	DESCRIPTION  "A table."
	::=  { mdlCl 1 }

mdlClEntry OBJECT-TYPE
      SYNTAX MdlClEntry
      MAX-ACCESS not-accessible
      STATUS current
	DESCRIPTION  "An entry in table."
	INDEX { mdlClIdx }
      ::= { mdlClTable 1}

MdlClEntry ::=
      SEQUENCE {
   mdlClIdx           INTEGER,
   mdlClSwchStatus    Integer32,
   mdlClLastFlipDate  DisplayString,
   mdlClLastFlipTime  DisplayString,
   mdlClLastFlipCause DisplayString
     }

mdlClIdx OBJECT-TYPE
      SYNTAX  INTEGER {
   clA   (3),
   clB   (4)
   }
      MAX-ACCESS  read-only
      STATUS  current
      DESCRIPTION
      "This object indicates the Cl slot referred."
      ::= { mdlClEntry 1}

mdlClSwchStatus OBJECT-TYPE
      SYNTAX  Integer32
      MAX-ACCESS  read-only
      STATUS  current
      DESCRIPTION
      "This object indicates the status of the switches on 
       the referred DCL card.
       Each switch is represented by a bit. The status is a sum
       of 2**n, according to the bits. There are 4 switches:
       bit 0  SP-PAR (LSB)  '1' - Default parameters    
       bit 1  PSWRD         '1' - Password=default
                         '0' - Password=user selected
       bit 2  DB-INIT       '1' - DB initiated with default
                         '0' - DB initiated with NVRAM contents 
       bit 3  PC-SP  (MSB)  '1' - Management by terminal only
                         '0' - Management by NMS
       Example: If SP-PAR  and PSWRD bits are set ('1'), the value
                will be 3 (2**1 + 2**0).
       When the status of the switches is unknown, the value of
       this object will be 255."
      ::= { mdlClEntry 2}

mdlClLastFlipDate  OBJECT-TYPE
      SYNTAX  DisplayString (SIZE (0..255))
      MAX-ACCESS  read-only
      STATUS  current
      DESCRIPTION
      "Date when last flip occured.
       The format would be as specified by the sysSDateFormat."
   ::= {mdlClEntry 3}

mdlClLastFlipTime  OBJECT-TYPE
      SYNTAX  DisplayString (SIZE (0..255))
      MAX-ACCESS  read-only
      STATUS  current
      DESCRIPTION
      "Time when last flip occured."
   ::= {mdlClEntry 4}

mdlClLastFlipCause  OBJECT-TYPE
      SYNTAX  DisplayString (SIZE (0..255))
      MAX-ACCESS  read-only
      STATUS  current
      DESCRIPTION
      "The cause of last flip."
   ::= {mdlClEntry 5}



--DACS Ps (Power Supply) card specific parameters  

mdlPsTable  OBJECT-TYPE
      SYNTAX SEQUENCE OF MdlPsEntry
      MAX-ACCESS not-accessible
      STATUS current
	DESCRIPTION  "A table."
	::=  { mdlPs 1 }

mdlPsEntry OBJECT-TYPE
      SYNTAX MdlPsEntry
      MAX-ACCESS not-accessible
      STATUS current
	DESCRIPTION  "An entry in table."
	INDEX { mdlPsIdx }
      ::= { mdlPsTable 1}

MdlPsEntry ::=
      SEQUENCE {
   mdlPsIdx          INTEGER,
   mdlPsStatus       INTEGER,
   mdlPsTestResult   INTEGER
     }

mdlPsIdx OBJECT-TYPE
      SYNTAX  INTEGER {
   psA   (1),
   psB   (2)
   }
      MAX-ACCESS  read-only
      STATUS  current
      DESCRIPTION
      "This object indicates the PS card referred."
      ::= { mdlPsEntry 1}

mdlPsStatus OBJECT-TYPE
      SYNTAX  INTEGER {
   notActive  (1),
   active     (2)
   }
      MAX-ACCESS  read-only
      STATUS  current
      DESCRIPTION
      "This object indicates the status of the PS card."
      ::= { mdlPsEntry 2}

mdlPsTestResult OBJECT-TYPE
      SYNTAX  INTEGER {
   ok   (1),
   f12V (2),
   f5V  (3)
   }
      MAX-ACCESS  read-only
      STATUS  current
      DESCRIPTION
      "This object indicates the result of the PS card test.
       ok   (1) - the test passed successfully.
       f12V (2) - 12V FAIL was detected
       f5V  (3) -  5V FAIL was detected."
      ::= { mdlPsEntry 3}



--Port level of DACS MIB

prtGen    OBJECT IDENTIFIER ::= {prtDacsMux 1}
prtT1E1   OBJECT IDENTIFIER ::= {prtDacsMux 2}
prtHS     OBJECT IDENTIFIER ::= {prtDacsMux 3}
prtSP     OBJECT IDENTIFIER ::= {prtDacsMux 4}
prtDim    OBJECT IDENTIFIER ::= {prtDacsMux 5}
prtI      OBJECT IDENTIFIER ::= {prtDacsMux 6} --ISDN port
prtHdsl   OBJECT IDENTIFIER ::= {prtDacsMux 7} --HDSL Line
prtT3E3   OBJECT IDENTIFIER ::= {prtDacsMux 8} --T3/E3 interface

--DACS port general parameters (common to all ports type except SP)
--The table contains both status and configuration information 

prtGenParamTable  OBJECT-TYPE
      SYNTAX SEQUENCE OF PrtGenEntry
      MAX-ACCESS not-accessible
      STATUS current
	DESCRIPTION  "A table."
	::=  { prtGen 1 }

prtGenEntry OBJECT-TYPE
      SYNTAX PrtGenEntry
      MAX-ACCESS not-accessible
      STATUS current
	DESCRIPTION  "An entry in table."
	INDEX { prtGenPrtIdx }
      ::= { prtGenParamTable 1}

PrtGenEntry ::=
     SEQUENCE {
  prtGenPrtIdx        Integer32,
  prtGenSlt           INTEGER,
  prtGenExtInt        INTEGER,
  prtGenIfIndex       Integer32,
  prtGenActiveStatus  INTEGER,
  prtGenAlrStatus     INTEGER,
  prtGenTestStatus    INTEGER,
  prtGenTestMask      Integer32,
  prtGenTestCmd       Integer32,
  prtGenTestRunning   Integer32,
  prtGenType          INTEGER,
  prtGenInterfaceType DisplayString (SIZE (0..255)),
  prtGenAlrClearCmd   INTEGER,
  prtGenAlrMaskAll    INTEGER,
  prtGenParamStatus   OCTET STRING,
  prtGenRdnStatus     INTEGER,
  prtGenTestMaskXP    OCTET STRING,
  prtGenTestCmdXP     OCTET STRING,
  prtGenTestRunningXP OCTET STRING

  }

 prtGenPrtIdx OBJECT-TYPE
      SYNTAX  Integer32
      MAX-ACCESS  read-only
      STATUS  current
      DESCRIPTION
      "This attribute indicates a unique number to identify a port. 
       The valid port number depends on the IO slot no.,  the 
       installed card type and the port type: outside/external, inside/internal. 

    In the Kilomux, the port index is calculated as follows:
    100*Slot+Ch. The external Ch numbers are 1..10, and the
    internal Ch numbers are 11..20.
       
    In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 ."
      ::= { prtGenEntry 1}

prtGenSlt     OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       io13 (17),
       io14 (18),
       io15 (19),
    kmxMlA (103),
    kmxMlB (104),
    kmxCl  (105),
    kmxOpt (106),
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118),
    standAlone (255)
       }
      MAX-ACCESS  read-only
      STATUS  current
      DESCRIPTION
      "This attribute indicates a unique number to identify the slot where
       the card is inserted in.
       When the unit is stand-alone, this object is not applicable
       and 255 will be used.
       The Kilomux should use the enumerated starting with kmx."
      ::= { prtGenEntry 2}

prtGenExtInt  OBJECT-TYPE
      SYNTAX  INTEGER
       {
  external (2),
  internal (3)
       }
      MAX-ACCESS  read-only
      STATUS  current
      DESCRIPTION
      "This attribute describes the type of the designated port. 
       Exteral  port is a port with  a physical connector. Internal 
       port might be of two types, one is a composite port which 
       collects data of a few external ports into a common 
       bandwidth (usually routed trough DS1 link); the other type is
       internal ports which get only part of external port data 
       (usually a few DS0's).
       In the Kilomux-2100, the internal(3) value is used for 
       composite channels or sub-channels of an ISDN Ch."
      ::= { prtGenEntry 3}

prtGenIfIndex  OBJECT-TYPE
      SYNTAX  Integer32
      MAX-ACCESS  read-only
      STATUS  current
      DESCRIPTION
      "This attribute indicates the  unique  interface number 
       assigned to the port. The specific interface of this 
       attribute is the same as the interface identified by the  
       value of ifindex in MIB-II.If there is no interface for the 
       specific prtIdx, the value will be '7fffffff'h."
      ::= { prtGenEntry 4}

prtGenActiveStatus   OBJECT-TYPE
      SYNTAX  INTEGER
       {
         unknown           (1),
         notUsed           (2),
         offLine           (3),
         onLine            (4),
         offLineRedundancy (5),
         onLineRedundancy  (6)
       }
      MAX-ACCESS  read-only
      STATUS  current
      DESCRIPTION
      "This attribute describes the activity status of the port.
       unknown(1) indicates that the information is not supported.
       notUsed(2) indicates that the port is not connected according
                  to the active config.
       offLine(3) indicates that the port is down (not working) 
                  due to any problem.
       onLine (4) indicates that the port is up (working)
       offLineRedundancy(5) indicates that the port is down because
                            it is a redundant port.
       onLineRedundancy (6) indicates that this is a redundant port 
                            which is up and works as the active link."
      ::= { prtGenEntry 5}

prtGenAlrStatus OBJECT-TYPE
      SYNTAX  INTEGER
       {
  off      (2),
  major    (3),
  minor    (4),
  event    (5),
  warning  (6),
  critical (7)
       }
      MAX-ACCESS  read-only
      STATUS  current
      DESCRIPTION
      "Indicates the alarm state at port (ch) agent level.
       This object will be: 
       - critical(7): when there is at least one active (ON) critical 
                    alarm .
       - major (3): when there is no active critical alarm, but there is
                    at least one active (ON) major alarm .
       - minor (4): when there is no active major or critical alarm, but 
                    there is at least one active minor alarm.
       - warning (6): when there is no active major, critical or minor alarm, but 
                    there is at least one active warning alarm.
       - event (5): when there is no active alarm of another type, but 
                    there is at least one active event alarm.
       - off(2): when there is no active (ON) alarm (since last clear operation)."
      ::= { prtGenEntry 6}

prtGenTestStatus OBJECT-TYPE
     SYNTAX  INTEGER
         {
       off(2),
       on (3)
         }
     MAX-ACCESS  read-only
     STATUS  current
     DESCRIPTION
     "This attribute will be on(3) when there is at least one test 
      in progress (running) on the port; otherwise the value will 
      be off(2)."
     ::= { prtGenEntry 7}

prtGenTestMask OBJECT-TYPE
      SYNTAX  Integer32
      MAX-ACCESS  read-only
      STATUS  current
      DESCRIPTION
      "This is a mask which indicates which tests from the
       'prtGenTestCmd' list are allowed for the selected port.
       If a specific test is allowed, its respective bit will be SET 
       in the mask :

         TEST                  BIT
        -----------            ---
        localLoop               1
        remoteLoop              2
        bert                    3
        plb                     4
        inband                  5

        prbs                    8
        loop2-v54  (RLB)        9
        loop3-v54  (LLB)       10

        Tone injection         13
        Tx-plb                 14
        Tx-llb                 15
        DTE loop (HSSI)        16

        HDSL-Tx-Inband         20
        HDSL-Rx-Inband         21
		Monitor                22  (test port)
		User Line Loopback	   23

        Rem-Loop-on-Rem-Unit   25
		LBBD                   26
		LB1                    27
		LB2                    28
        BERT-on-Rem-Unit       29
		TS Remote Loop         30
		LLB-on-Rem-Unit        31

        e.g : If the return value is 3 -> 0000000000000011  ->
              Bits 1 & 2 are set -> the allowed tests are :
                                           local-loop
                                           remote-loop  "
      ::= { prtGenEntry 8}


prtGenTestCmd OBJECT-TYPE
      SYNTAX  Integer32
      MAX-ACCESS  read-write
      STATUS  current
      DESCRIPTION
      "Setting this object to a value as detailed furter on 
       (except 0) will initiate a test on the specific port, 
       if the operation is allowed (according to TestMask). 
       If the operation is not allowed, the mux will ignore the 
       operation.
       The test/s requested will be set according to the respective
       bit:
         TEST                  BIT
        -----------            ---
        localLoop               1
        remoteLoop              2
        bert                    3
        plb                     4
        inband                  5

        prbs                    8
        loop2-v54  (RLB)        9
        loop3-v54  (LLB)       10

        Tone injection         13
        Tx-plb                 14
        Tx-llb                 15
        DTE loop (HSSI)        16

        HDSL-Tx-Inband         20
        HDSL-Rx-Inband         21
		Monitor                22  (test port)
		User Line Loopback	   23

        Rem-Loop-on-Rem-Unit   25
		LBBD                   26
		LB1                    27
		LB2                    28
        BERT-on-Rem-Unit       29
		TS Remote Loop         30
		LLB-on-Rem-Unit        31

        e.g : If the requested value is 3 -> 0000000000000011  ->
              Bits 1 & 2 are set -> the requested tests are :
                                           local-loop
                                           remote-loop  

       Setting this object to stop (value=0 ; all bits are 0), 
       will stop all the user requested tests running on the 
       selected port; it will NOT stop the tests initiated by 
       the system."
      ::= { prtGenEntry 9}

prtGenTestRunning OBJECT-TYPE
      SYNTAX  Integer32
      MAX-ACCESS  read-only
      STATUS  current
      DESCRIPTION
      "This object indicates which tests are running currently on 
       the selected port (initiated by user and/or by the system).
       If a specific test is currently running on the port, its 
       respective bit will be SET: 

         TEST                  BIT
        -----------            ---
        localLoop               1
        remoteLoop              2
        bert                    3
        plb                     4
        llb                     5
        txInband                6
        rxInband                7
        prbs                    8
        loop2-v54  (RLB)        9
        loop3-v54  (LLB)       10
        DDS DSU loop           11
        DDS CSU loop           12
        Tone injection         13
        Tx-plb                 14
        Tx-llb                 15
        DTE loop (HSSI)        16
        Local  DTE  loop (HSSI)17
        Local  Line loop (HSSI)18
        Remote Line loop (HSSI)19
        HDSL-Tx-Inband         20
        HDSL-Rx-Inband         21
		Monitor                22  (test port)
		User Line Loopback	   23
		Network Line Loopback  24
        Rem-Loop-on-Rem-Unit   25
		LBBD                   26
		LB1                    27
		LB2                    28
        BERT-on-Rem-Unit       29
		TS Remote Loop         30
		LLB-on-Rem-Unit        31

        e.g : If the return value is 3 -> 0000000000000011  ->
              Bits 1 & 2 are set -> the running tests are :
                                           local-loop
                                           remote-loop  
        llb (Bit 5) - can be initiated by system only!            "
      ::= { prtGenEntry 10}


prtGenType OBJECT-TYPE
      SYNTAX  INTEGER {
   unknown (1),
   t1      (2),
   e1      (3),
   hs      (4),
   t1Csu   (5),
   t1Dsu   (6),
   e1Ltu   (7),
   e1Dsu   (8),
   hdsl    (9),
   sp      (10),
   t1F     (11),  --T1 Fiber-optic
   e1F     (12),  --E1 Fiber-optic
   dim     (13),
   isdn    (14),
   t3      (15),
   e3      (16),
   t3f     (17),
   e3f     (18),
   idsl    (19),
   stm1    (20),
   vc4     (21),
   vc12    (22),
   msdsl   (23),
   vc11    (24), 
   vc3     (25),
   soh     (26), 
   eth     (27),
   shdsl   (28),
   other   (255)
   }
      MAX-ACCESS  read-only
      STATUS  current
      DESCRIPTION
      "This object describes the type of the selected port.
       idsl - applicable for external ports of HS-U cards (of DXC) when 
              interface is LT-1."
      ::= { prtGenEntry 11}

prtGenInterfaceType OBJECT-TYPE
      SYNTAX  DisplayString (SIZE (0..255))
      MAX-ACCESS  read-only
      STATUS  current
      DESCRIPTION
      "This attribute indicates a unique HW interface type of the
       selected port.
       Examples: 
       - for T1 cards: DSU, CSU
       - for E1 cards: DSU, LTU
       - for HS cards: v35, rs422, x21
       etc..."
      ::= { prtGenEntry 12}

prtGenAlrClearCmd  OBJECT-TYPE
      SYNTAX  INTEGER
       {
  noOp (1),
  off  (2),
  on   (3)
       }
      MAX-ACCESS  read-write
      STATUS  current
      DESCRIPTION
      "Setting this attribute to ON, will enforce a  clear 
       operation on the port level alarms . Upon completion, 
       the value will automatically change to off(2).
       noOp - will be used by agents that do not support this 
              feature or object."
      ::= { prtGenEntry 13 }

prtGenAlrMaskAll  OBJECT-TYPE
      SYNTAX  INTEGER
       {
  noOp (1),
  off  (2),
  on   (3)
       }
      MAX-ACCESS  read-write
      STATUS  current
      DESCRIPTION
      "on(3) - will mask all the alarms of the selected port
       off(2)- will unmask all alarms of the selected port except
               the ones selected by the prtAlrMaskTable.
       noOp - will be used by agents that do not support this 
              feature or object."
      ::= { prtGenEntry 14 }

prtGenParamStatus OBJECT-TYPE
      SYNTAX  OCTET STRING
      MAX-ACCESS  read-only
      STATUS  current
      DESCRIPTION
      "This object indicates Status of parameters specific to the 
       selected port.
       - For a port that has no special status or is supported
         by prtSExHsfStatTable - 1 Octet: 00hex

       - For HS cards (Dxc cards) - 1 octet:
         Bit 7 (MSB)..Bit 2 = 0 (NA)
		 Bit 0 and 1 indicates RTS control signal state:
		 Bit 1:       '1'=active  ; '0'=notActive
         Bit 0 (LSB): '1'=unknown ; '0'=NA

       - For HS-U/1 external port (MP card, used in FCD-M) - 1 Octet:
	     Bit 7  6  5  4  3  2  1  0 LSB
             |________|  |__|  |__|
               spare     modem  sync  
               
         modem: 00 = other         sync:  00 = not sync
                01 = unknown              01 = sync
                10 = ASMi-31/2            10 = reserved
                11 = reserved             11 = reserved 

       - For VC-6, VC-12, VC-12/6 external ports - 1 Octet :
         Bit 7 (MSB)..Bit 2 = 0 (NA)
         Bit 1:       Tx Signaling '1'=On ; '0'=Off
         Bit 0 (LSB): Rx Signaling '1'=On ; '0'=Off

       - For VC-2/R2(FXS) external ports - 1 Octet : 
         Bit  -   7 6 5 4 3 2 1 0
                  |_| |_________|
                  Call  Call State
             Direction     

         Bit 7 (MSB) and Bit 6  : Call Direction
         00 - Incoming
         01 - Outgoing
         Bit 5..Bit 0: Call State
         000000 - Idle
         000001 - Seized
         000010 - Both-Way Conflict
         000011 - Seizure Ack
         000100 - Answered
         000101 - Clear Backward
         000110 - Clear Forward
         000111 - Blocked
         001000 - Fault
         001001 - Fault 3
         001010 - Fault 4
         001011 - Fault 5
         001100 - Fault 6
         001101 - Fault 7 
   
       - For ML-20 external port - 3 Octets :
         - 1 MS Octet will represent the Real Rate used:
           Bit    - 7 6 5 4 3 2 1 0
                    |___| |_______|
                     spare  Rate
             
          Valid values: 0..31, meaning 0..31x64Kbps
          Invalid values: 32..255.
           - 2 LS Octets will represent the Status of 7 Control 
             Signals:
             Signal - ---  CTS  DSR  DCD   RJ   TM   DTR  RTS
             Bit   - 7 6  5 4  3 2  1 0    7 6  5 4  3 2  1 0
             Octet  -          2                     3 (LS)
             '---' will always have the value 00
             Rest of the Signals (2 bits each) can have the following
             values:
             00=NA   ;  01=Unused ; 10=Off  ; 11=On 
         
       - For ML-H/E1, ML-H/1/E1, ML-H/S/E1 internal port - 1 Octet
         Bit    - 7 6 5 4 3 2 1 0
                  |___________|
                        spare   Mode of Operation

         Mode of Operation: '1'=Central  ; '0'=Remote 

       - For KM2100, KVF.5 cards - indicates the status of A and B signaling
	                               for each internal channel.
	     1 Octet:

		 Bit  -   7 6 5 4 3 2 1 0
                  |_____| |_| |_| 
                   spare   B   A

		 Bit 0 (LSB) and Bit 1 : A status
		 Bit 2 and Bit 3       : B status

		 00 - Off
		 01 - On
		 11 - Unknown
		  
	   - For FCD-W, NETWORK and USER ports - 1 Octet
         Status of Control Signals: '1'=On  ; '0'=Off or when not applicable

         Bit    - 7 6 5 4 3 2 1 0

         Bit 7 (MSB) - Signal Loss (applicable only for G.703 interface)
         Bit 6       - CONTROL     (applicable only for X.21 interface)
         Bit 5       - INDICATION  (applicable only for X.21 interface)
         Bit 4       - DSR         (applicable only for V.35 interface)
         Bit 3       - RTS         (applicable only for V.35 interface)
         Bit 2       - CTS         (applicable only for V.35 interface)
         Bit 1       - DTR         (applicable only for V.35 interface)
         Bit 0       - DCD         (applicable only for V.35 interface)

       - For DXC R6 , D8U, D16U External ports - 1 Octet
	     Bit 7  6  5  4  3  2  1  0 LSB
             |________|  |__|  |__|
               spare     modem  sync  
               
         modem: 00 = other         sync:  00 = not sync
                01 = unknown              01 = sync
                10 = ASMi-31/2            10 = reserved
                11 = reserved             11 = reserved
         
       - For DXC DE1-HDSL, DT1-HDSL, D16GSDSL, D8SL External ports - 2 Octets

         MSB octet: far-end modem channel interface
		 LSB octet: Sub Link existence (Y/N), far-end modem type,   
		            synchronization with far-end modem

         MSB octet:  0000 0000 = no interface
					 0000 0001 = db15 (X21)
					 0000 0010 = IR-IP
					 0000 0011 = IR-ETH-Q
					 0000 0100 = V35
					 0000 0101 = ETH-RJ45
					 0000 0110 = G703
					 0000 0111 = db25 (RS530)
					 0000 1000 = ETH-BNC
					 0000 1001 = E1(Balanced)
					 0000 1010 = E1(Unbalanced) 
					 Rest of the combinations: reserved

         LSB octet:
		             
	     Bit 7  6  5  4  3  2  1  0 LSB
             |  |___________|  |__|
            SL       modem     sync
    or Box material     
               
         SL:          modem: 00000 = other      sync:  00 = not sync
         0=not exist         00001 = unknown           01 = sync
         1=exists            00010 = ASMi-31/2         10 = reserved
                             00011 = HCD-E1            11 = reserved
         Box material        00100 = HTU-E1             
         (for D8SL card):    00101 = HTU-2
		 0=metal			 00110 = ASMi-52 SA/2W/Slave
		 1=plastic			 00111 = ASMi-52 SA/2W/Master     
							 01000 = ASMi-52/CQ card of LRS-24
							 01001 = ASMi-52/CD card of LRS-24
							 01010 = D16GSDSL card of DXC-3000
							 01011 = LRS-52
							 01100 = FCD  
                             01110 = D8GSDSL card of DXC-3000 
							 Rest  = reserved "
      ::= { prtGenEntry 15}

prtGenRdnStatus  OBJECT-TYPE
      SYNTAX  INTEGER
       {
       none (1),
       off  (2),
       on   (3)
       }
      MAX-ACCESS  read-only
      STATUS  current
      DESCRIPTION
      "This object indicates if this port is part of a redundant pair and in
       this case, if it is On or Off.
	   
       none(1) - No redundancy or Not Applicable
       off (2) - the port is part of a redundant pair and it is Off from 
                 Redundancy point of view (not the port used).
       on  (3) - the port is part of a redundant pair and it is On from 
                 Redundancy point of view (it is the port used)."
      ::= { prtGenEntry 16 }

prtGenTestMaskXP OBJECT-TYPE
      SYNTAX  OCTET STRING
      MAX-ACCESS  read-only
      STATUS  current
      DESCRIPTION
      "This is an Expanded test mask of the prtGenTestMask object.
       The prtGenTestMask object reached its maximum, being an Integer with 31 bits.
       This object indicates which tests from the  'prtGenTestCmdXP' list are 
       allowed for the selected port.
       If a specific test is allowed, its respective bit will be SET 
       in the mask :

         TEST                  BIT
        -----------            ---
        localLoop               1	  =LSB
        remoteLoop              2
        bert                    3
        plb                     4
        inband                  5

        prbs                    8
        loop2-v54  (RLB)        9
        loop3-v54  (LLB)       10

        Tone injection         13
        Tx-plb                 14
        Tx-llb                 15
        DTE loop (HSSI)        16

        HDSL-Tx-Inband         20
        HDSL-Rx-Inband         21
		Monitor                22  (test port)
		User Line Loopback	   23

        Rem-Loop-on-Rem-Unit   25
		LBBD                   26
		LB1                    27
		LB2                    28
        BERT-on-Rem-Unit       29
		TS Remote Loop         30
		LLB-on-Rem-Unit        31
		Downstream-AIS         32
		Upstream-AIS           33
		Send-RDI               34 

        e.g : If the return value is  00000003 hex  ->
              Bits 1 & 2 are set -> the allowed tests are :
                                           local-loop
                                           remote-loop  "
      ::= { prtGenEntry 17}


prtGenTestCmdXP OBJECT-TYPE
      SYNTAX  OCTET STRING
      MAX-ACCESS  read-write
      STATUS  current
      DESCRIPTION
	  "This is an Expanded test command of the prtGenTestCmd object.
       The prtGenTestCmd object reached its maximum, being an Integer with 31 bits.
       Setting this object to a value as detailed furter on 
       (except 0) will initiate a test on the specific port, 
       if the operation is allowed (according to TestMaskXP). 
       If the operation is not allowed, the mux will ignore the 
       operation.
       The test/s requested will be set according to the respective
       bit:
         TEST                  BIT
        -----------            ---
        localLoop               1	=LSB
        remoteLoop              2
        bert                    3
        plb                     4
        inband                  5

        prbs                    8
        loop2-v54  (RLB)        9
        loop3-v54  (LLB)       10

        Tone injection         13
        Tx-plb                 14
        Tx-llb                 15
        DTE loop (HSSI)        16

        HDSL-Tx-Inband         20
        HDSL-Rx-Inband         21
		Monitor                22  (test port)
		User Line Loopback	   23

        Rem-Loop-on-Rem-Unit   25
		LBBD                   26
		LB1                    27
		LB2                    28
        BERT-on-Rem-Unit       29
		TS Remote Loop         30
		LLB-on-Rem-Unit        31
		Downstream-AIS         32
		Upstream-AIS           33
		Send-RDI               34 

        e.g : If the requested value is 00000003 hex  ->
              Bits 1 & 2 are set -> the requested tests are :
                                           local-loop
                                           remote-loop  

       Setting this object to stop (value=0 ; all bits are 0), 
       will stop all the user requested tests running on the 
       selected port; it will NOT stop the tests initiated by 
       the system."
      ::= { prtGenEntry 18}

prtGenTestRunningXP OBJECT-TYPE
      SYNTAX  OCTET STRING
      MAX-ACCESS  read-only
      STATUS  current
      DESCRIPTION
	  "This is an Expanded object of the prtGenTestRunning object.
       The prtGenTestRunning object reached its maximum, being an Integer with 31 bits.
       This object indicates which tests are running currently on 
       the selected port (initiated by user and/or by the system).
       If a specific test is currently running on the port, its 
       respective bit will be SET: 

         TEST                  BIT
        -----------            ---
        localLoop               1	 =LSB
        remoteLoop              2
        bert                    3
        plb                     4
        llb                     5
        txInband                6
        rxInband                7
        prbs                    8
        loop2-v54  (RLB)        9
        loop3-v54  (LLB)       10
        DDS DSU loop           11
        DDS CSU loop           12
        Tone injection         13
        Tx-plb                 14
        Tx-llb                 15
        DTE loop (HSSI)        16
        Local  DTE  loop (HSSI)17
        Local  Line loop (HSSI)18
        Remote Line loop (HSSI)19
        HDSL-Tx-Inband         20
        HDSL-Rx-Inband         21
		Monitor                22  (test port)
		User Line Loopback	   23
		Network Line Loopback  24
        Rem-Loop-on-Rem-Unit   25
		LBBD                   26
		LB1                    27
		LB2                    28
        BERT-on-Rem-Unit       29
		TS Remote Loop         30
		LLB-on-Rem-Unit        31
		Downstream-AIS         32
		Upstream-AIS           33
		Send-RDI               34 

        e.g : If the return value is 00000003 hex  ->
              Bits 1 & 2 are set -> the running tests are :
                                           local-loop
                                           remote-loop  
        llb (Bit 5) - can be initiated by system only!            "
      ::= { prtGenEntry 19}


--prtGenTestDuration - Setting Duration of tests

prtGenTestDurationTable  OBJECT-TYPE
      SYNTAX SEQUENCE OF PrtGenTestDurationEntry
      MAX-ACCESS not-accessible
      STATUS current
	DESCRIPTION  "A table."
	::=  { prtGen 2 }

prtGenTestDurationEntry OBJECT-TYPE
      SYNTAX PrtGenTestDurationEntry
      MAX-ACCESS not-accessible
      STATUS current
	DESCRIPTION  "An entry in table."
	INDEX { prtGenTestPrtIdx, prtGenTestIdx }
      ::= { prtGenTestDurationTable 1}

PrtGenTestDurationEntry ::=
     SEQUENCE {
  prtGenTestPrtIdx     Integer32,
  prtGenTestIdx        INTEGER,
  prtGenTestDuration   Integer32 
	}

prtGenTestPrtIdx OBJECT-TYPE
      SYNTAX  Integer32
      MAX-ACCESS  read-only
      STATUS  current
      DESCRIPTION
      "This attribute indicates a unique number to identify a port. 
       The valid port number depends on the IO slot no.,  the 
       installed card type and the port type: outside/external, inside/internal. 

    In the Kilomux, the port index is calculated as follows:
    100*Slot+Ch. The external Ch numbers are 1..10, and the
    internal Ch numbers are 11..20.
       
    In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 ."
      ::= { prtGenTestDurationEntry 1}

prtGenTestIdx OBJECT-TYPE
   SYNTAX  INTEGER  
   {
   localLoop  (1),
   remoteLoop (2),
   bert       (3),
   plb        (4),
   rlb        (5),
   llb        (6),
   toneInjection (7),
   txInband (8),
   rxInband (9),
   remLoopOnRemUnit (10), 
   bertOnRemUnit (11),
   llbOnRemUnit (12),

   txPlb        (14),
   txLlb        (15),
   dteLoop      (16), --HSSI

   hdslTxInband (20),
   hdslRxInband (21),
   monitor      (22),
   userLineLoopback(23),

   lbbd         (26),
   lb1          (27),
   lb2          (28),

   tsRemoteLoop (30),

   downstreamAis(32),
   upstreamAis  (33),
   sendRdi      (34)
   }
   MAX-ACCESS  read-only
   STATUS  current
   DESCRIPTION
   "This attribute indicates the test, the duration refers. "
   ::= { prtGenTestDurationEntry 2}

prtGenTestDuration OBJECT-TYPE
      SYNTAX  Integer32
      MAX-ACCESS  read-write
      STATUS  current
      DESCRIPTION
      "This attribute indicates the maximum duration of executing
       a test on the specific port. This entry applies to the
       specified test . The resolution will be a minute, and the
       maximum duration is limited to 30 minutes .
       A zero  value specifies no time limitation.
       When the test isn't active the agent initiates this object to
       2 min. when the duration is needed and to 0 if it's not 
       required."
      ::= { prtGenTestDurationEntry 3}
       

--prtGen TS (TimeSlot) Assignment Table - for all ports of IO cards

prtGenTsTable  OBJECT-TYPE
     SYNTAX SEQUENCE OF PrtGenTsEntry
     MAX-ACCESS not-accessible
     STATUS  current
     DESCRIPTION
      "The write operation into the Table's Objects is valid only
       for the TmpCnfg entry (Scratch),exept some products 
       which enable direct writing to the ActiveCnfg. 
       This is written in the respective product's spec. "
  ::= { prtGen 3}

prtGenTsEntry OBJECT-TYPE
      SYNTAX PrtGenTsEntry
      MAX-ACCESS not-accessible
      STATUS current
	DESCRIPTION  "An entry in table."
	INDEX {prtGenTsCnfgIdx, prtGenTsPrtIdx, prtGenTsIdx }
      ::= { prtGenTsTable 1}

PrtGenTsEntry ::=
      SEQUENCE {
      prtGenTsCnfgIdx        Integer32,
      prtGenTsPrtIdx         Integer32,
      prtGenTsIdx            Integer32,
      prtGenTsType           INTEGER,
      prtGenTsIConPrt        Integer32,
      prtGenTsIConTs         Integer32 
	}

prtGenTsCnfgIdx OBJECT-TYPE
      SYNTAX  Integer32  (1..255)
      MAX-ACCESS  read-only
      STATUS  current
      DESCRIPTION
      "This attribute indicates the Idx of the Cnfg(1..255) being 
       accessed.
       Idx of 255 relates to the TmpCnfg. "
      ::= { prtGenTsEntry 1}


prtGenTsPrtIdx OBJECT-TYPE
      SYNTAX  Integer32
     MAX-ACCESS  read-only
      STATUS  current
      DESCRIPTION
      "This attribute indicates a unique  port number.
       The valid port number depends on the IO slot no.,  the 
       installed card type and the port type: outside, inside, 
       SP.
      In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 ."
      ::= { prtGenTsEntry 2}

prtGenTsIdx OBJECT-TYPE
      SYNTAX  Integer32
      MAX-ACCESS  read-only
      STATUS  current
      DESCRIPTION
      "This attribute indicates a unique time slot  position.
       The valid time slots are 
       1..25 for T1 Card (25=Fbit)
       0..31 for E1 or HS Card . 
       In G732S-E1 lines time slot 16 is not valid for data, 
       it is dedicated for multiframe synchronization bits
       and voice signaling."
      ::= { prtGenTsEntry 3}

prtGenTsType  OBJECT-TYPE
      SYNTAX  INTEGER
   {
   unknown       (1),
   voice         (2),
   data          (3),
   vcMP          (4),
   nc            (5),
   mng           (6)
   }
      MAX-ACCESS  read-write
      STATUS  current
      DESCRIPTION
   "The type of Timeslot. 
    If the source or destination port is an HS port,'TS Type'    
    must be 'data'.
    nc - means that this TimeSlot is not connected.
    voice, data, vcMP - also mean that this TS is connected.
    mng - means that this TS is dedicated to Management (not 
          connected to another port."
          
   ::= { prtGenTsEntry 4}

prtGenTsIConPrt OBJECT-TYPE
      SYNTAX  Integer32
      MAX-ACCESS  read-write
      STATUS  current
      DESCRIPTION
      "This attribute indicates the internally (In Mux) 
       connected port.
       The valid port number depends on the IO slot no.,  the 
       installed card type and the port type: outside, inside, 
       SP.
       * The outside ports will be the T1/E1 cards ports. 
         The convention used will be (for DXC):
         - first two digits will be: (IO slot number+10)
           for a stand-alone unit, the IO slot will be considered 1.
         - last one/two digits will be the port number within the 
           card, in odd numbers:
        port1 = 1
        port2 = 3
        port3 = 5 
        etc...
        Example: port2 of IO slot 11 will be: 213 .
       * The inside ports will be for example, the HS cards ports. 
         The convention used will be (for DXC):
         - first two digits will be: (IO slot number+10)
           for a stand-alone unit, the IO slot will be considered 1.
         - last one/two digits will be the port number within the 
           card, in even numbers:
           port1 = 2
           port2 = 4
           port3 = 6 
           etc...
           Example: port2 of IO slot 11 will be: 214 .
       * noConnection - will be indicated as 10 for DXC and FCD-E1/T1.
                      - will be indicated as 100 for FCD-E1/I and SMODs.   
       * Split TS (same TS is Split to several ports) - 11. 
	   * notApplicable- will be indicated as 100 for LRS IMODs.
       
       All HS port's timeslots must have the same destination
       port."
      ::= {prtGenTsEntry 5}

prtGenTsIConTs OBJECT-TYPE
      SYNTAX  Integer32
      MAX-ACCESS  read-write
      STATUS  current
      DESCRIPTION
      "This attribute indicates a unique time slot  position.
       The valid time slots are 
       1..25 for T1 Card (25=Fbit)
       0..31 for E1 (or HS) Card. 
       In G732S-E1 lines time slot 16 is not valid for data, it is 
       dedicated for multiframe synchronization bits and voice 
       signaling.
       * For DXC: All HS port's timeslots must start with Timeslot 
         no.1 "
      ::= {prtGenTsEntry 6}

--Port current alarms table

prtAlr  OBJECT IDENTIFIER ::= {prtGen 4}

prtSAlarmTable OBJECT-TYPE
      SYNTAX SEQUENCE OF PrtSAlarmEntry
      MAX-ACCESS not-accessible
      STATUS current
	DESCRIPTION  "A table."
	::=  { prtAlr 1 }

prtSAlarmEntry OBJECT-TYPE
      SYNTAX PrtSAlarmEntry
      MAX-ACCESS not-accessible
      STATUS current
	DESCRIPTION  "An entry in table."
	INDEX { prtSAlarmPrtIdx, prtSAlarmIdx}
      ::= { prtSAlarmTable 1}

PrtSAlarmEntry ::=
      SEQUENCE {
  prtSAlarmPrtIdx            Integer32,
  prtSAlarmIdx               Integer32,
  prtSAlarmCode              Integer32,
  prtSAlarmState             INTEGER, --severity
  prtSAlarmMask              INTEGER,
  prtSAlarmInvert            INTEGER,
  prtSAlarmOnOff             INTEGER,
  prtSAlarmCounter           Integer32 
	}        

prtSAlarmIdx OBJECT-TYPE
      SYNTAX  Integer32
      MAX-ACCESS  read-only
      STATUS  current
      DESCRIPTION
      "A unique number to identify an entry in the alarm status 
       table.
       Users should use the get next function to read this table 
       because the indexes are not consecutive."
      ::= { prtSAlarmEntry 1}

prtSAlarmPrtIdx OBJECT-TYPE
      SYNTAX  Integer32
      MAX-ACCESS  read-only
      STATUS  current
      DESCRIPTION
      "This attribute indicates a unique number to identify a port. 
       The valid port number depends on the IO slot no.,  the 
       installed card type and the port type: outside/external, inside/internal. 

    In the Kilomux, the port index is calculated as follows:
    100*Slot+Ch. The external Ch numbers are 1..10, and the
    internal Ch numbers are 11..20.
       
    In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 ."
    ::= { prtSAlarmEntry 2}

prtSAlarmCode OBJECT-TYPE
      SYNTAX  Integer32
      MAX-ACCESS  read-only
      STATUS  current
      DESCRIPTION
      "This object indicates a code related to a specific
       alarm description. The list of codes and their related
       descriptions will be sent to NMS request (for display purpose)
       by alrGenTable."
      ::= { prtSAlarmEntry 3 }

prtSAlarmState OBJECT-TYPE
      SYNTAX  INTEGER {
   event    (3),
   minor    (4),
   major    (5),
   warning  (6),
   critical (7)
       }
      MAX-ACCESS  read-only
      STATUS  current
      DESCRIPTION
      "This object indicates the port alarm severity."      
      ::= { prtSAlarmEntry 4 }

prtSAlarmMask OBJECT-TYPE
      SYNTAX  INTEGER {
  off(2),
  on (3)
       }
      MAX-ACCESS  read-only
      STATUS  current
      DESCRIPTION
      "Alarm Mask is : on/off."
      ::= { prtSAlarmEntry 5 }

prtSAlarmInvert OBJECT-TYPE
      SYNTAX  INTEGER {
  off(2),
  on (3)
       }
      MAX-ACCESS  read-only
      STATUS  current
      DESCRIPTION
      "Alarm Invert is : on/off."
      ::= { prtSAlarmEntry 6 }

prtSAlarmOnOff OBJECT-TYPE
      SYNTAX  INTEGER {
  off(2),
  on (3)
       }
      MAX-ACCESS  read-only
      STATUS  current
      DESCRIPTION
      "Alarm state is : on/off."
      ::= { prtSAlarmEntry 7 }

prtSAlarmCounter OBJECT-TYPE
      SYNTAX  Integer32
      MAX-ACCESS  read-only
      STATUS  current
      DESCRIPTION
      "A counter - how many times the alarm occured (ON) since last
       clear operation or since last Reset."
      ::= { prtSAlarmEntry 8 }

prtAlrMaskTable OBJECT-TYPE
      SYNTAX SEQUENCE OF PrtAlrMaskEntry
      MAX-ACCESS not-accessible
      STATUS current
	DESCRIPTION  "A table."
	::=  { prtAlr 2 }

prtAlrMaskEntry OBJECT-TYPE
      SYNTAX PrtAlrMaskEntry
      MAX-ACCESS not-accessible
      STATUS current
	DESCRIPTION  "An entry in table."
	INDEX { prtAlrMaskPrtIdx}
      ::= { prtAlrMaskTable 1}

PrtAlrMaskEntry ::=
      SEQUENCE {
  prtAlrMaskPrtIdx         Integer32,
  prtAlrMask               OCTET STRING
      }        


prtAlrMaskPrtIdx OBJECT-TYPE
      SYNTAX  Integer32
      MAX-ACCESS  read-only
      STATUS  current
      DESCRIPTION
      "This attribute indicates a unique number to identify a port. 
       The valid port number depends on the IO slot no.,  the 
       installed card type and the port type: outside/external, inside/internal. 

    In the Kilomux, the port index is calculated as follows:
    100*Slot+Ch. The external Ch numbers are 1..10, and the
    internal Ch numbers are 11..20.
       
    In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 ."
    ::= { prtAlrMaskEntry 1}

prtAlrMask OBJECT-TYPE
      SYNTAX OCTET STRING  (SIZE (8))
      MAX-ACCESS read-write
      STATUS current
   DESCRIPTION
   "This object is a mask that indicates which port level 
    alarms are masked. The masked alarms (their bit is set to 
    '1') are neither sent to the manager, nor taken into account
    for alarm status and LEDs.
    Bit no. = Alarm code
    The bits that do not belong to the port level will be 0.
    This object is applicable only when prtGenAlrMaskAll=off 
    (otherwise all port alarms are masked).
    Example: When Alarms having the codes 31 and 40 are masked,
             the value of this object will be 10080000000 (hex)."
      ::= { prtAlrMaskEntry 2 }
      
      
--Port BERT table


prtBertTable OBJECT-TYPE
      SYNTAX SEQUENCE OF PrtBertEntry
      MAX-ACCESS not-accessible
      STATUS current
   DESCRIPTION   
      "This table includes the BERT parameters, counters and 
       commands.
    The configurable parameters:
    - prtBertPattern
    - prtBertInjectRate
    - prtBertTs
    are not Set per configuration (same for all Configurations)
    but start being applied by the Agent only upon successful
    Update/Download operation. Therefore, Set will enter the 
    values to the Temporary Configuration of the agent, while
    Get will get the values of the Active Configuration."
    ::= { prtGen 5 }

prtBertEntry OBJECT-TYPE
      SYNTAX PrtBertEntry
      MAX-ACCESS not-accessible
      STATUS current
	DESCRIPTION  "An entry in table."
	INDEX { prtBertPrtIdx}
      ::= { prtBertTable 1}

PrtBertEntry ::=
      SEQUENCE {
  prtBertPrtIdx             Integer32,
  prtBertPattern            INTEGER,
  prtBertInjectRate         INTEGER,
  prtBertInjectErrRateCmd   INTEGER,
  prtBertInjectSingleErrCmd INTEGER,
  prtBertRunTime            Integer32,
  prtBertESs                Integer32,
  prtBertSyncLoss           Integer32,
  prtBertErrorBits          Integer32,
  prtBertClearCounters      INTEGER,
  prtBertSyncStatus         INTEGER,     
  prtBertTs                 OCTET STRING,
  prtBertResult 		    DisplayString (SIZE (0..255))
      }        

prtBertPrtIdx OBJECT-TYPE
      SYNTAX  Integer32
      MAX-ACCESS  read-only
      STATUS  current
      DESCRIPTION
      "This attribute indicates a unique number to identify a port. 
       The valid port number depends on the IO slot no.,  the 
       installed card type and the port type: outside/external, inside/internal. 

    In the Kilomux, the port index is calculated as follows:
    100*Slot+Ch. The external Ch numbers are 1..10, and the
    internal Ch numbers are 11..20.
       
    In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 .

    In the MP :   
      - first two digits will be: (IO slot number+10)
      - last one/two digits will be according to the external port 
        number within the card:
        exPrt1 -> 1
        exPrt2 -> 3
        exPrt3 -> 5
        exPrt4 -> 7 . "
    ::= { prtBertEntry 1}

prtBertPattern OBJECT-TYPE
      SYNTAX  INTEGER
    {
     p2E3m1   (1),
     p2E4m1   (2),
     p2E5m1   (3),
     p2E6m1   (4),
     p2E7m1   (5),
     p511     (6),
     p2E10m1  (7),
     p2047    (8),
     p2E15m1  (9),
     p2E17m1 (10),
     p2E18m1 (11),
     p2E20m1 (12),
     qrss    (13),
     p2E21m1 (14),
     p2E22m1 (15),
     p2E23m1 (16),
     p2E25m1 (17),
     p2E28m1 (18),
     p2E29m1 (19),
     p2E31m1 (20),
     p2E32m1 (21),
     rj011   (22),  
     p63     (23),  
     p1M7S   (24),  
     p1S7M   (25),  
     alternate(26), 
     mark    (27),  
     space   (28),  
     notApplicable (255)
    }    
      MAX-ACCESS  read-write
      STATUS  current
      DESCRIPTION
      "This object indicates the pattern of the BERT.
       p2Exxm1 = 2Exx-1.
       pxx     = pattern xx.
       This object is the same for all configurations.
       notApplicable - when this object is not supported."
      ::= { prtBertEntry 2}

prtBertInjectRate OBJECT-TYPE
      SYNTAX  INTEGER
    {
     noError  (1),
     r10Em1   (2),
     r10Em2   (3),
     r10Em3   (4),
     r10Em4   (5),
     r10Em5   (6),
     r10Em6   (7),
     r10Em7   (8),
     single   (9),
     notApplicable (255)
    }    
      MAX-ACCESS  read-write
      STATUS  current
      DESCRIPTION
      "This object indicates the error rate injection of the BERT.
       r10Emx = 10E-x
       This object is the same for all configurations.
       single - single error injection.
       notApplicable - when this object is not supported."
      ::= { prtBertEntry 3}

prtBertInjectErrRateCmd OBJECT-TYPE
      SYNTAX  INTEGER
    {
     off  (2),
     on   (3)
    }    
      MAX-ACCESS  read-write
      STATUS  current
      DESCRIPTION
      "This object controls activation/deactivation of the Error 
       Rate Injection during BERT."   
      ::= { prtBertEntry 4}

prtBertInjectSingleErrCmd OBJECT-TYPE
      SYNTAX  INTEGER
    {
     off  (2),
     on   (3)
    }    
      MAX-ACCESS  read-write
      STATUS  current
      DESCRIPTION
      "This object enables to initiate a Single Error Injection 
       during BERT (on). Upon completion, the value will 
       automatically change to off(2)."   
      ::= { prtBertEntry 5}

prtBertRunTime OBJECT-TYPE
      SYNTAX  Integer32
      MAX-ACCESS  read-only
      STATUS  current
      DESCRIPTION
      "This object indicates how much time (seconds) passed since
       BERT started to run."   
      ::= { prtBertEntry 6}

prtBertESs OBJECT-TYPE
      SYNTAX  Integer32
      MAX-ACCESS  read-only
      STATUS  current
      DESCRIPTION
      "How many Errored Seconds were detected since BERT started
       to run.
       Counter for Kmux and MP."  
      ::= { prtBertEntry 7}
       
prtBertSyncLoss OBJECT-TYPE
      SYNTAX  Integer32
      MAX-ACCESS  read-only
      STATUS  current
      DESCRIPTION
      "How many times Sync Loss was detected since BERT started
       to run.
       For some products: number of seconds in which Sync Loss occured 
       since BERT started to run. See product specification."   
      ::= { prtBertEntry 8}
         
prtBertErrorBits OBJECT-TYPE
      SYNTAX  Integer32
      MAX-ACCESS  read-only
      STATUS  current
      DESCRIPTION
      "How many Error Bits were detected since BERT started
       to run."   
      ::= { prtBertEntry 9}

prtBertClearCounters  OBJECT-TYPE
      SYNTAX  INTEGER
       {
       off(2),
       on (3)
       }
      MAX-ACCESS  read-write
      STATUS  current
      DESCRIPTION
      "Setting this object to ON, will enforce a  clear 
       operation of some BERT Counters. Upon completion, 
       the value will automatically change to off(2)."
      ::= { prtBertEntry 10}

prtBertSyncStatus  OBJECT-TYPE
      SYNTAX  INTEGER
       {
  notApplicable(1),
  syncLoss     (2),
  sync         (3)
       }
      MAX-ACCESS  read-only
      STATUS  current
      DESCRIPTION
      "Sync Status while BERT runs."
      ::= { prtBertEntry 11}

prtBertTs  OBJECT-TYPE
      SYNTAX  OCTET STRING (SIZE(0..4))
      MAX-ACCESS  read-write
      STATUS  current
      DESCRIPTION
     "This object indicates on which TSs of the selected port, BERT 
      should be applied. 
      Each Bit of the Octet represents a TS:
      31 ......0
      MSB     LSB

      Bit 0 will not be used.
      If the bit value is '1' - BERT should be applied on this TS.
      For a  T1 port, the valid raised bits ('1') are: 1..25.
      For an E1 port, the valid raised bits ('1') are: 1..31.
      
      Agents that do not support this feature will send SIZE 0."
      ::= { prtBertEntry 12}

prtBertResult     OBJECT-TYPE
      SYNTAX      DisplayString (SIZE (0..255)) 
      MAX-ACCESS  read-only
      STATUS      current
      DESCRIPTION
     "This object indicates Result of BERT 
      for the selected port
      (number of error bits divided to the total
      number of data bits.)
      Applicable only if BERT is running on this port

      Agents that do not support this feature will send SIZE 0."
      ::= { prtBertEntry 13}

--Port Monitoring Table - for Monitoring ports
--The table is applicable only for DXC T1/E1/HS ports and Optimux-T3

prtMonTable  OBJECT-TYPE
     SYNTAX SEQUENCE OF PrtMonEntry
     MAX-ACCESS not-accessible
     STATUS  current
     DESCRIPTION
      "For DXC, the write operation into the Table's Objects is valid only
       for the TmpCnfg entry (Scratch)."
  ::= { prtGen 6}

prtMonEntry OBJECT-TYPE
      SYNTAX PrtMonEntry
      MAX-ACCESS not-accessible
      STATUS current
	DESCRIPTION  "An entry in table."
	INDEX {prtMonCnfgIdx, prtMonitoringIdx }
      ::= { prtMonTable 1}

PrtMonEntry ::=
      SEQUENCE {
      prtMonCnfgIdx        Integer32,
      prtMonitoringIdx     Integer32,
	  prtMonitoringEnable  INTEGER,
      prtMonitoringTSs     OCTET STRING,
      prtMonitoredPort     Integer32,
      prtMonitoredTSs      OCTET STRING
      }

prtMonCnfgIdx OBJECT-TYPE
      SYNTAX  Integer32  (1..255)
      MAX-ACCESS  read-only
      STATUS  current
      DESCRIPTION
      "This object indicates the Idx of the Cnfg(1..255) being 
       accessed.
       Idx of 255 relates to the TmpCnfg.
       For products that do not support configurations, 1 will be always used."
      ::= { prtMonEntry 1}

prtMonitoringIdx OBJECT-TYPE
      SYNTAX  Integer32
      MAX-ACCESS  read-only
      STATUS  current
      DESCRIPTION
      "This object indicates the Monitoring Port Index.
	   For DXC:
         The valid port number depends on the IO slot no.,  the 
         installed card type and the port type: external, internal.
         * The external ports will according to the convention (for DXC):
         - first two digits will be: (IO slot number+10)
         - last one/two digits will be the port number within the 
           card, in odd numbers:
           port1 = 1
           port2 = 3
           port3 = 5 
           etc...
           Example: port2 of IO slot 11 will be: 213 .
         * The internal ports will be according to the convention (for DXC):
           - first two digits will be: (IO slot number+10)
           - last one/two digits will be the port number within the 
             card, in even numbers:
             port1 = 2
             port2 = 4
             port3 = 6 
             etc...
           Example: port2 of IO slot 11 will be: 214 .
        For Optimux-T3: 
          255 (Not Applicable) will be always used. The Monitoring port is always 
		  the Station Clock (not considered an interface)."
      ::= { prtMonEntry 2}

prtMonitoringEnable  OBJECT-TYPE
      SYNTAX  INTEGER
       {
      notApplicable(1),
      disabled     (2),
      enabled      (3)
       }
      MAX-ACCESS  read-write
      STATUS  current
      DESCRIPTION
      "This object indicates if the prtMonitoringIdx is configured as 
       a monitoring port or not.
       disabled = the port is NOT configured to monitor. Setting this object
	              to this value will cause reset (to 0) of the prtMonitoringTSs
				  and prtMonitoredTSs objects.
       enabled  = the port IS configured to monitor.
       For Optimux-T3: always enabled (RO supported)."
      ::= {prtMonEntry 3}

prtMonitoringTSs OBJECT-TYPE
      SYNTAX  OCTET STRING (SIZE(0..4))
      MAX-ACCESS  read-write
      STATUS  current
      DESCRIPTION
     "This object indicates which TSs of the Monitoring port, 
      the test equipment should monitor. 
      Each Bit of the Octet represents a TS:
      31 ......0
      MSB     LSB

      Bit 0 will not be used.
      If the bit value is '1' - this TS should be monitored.
      For a  T1 port, the valid raised bits ('1') are: 1..24.
      For an E1 port, the valid raised bits ('1') are: 1..31.
      Default: all bits='0'
      Agents that do not support this feature will send SIZE 0.
      This object can be Set as described only if prtMonitoringEnable=enabled. "
      ::= {prtMonEntry 4}

prtMonitoredPort  OBJECT-TYPE
      SYNTAX  Integer32
      MAX-ACCESS  read-write
      STATUS  current
      DESCRIPTION
      "This object indicates the MONITORED Port Index that the Monitoring
       port monitors.
	   For DXC:
         The valid port number depends on the IO slot no.,  the 
         installed card type and the port type: external, internal.
         * The external ports will according to the convention (for DXC):
           - first two digits will be: (IO slot number+10)
           - last one/two digits will be the port number within the 
             card, in odd numbers:
             port1 = 1
             port2 = 3
             port3 = 5 
             etc...
           Example: port2 of IO slot 11 will be: 213 .
         * The internal ports will be according to the convention (for DXC):
           - first two digits will be: (IO slot number+10)
           - last one/two digits will be the port number within the 
             card, in even numbers:
             port1 = 2
             port2 = 4
             port3 = 6 
             etc...
           Example: port2 of IO slot 11 will be: 214 .
         * 100 - no port monitored
       For Optimux-T3:
	     The valid channels are:
         0 =  no Ch monitored
         1..21 or 1..28 (=CH1..CH21 or CH1..CH28) according to product's 
         configuration."
   ::= { prtMonEntry 5}

prtMonitoredTSs OBJECT-TYPE
      SYNTAX  OCTET STRING (SIZE(0..4))
      MAX-ACCESS  read-write
      STATUS  current
      DESCRIPTION
     "This object indicates which TSs of the Monitored port, should be monitored. 
      Each Bit of the Octet represents a TS:
      31 ......0
      MSB     LSB

      Bit 0 will not be used.
      If the bit value is '1' - this TS should be monitored.
      For a  T1 port, the valid raised bits ('1') are: 1..24.
      For an E1 port, the valid raised bits ('1') are: 1..31.
      Default: all bits='0'
      Agents that do not support this feature will send SIZE 0.
      This object can be Set as described only if prtMonitoringEnable=enabled."
      ::= {prtMonEntry 6}


-- Port Configuration Table
-- This table is applicable only for KMUX ports 

prtCfgParam  OBJECT IDENTIFIER  ::=  {prtGen 7}

prtCfgParamTable OBJECT-TYPE
      SYNTAX SEQUENCE OF PrtCfgParamEntry
      MAX-ACCESS not-accessible
      STATUS  current
      DESCRIPTION
       "The write operation into the Table Objects is valid only
        to the TmpCnfg entry.
        Parameters for the channels of the KMUX Cards: KMBE/New, KVF.6 family."
      ::= { prtCfgParam 1}

prtCfgParamEntry OBJECT-TYPE
      SYNTAX PrtCfgParamEntry
      MAX-ACCESS not-accessible
      STATUS current
	DESCRIPTION  "An entry in table."
	INDEX {prtCfgParamCnfgIdx, prtCfgParamIdx }
      ::= { prtCfgParamTable 1}

PrtCfgParamEntry ::=
      SEQUENCE {
        prtCfgParamCnfgIdx        Integer32,
        prtCfgParamIdx            Integer32,
        prtCfgParamSlt            INTEGER,
        prtCfgParamOperatedMl     INTEGER,
        prtCfgParamMlAtoMlBPrio   INTEGER,
        prtCfgParamMlBtoMlAPrio   INTEGER,
		prtCfgParamInbandLoopDetection INTEGER
        }

prtCfgParamCnfgIdx OBJECT-TYPE
      SYNTAX  Integer32  (1..255)
      MAX-ACCESS  read-only
      STATUS  current
      DESCRIPTION
      "This attribute indicates the Idx of the Cnfg (1..100) being 
       accessed.
       Idx  255 relates to the TmpCnfg."
      ::= {prtCfgParamEntry 1}

prtCfgParamIdx OBJECT-TYPE
      SYNTAX  Integer32
      MAX-ACCESS  read-only
      STATUS  current
      DESCRIPTION
      "A unique identifier of the port (within the card when applicable).
       - For KM-2100:  Slot*100+Ch
         external ports:  Ch=1..10
         internal ports (sub-channels): Ch=11..20.
       - For FCD-T1/E1: SUB=113, CH1=122, CH2=124. "
      ::= {prtCfgParamEntry 2}

prtCfgParamSlt OBJECT-TYPE
      SYNTAX  INTEGER
 {
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118),
	notApplicable(255)
       }
      MAX-ACCESS  read-only
      STATUS  current
      DESCRIPTION
      "This attribute indicates a unique number to identify the slot where
       the card is inserted in.
       In the 2104 Unit the entries kmxIO5(111)..kmxIO12(118) are not valid.
       notApplicable(255) - for products that do not have Slots."
      ::= {prtCfgParamEntry 3}

 prtCfgParamOperatedMl OBJECT-TYPE
      SYNTAX  INTEGER {
                  notApplicable(1),
                  kmxMlA     (103),
                  kmxMlB     (104)				  
        }
      MAX-ACCESS  read-write
      STATUS  current
      DESCRIPTION
      "The main link for this channel.
       The field is relevant only for ML modes of Dual, Priority 
       Bumping and Switched Backup."
      ::= {prtCfgParamEntry 4}

prtCfgParamMlAtoMlBPrio OBJECT-TYPE
      SYNTAX  INTEGER {
                       notApplicable(1),
                       low          (2),
                       high         (3)
        }
      MAX-ACCESS  read-write
      STATUS  current
      DESCRIPTION
      "ML-A to ML-B Priority.
       The field is relevant only for ML modes of Priority Bumping
       and Switched Backup."
      ::= {prtCfgParamEntry 5}

prtCfgParamMlBtoMlAPrio OBJECT-TYPE
      SYNTAX  INTEGER {
                     notApplicable(1),
                     low          (2),
                     high         (3)
        }
      MAX-ACCESS  read-write
      STATUS  current
      DESCRIPTION
      "ML-B to ML-A Priority.
       The field is relevant only for ML modes of Priority Bumping."
      ::= {prtCfgParamEntry 6}

prtCfgParamInbandLoopDetection OBJECT-TYPE
      SYNTAX  INTEGER {
                     notApplicable(1),
                     disabled     (2),
                     enabled      (3)
        }
      MAX-ACCESS  read-write
      STATUS  current
      DESCRIPTION
      "Inband Loop Detection.
       The field is relevant for the following FCD-T1/E1 ports:
       SUB, CH1, CH2."
      ::= {prtCfgParamEntry 7}


--DACS T1/E1 port specific parameters  

--DACS T1/E1 port statistics parameters.
--These parameters are in addition to those of RFC-1406 MIB. 

prtT1E1StatTable OBJECT-TYPE
  SYNTAX  SEQUENCE OF PrtT1E1StatEntry
  MAX-ACCESS  not-accessible
  STATUS  current
  DESCRIPTION
  "T1/E1 port statistics table."
  ::= { prtT1E1 1}

prtT1E1StatEntry   OBJECT-TYPE
  SYNTAX  PrtT1E1StatEntry
  MAX-ACCESS  not-accessible
  STATUS  current
  DESCRIPTION
  " An entry in the T1/E1 port statistics table."
  INDEX { prtT1E1SPrtIdx }
  ::= { prtT1E1StatTable 1}

PrtT1E1StatEntry ::=
     SEQUENCE {
  prtT1E1SPrtIdx
  Integer32,
  prtT1E1SSlt
  INTEGER,
  prtT1E1OosCount
  Gauge32,
  prtT1E1BpvLastMin
  Gauge32,
  prtT1E1BpvMax
  Gauge32
  }

prtT1E1SPrtIdx OBJECT-TYPE
      SYNTAX  Integer32
      MAX-ACCESS  read-only
      STATUS  current
      DESCRIPTION
      "This attribute indicates a unique  port number.
       The same numbering as for prtGenPrtIdx.
       The valid port number depends on the IO slot no.,  the 
       installed card type and the port type: outside, inside. 
      * The outside ports will be the T1/E1 cards ports. 
        The convention used will be (for DXC):
        - first two digits will be: (IO slot number+10)
        - last one/two digits will be the port number within the 
          card, in odd numbers:
          port1 = 1
          port2 = 3
          port3 = 5 
          etc...
        Example: port2 of IO slot 11 will be: 213 ."
      ::= { prtT1E1StatEntry 1}

prtT1E1SSlt     OBJECT-TYPE
      SYNTAX  INTEGER
       {
       clA   (3),
       clB   (4),
       io1   (5),
       io2   (6),
       io3   (7),
       io4   (8),
       io5   (9),
       io6  (10),
       io7  (11),
       io8  (12),
       io9  (13),
       io10 (14),
       io11 (15),
       io12 (16),
    io13 (17),
    io14 (18),
    io15 (19),
    standAlone (255)
       }
      MAX-ACCESS  read-only
      STATUS  current
      DESCRIPTION
      "This attribute indicates a unique number to identify the slot where
       the card is inserted in.
       When the unit is stand-alone, this object is not applicable
       and 255 will be used."
      ::= { prtT1E1StatEntry 2}

prtT1E1OosCount  OBJECT-TYPE
   SYNTAX  Gauge32
      MAX-ACCESS  read-only
      STATUS  current
      DESCRIPTION
   "This object is applicable only for an E1 active port.
    It provides the number of red alarm events since the last
    count clearing."
   ::= { prtT1E1StatEntry 3 }

prtT1E1BpvLastMin  OBJECT-TYPE
   SYNTAX  Gauge32
      MAX-ACCESS  read-only
      STATUS  current
      DESCRIPTION
   "This object is applicable only for an E1 active port.
    It provides the number of BPV (BiPolar Violation) events 
    detected during the last minute."
   ::= { prtT1E1StatEntry 4 }

prtT1E1BpvMax  OBJECT-TYPE
   SYNTAX  Gauge32
      MAX-ACCESS  read-only
      STATUS  current
      DESCRIPTION
   "This object is applicable only for an E1 active port.
    It provides the maximal number of BPV (BiPolar Violation) 
    events (per minute), detected during the worst minute."
   ::= { prtT1E1StatEntry 5 }


--DACS T1/E1 port configuration parameters.
--
--Objects 2..9 appear in RFC-1406 MIB (dsx1ConfigTable) as RW
--objects. They were entered in this private MIB, because in
--RFC-1406 MIB there is no reference to configuration number.


prtT1E1CnfgTable OBJECT-TYPE
  SYNTAX  SEQUENCE OF PrtT1E1CnfgEntry
  MAX-ACCESS  not-accessible
  STATUS  current
  DESCRIPTION
  "T1/E1 port configuration table."
  ::= { prtT1E1 2}

prtT1E1CnfgEntry   OBJECT-TYPE
  SYNTAX  PrtT1E1CnfgEntry
  MAX-ACCESS  not-accessible
  STATUS  current
  DESCRIPTION
  " An entry in the T1/E1 port configuration table."
  INDEX { prtT1E1CnfgIdx, prtT1E1PrtIdx }
  ::= { prtT1E1CnfgTable 1}

PrtT1E1CnfgEntry ::=
     SEQUENCE {
  prtT1E1CnfgIdx
  Integer32,
  prtT1E1PrtIdx
  Integer32,
  prtT1E1Slt
  INTEGER,
  prtT1E1LineType
  INTEGER,
  prtT1E1LineCode
  INTEGER,
  prtT1E1SignalMode
  INTEGER,
  prtT1E1Fdl
  INTEGER,
  prtT1E1FdlMode
  INTEGER,
  prtT1E1Sync
  INTEGER,
  prtT1E1CGA
  INTEGER,
  prtT1E1IdleCode
  OCTET STRING,
  prtT1E1OosSignal
  INTEGER,
  prtT1E1VoiceOos
  OCTET STRING,
  prtT1E1DataOos
  OCTET STRING,
  prtT1E1LineLengthMask
  INTEGER,
  prtT1E1TxGainMask
  INTEGER,
  prtT1E1InbandMng
  INTEGER,
  prtT1E1InbandMngRate
  INTEGER,
  prtT1E1DedicatedTs
  Integer32,
  prtT1E1InbandMngRoutProt
  INTEGER,
  prtT1E1LinkMode
  INTEGER,
  prtT1E1Multiplier 
  INTEGER,
  prtT1E1RxGain 
  INTEGER,
  prtT1E1RAI
  INTEGER, 
  prtT1E1LineMode	  
  INTEGER,
  prtT1E1TS0SaBits
  OCTET STRING,
  prtT1E1ConnectedTS
  INTEGER,
  prtT1E1Ts0SaBit
  INTEGER,
  prtT1E1SameFeCnfg
  INTEGER,
  prtT1E1RemCrc4
  INTEGER,
  prtT1E1MaxTSs
  Integer32,
  prtT1E1EocTsConfig
  INTEGER
  }

prtT1E1CnfgIdx OBJECT-TYPE
      SYNTAX  Integer32 (1..255)
      MAX-ACCESS  read-only
      STATUS  current
      DESCRIPTION
      "This attribute indicates the Idx of the Config being accessed.
       Idx of 255 relates to the Temporary (Scratch) Config. "
      ::= { prtT1E1CnfgEntry 1}

prtT1E1PrtIdx OBJECT-TYPE
      SYNTAX  Integer32
      MAX-ACCESS  read-only
      STATUS  current
      DESCRIPTION
      "This attribute indicates a unique  port number.
    The same numbering as for prtGenPrtIdx.
       The valid port number depends on the IO slot no.,  the 
       installed card type and the port type: outside, inside. 
       In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 .
   
       In the Kilomux, the port index is calculated as follows:
       100*Slot+Ch. The external Ch numbers are 1..10, and the
       internal Ch numbers are 11..20."
      ::= { prtT1E1CnfgEntry 2}

prtT1E1Slt     OBJECT-TYPE
      SYNTAX  INTEGER
       {
       clA   (3),
       clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
   
    kmxMlA (103),
    kmxMlB (104),

    kmxOpt (106),
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118),
    standAlone (255)
       }
      MAX-ACCESS  read-only
      STATUS  current
      DESCRIPTION
      "This attribute indicates a unique number to identify the slot where
       the card is inserted in.
       When the unit is stand-alone, this object is not applicable
       and 255 will be used."
      ::= { prtT1E1CnfgEntry 3}

prtT1E1LineType OBJECT-TYPE
    SYNTAX  INTEGER {
                other    (1),
                esf      (2),
                d4       (3), --sf
                e1       (4),
                e1Crc    (5),
                e1MF     (6),
                e1CrcMF  (7),
                unframed (8)
            }
    MAX-ACCESS  read-write
    STATUS  current
    DESCRIPTION
       "This variable indicates  the  variety  of T1/E1
        Line  implementing  this  circuit.  The type of
        circuit affects the number of bits  per  second
        that  the circuit can reasonably carry, as well
        as the interpretation of the  usage  and  error
        statistics.  The values, in sequence, describe:

       TITLE:        SPECIFICATION:
       esf       Extended SuperFrame DS1
       d4        AT&T D4 format DS1  - SF
       e1        CCITT Recommendation G.704
                 (Table 4a) - G732N
       e1Crc     CCITT Recommendation G.704
                 (Table 4b) - G732N with CRC
       e1MF      G.704 (Table 4a) with TS16
                 multiframing enabled - G732S
       e1CrcMF   G.704 (Table 4b) with TS16
                 multiframing enabled - G732S with CRC
       unframed  
     
       T1 - applicable values: (1),(2),(3),(8)
       E1 - applicable values: (1),(4),(5),(6),(7),(8) "
    ::= { prtT1E1CnfgEntry 4 }

prtT1E1LineCode OBJECT-TYPE
    SYNTAX  INTEGER {
                jbzs (1),
                b8zs (2),
                hdb3 (3),
                zbtsi(4),
                ami  (5),
                other(6)
            }
    MAX-ACCESS  read-write
    STATUS  current
    DESCRIPTION
       "This variable describes the  variety  of  Zero
       Code  Suppression  used  on  the link, which in
       turn affects a number of its characteristics.

       jbzs=b7zs refers the Jammed  Bit  Zero  Suppres-
       sion,  in  which  the  AT&T specification of at
       least one pulse every 8 bit periods is literal-
       ly  implemented  by forcing a pulse in bit 8 of
       each channel.  Thus, only seven bits per  chan-
       nel, or 1.344 Mbps, is available for data (used for T1).

       b8zs refers to the use of a specified pattern
       of  normal  bits  and  bipolar violations
       which are used to replace a sequence  of  eight
       zero bits (used for T1).

       ANSI Clear Channels may use zbtsi, or  Zero
       Byte Time Slot Interchange.

       E1 links, with or without CRC, use hdb3  or
       ami (= TRAN).

       amI (=TRAN) refers to a mode wherein no zero code
       suppression  is  present  and the line encoding
       does not solve the problem directly. In this
       application, the higher layer must provide data
       which meets or exceeds the  pulse  density  re-
       quirements, such as inverting HDLC data."
   ::= { prtT1E1CnfgEntry 5 }

prtT1E1SignalMode OBJECT-TYPE
    SYNTAX  INTEGER {
                none            (1),
                robbedBit       (2),
                bitOriented     (3),  --CAS
                messageOriented (4)   --CCS
            }
    MAX-ACCESS  read-write
    STATUS  current
    DESCRIPTION
       "'none' indicates that no bits are reserved for
               signaling on this channel.

        'robbedBit' indicates that T1 Robbed Bit Signaling is in use.

        'bitOriented' indicates that E1 Channel  Associated 
               Signaling (CAS) is in use.

        'messageOriented' indicates that Common  Channel Signaling 
               (CCS) is in use either on channel 16 of an E1 link or 
               channel 24 of a T1."
   ::= { prtT1E1CnfgEntry 6 }

prtT1E1Fdl OBJECT-TYPE
    SYNTAX  INTEGER {
                  other      (1),
                  ansi-T1-403(2),
                  att-54016  (4),
                  fdl-none   (8),
                  transFdl   (16)
            }
    MAX-ACCESS  read-write
    STATUS  current
    DESCRIPTION
       "This bitmap describes the use of  the  facili-
        ties data link, and is the sum of the capabili-
        ties:

        'other' indicates that a protocol  other  than
         one following is used.

        'ansi-T1-403' refers to the  FDL  exchange
         recommended by ANSI.

        'att-54016' refers to ESF FDL exchanges.

        'fdl-none' indicates that the device  does
         not use the FDL.
        'transFdl' indicates transition between two ports of 
         the same card. "
   ::= { prtT1E1CnfgEntry 7 }

prtT1E1FdlMode OBJECT-TYPE
    SYNTAX  INTEGER {
      other     (1),
      user      (2),
      carrier   (3),
      notApplicable (255)
            }
    MAX-ACCESS  read-write
    STATUS  current
    DESCRIPTION
    " Fdl Mode of the T1 selected port.
      notApplicable - will be used for an E1 port."
   ::= { prtT1E1CnfgEntry 8 }


prtT1E1Sync OBJECT-TYPE
    SYNTAX  INTEGER {
    other  (1),
    tr62411(2),
    ccitt  (3),
    fast   (4)                 
            }
    MAX-ACCESS  read-write
    STATUS  current
    DESCRIPTION
    "This object enables returning to normal operation, after 
     the end of a main/sub link red alarm event, in reduced time.
        'tr62411' - complies with AT&T TR-62411 (after 10 seconds).
              Applicable for both T1 and E1 interfaces.
    'ccitt'   - complies with CCITT standard. Applicable only
              for E1 interfaces.
    'fast'    - after 1 second."
    ::= { prtT1E1CnfgEntry 9 }

prtT1E1CGA OBJECT-TYPE
    SYNTAX  INTEGER {
      none (1),
      trans(2),
      full (3)                                   
            }
    MAX-ACCESS  read-write
    STATUS  current
    DESCRIPTION
    "This object selects the method used to signal the CGA state
     to the other end, through the main/sub link. 
     'none'  - non-transparent mode. When one of the links 
               (main/sub) will be in Out Of Service state, both 
               'Data/Voice Oos' and 'Oos Signal' will be 
               transmitted to the other end.
     'trans' - when one of the links (main/sub) will be in Out
               Of Service state, 'Data/Voice Oos' will be 
               transmitted to the other end.
     'full'  - fully-transparent mode. When one of the links 
                  (main/sub) will be in Out Of Service state, 
                  neither 'Data/Voice Oos' nor 'Oos Signal' will 
                  be transmitted to the other end."
    ::= { prtT1E1CnfgEntry 10 }

prtT1E1IdleCode OBJECT-TYPE
    SYNTAX  OCTET STRING (SIZE (0..4))
    MAX-ACCESS  read-write
    STATUS  current
    DESCRIPTION
    "This object selects the code transmitted to fill idle 
     (unused) time slots in the main link frame. 
     Valid range: (0 - FF HEX) ."
    ::= { prtT1E1CnfgEntry 11 }

prtT1E1OosSignal  OBJECT-TYPE
      SYNTAX  INTEGER
       {
        notsupported  (2),
        forcedIdle    (3),
        forcedBusy    (4),
        busyIdle      (5),
        idleBusy      (6)
       }
      MAX-ACCESS  read-write
      STATUS  current
      DESCRIPTION
      "'idle' = '0' = on-hook, idle state
       'busy' = '1' = off-hook, busy state
       'forcedIdle' = SP = both A and B signaling bits are forced
                      to '0' during out-of-service periods.
       'forcedBusy' = MK = both A and B signaling bits are forced
                      to '1' during out-of-service periods.
       'busyIdle'   = MK_SP = A and B bits are forced to '1' for
                      2.5 seconds; then they are switched to '0'
                      until out-of-service condition disappears.
       'idleBusy'   = SP_MK = A and B bits are forced to '0' for
                      2.5 seconds; then they are switched to '1'
                      until out-of-service condition disappears.
       - for T1:    '0'=0   ;  '1'=1                         
       - for E1:    '0'=1   ;  '1'=0   "
   ::= { prtT1E1CnfgEntry 12 }

prtT1E1VoiceOos  OBJECT-TYPE
    SYNTAX  OCTET STRING (SIZE (0..4))
    MAX-ACCESS  read-write
    STATUS  current
    DESCRIPTION
    "Voice Out-Of-Service code. Valid range: (0 - FF HEX).
     For agents that do not support this feature, the value will
     always be 0."
   ::= { prtT1E1CnfgEntry 13 }

prtT1E1DataOos  OBJECT-TYPE
    SYNTAX  OCTET STRING (SIZE (0..4))
    MAX-ACCESS  read-write
    STATUS  current
    DESCRIPTION
    "Data Out-Of-Service code. Valid range: (0 - FF HEX).
     For agents that do not support this feature, the value will
     always be 0."
   ::= { prtT1E1CnfgEntry 14 }

prtT1E1LineLengthMask  OBJECT-TYPE
      SYNTAX  INTEGER
       {
        unknown      (1),
        len0p133ft   (2),
        len134p266ft (3),
        len267p399ft (4),
        len400p533ft (5),
        len534p655ft (6),
        fcc68        (7)
       }
      MAX-ACCESS  read-write
      STATUS  current
      DESCRIPTION
      "This attribute is the line length mask parameter used only 
       for T1/DSU interfaces.
       len400p533ft=length range: 400ft to 533ft 
       'fcc68' - provides compliance with the FCC 68.308 Option A
                 output pulse mask. "
      ::= { prtT1E1CnfgEntry 15 }

prtT1E1TxGainMask  OBJECT-TYPE
      SYNTAX  INTEGER
       {
          notApplicable     (1),
          txGain0db         (2),
          txGain7dot5db     (3),
          txGain15db        (4),
          txGain22dot5db    (5)
       }
      MAX-ACCESS  read-write
      STATUS  current
      DESCRIPTION
      "This attribute is the tx gain mask parameter (dB), used 
       only for T1/CSU interfaces."
   ::= { prtT1E1CnfgEntry 16 }

prtT1E1InbandMng  OBJECT-TYPE
      SYNTAX  INTEGER
       {
          off         (2),
          fdlOrTs0    (3),
          dedicatedTs (4),
          dedicatedPpp(5),
          dedicatedFr (6),
          internal    (7)
       }
      MAX-ACCESS  read-write
      STATUS  current
      DESCRIPTION
      "A unique number to identify an Inband management over the 
       link.
       internal - supported by KM-2100 only. It means that the management is internal
                  to the frame. It takes part of the ML Frame bits (instead of data)."
      ::= {prtT1E1CnfgEntry 17}

prtT1E1InbandMngRate  OBJECT-TYPE
      SYNTAX  INTEGER
       {
          notApplicable(1),
          r4k   (2),
          r8k   (3),
          r12k  (4),
          r16k  (5),
          r32k  (6),
          r64k  (7),
          r20k  (8)
       }
      MAX-ACCESS  read-write
      STATUS  current
      DESCRIPTION
      "A unique number to identify the rate of the Inband management.
       It is required only for E1 links and is applicable only when 
       prtExT1E1InbandMng selected is FdlOrTs0 or dedicatedTs."
      ::= {prtT1E1CnfgEntry 18}

prtT1E1DedicatedTs  OBJECT-TYPE
      SYNTAX  Integer32
      MAX-ACCESS  read-write
      STATUS  current
      DESCRIPTION

      "The value is differently determined for different products.
       There are two methods:

       1) A unique number to identify Dedicated TS of the T1/E1 port.
          It is applicable only when prtExT1E1InbandMng selected is 
          dedicatedTs.
          1..24 - Dedicated TS of T1
          1..31 - Dedicated TS of E1
          255   - notApplicable (for agents that do not support this 
                  feature)
          Other values are invalid.

       2) For FCD-STM,  up to five TSs may be dedicated to management.
          This object value is the Sum (sigma) of 2**n, where n =TS-1
          e.g. 	  Time slots 3,5,7,9,11 are dedicated to management:
            	   2** 2
          		  +2** 4
          		  +2** 6 
          		  +2** 8
          		  +2**10  = 4+16+64+256+1024=1364 
       
       User should consult the product specification, to find out 
       the method employed."
	   ::= {prtT1E1CnfgEntry 19}

prtT1E1InbandMngRoutProt  OBJECT-TYPE
      SYNTAX  INTEGER
       {
       notApplicable (1),
       none          (2),  
       proprietary   (3),
       rip2          (4)
       }
      MAX-ACCESS  read-write
      STATUS  current
      DESCRIPTION
      "Inband Mng Routing Protocol of the port.
       When prtT1E1InbandMng is 'dedicatedPpp'-'proprietary' and
                                               'rip2' are applicable.
       For other values  - only 'proprietary' is applicable.
       
       For FCD-M and FCD-A:
       When prtT1E1InbandMng is 'dedicatedPpp' or 'dedicatedFr':
                             'None', 'proprietary' and 'rip2' are applicable.
       When prtT1E1InbandMng is 'fdlOrTS0' or 'dedicatedTs':
                             'None' and 'proprietary' are applicable.
       When prtT1E1InbandMng is 'off':
                             'None' is applicable."             
      ::= {prtT1E1CnfgEntry 20}

prtT1E1LinkMode  OBJECT-TYPE
      SYNTAX  INTEGER
       {
       notApplicable (1),
       regular       (2),  
       transparent   (3)
       }
      MAX-ACCESS  read-write
      STATUS  current
      DESCRIPTION
      "regular - TSs are connected by user via TS Assignment only
       transparent - when a port with this Link Mode is connected to an 
                     internal T1/E1 port of a T3/E3 card, TS0, TS16 and Fbit
                     are transparently transferred to the E3/T3 stream."             
      ::= {prtT1E1CnfgEntry 21}

prtT1E1Multiplier OBJECT-TYPE
      SYNTAX  INTEGER { 
      notApplicable (1), 
      br56 (2),
      br64 (3)
      }
      MAX-ACCESS  read-write
      STATUS  current
      DESCRIPTION
      "The data rate of each TS. The multiplier values
       can be 56 kbps or 64 kbps. For T1 only."
      ::= { prtT1E1CnfgEntry 22 }

prtT1E1RxGain OBJECT-TYPE
      SYNTAX  INTEGER
       {
       notApplicable  (1),
       rxGain12dB     (2),
       rxGain30dB     (3),
       rxGain36dB     (4),
	   shortHaul      (5),
	   longHaul       (6)
       }
      MAX-ACCESS  read-write
      STATUS  current
      DESCRIPTION
      "This attribute is the rx volume (dB)."
   ::= { prtT1E1CnfgEntry 23 }

 prtT1E1RAI  OBJECT-TYPE
      SYNTAX  INTEGER
       {
        notApplicable  (1),
        off (2),
        on  (3)
       }
      MAX-ACCESS  read-write
      STATUS  current
      DESCRIPTION
      "Remote Alarm Signal"
   ::= { prtT1E1CnfgEntry 24 }

prtT1E1LineMode OBJECT-TYPE
      SYNTAX  INTEGER 
       {
        notApplicable	(1), 
        csu				(2),
        dsu				(3),
		ltu				(4)
       }
        MAX-ACCESS  read-write
        STATUS  current
        DESCRIPTION
      "Interface type of the port.
       For T1 - csu, dsu are the valid values
       For E1 - dsu, ltu are the valid values"
   ::= { prtT1E1CnfgEntry 25 }

prtT1E1TS0SaBits OBJECT-TYPE
    SYNTAX  OCTET STRING 
    MAX-ACCESS  read-write
    STATUS  current
    DESCRIPTION
    "This object is applicable only for E1 ports. For T1, string size will be 0.
     For E1, it enables user to select the use of TS0 Sa Bits 4..8, by 3 octets:
	 The order (in hexa display):
	 free Sa-Bit-4  Sa-Bit-5  Sa-Bit-6  Sa-Bit-7  Sa-Bit-8
	 |___________|  |________________|  |________________|
	     MSByte                                 LSByte
	     
	 Each Sa Bit will be represented by a nibble, having the following meaning:
	 0000 = zero
	 0001 = one
	 0010 = management
	 0011 = transparent
	 the rest are reserved for future use."      
   ::= { prtT1E1CnfgEntry 26 }

prtT1E1ConnectedTS OBJECT-TYPE
      SYNTAX  INTEGER 
       {
        notApplicable	(1), 
        no				(2),
        yes				(3)
       }
        MAX-ACCESS  read-only
        STATUS  current
        DESCRIPTION
      "This parameter indicates if there is any connected TS for this interface."
   ::= { prtT1E1CnfgEntry 27 }

prtT1E1Ts0SaBit OBJECT-TYPE
      SYNTAX  INTEGER 
       {
        notApplicable	(1), 
        noMng	(2),
        mng		(3)
       }
        MAX-ACCESS  read-write
        STATUS  current
        DESCRIPTION
      "This parameter indicates whether to send TS 0, or not.
       noMng= TS 0 is looped, therefore not sent.
       mng= TS 0 isn't looped, therefore it is sent."
   ::= { prtT1E1CnfgEntry 28 }
	   
prtT1E1SameFeCnfg OBJECT-TYPE
      SYNTAX  INTEGER 
       {
        notApplicable	(1), 
        no              (2),
        yes             (3)
       }
      MAX-ACCESS  read-write
      STATUS  current
      DESCRIPTION
      "This parameter indicates whether the same E1 configuration 
       parameters and TS assignment are set both to the local
       and remote device.
       Read-Write access is applicable only in G732N framed mode.
       For G732S and UNFRAMED this parameter is set by 
       agent to YES and is Read Only.
       In Case of conflict during power-up between the central 
       and remote, the value set by the central unit is the valid one."
      ::= { prtT1E1CnfgEntry 29 }

prtT1E1RemCrc4 OBJECT-TYPE
      SYNTAX  INTEGER 
       {
        notApplicable	(1), 
        no              (2),
        yes             (3)
       }
      MAX-ACCESS  read-write
      STATUS  current
      DESCRIPTION
      "This object indicates whether the E1 of the Remote device
       connected to this E1 port, will have CRC-4 or not."
      ::= { prtT1E1CnfgEntry 30 }

prtT1E1MaxTSs OBJECT-TYPE
      SYNTAX  Integer32 
      MAX-ACCESS  read-write
      STATUS  current
      DESCRIPTION
      "This object is applicable only for DXC D4T1, D4E1, D8T1, D8E1 
       external ports and D8GSL internal E1 ports.
	   It is relevant only when sysCIntTsAllocMode=static(2).
       255=not applicable
       If prtT1E1LineType=unframed(8), the value of this object must be 32.
       Else, the valid values are 0..31."
      ::= { prtT1E1CnfgEntry 31}

prtT1E1EocTsConfig OBJECT-TYPE
      SYNTAX  INTEGER 
       {
        notApplicable (1), 
        disabled      (2),
        enabled       (3)
       }
      MAX-ACCESS  read-write
      STATUS  current
      DESCRIPTION
      "This object indicates whether the use of EOC for TS Configuration
       is enabled or not."
      ::= { prtT1E1CnfgEntry 32 }



--prtT1E1 Last FDL Message Table - Statistics

prtT1E1FdlMsgTable  OBJECT-TYPE
     SYNTAX SEQUENCE OF PrtT1E1FdlMsgEntry
     MAX-ACCESS not-accessible
     STATUS  current
     DESCRIPTION
      "This table is applicable for a T1 interface with 'esf'
       LineType or E1 interface, when CRC is enabled (LineType)."
  ::= { prtT1E1 3}

prtT1E1FdlMsgEntry OBJECT-TYPE
      SYNTAX PrtT1E1FdlMsgEntry
      MAX-ACCESS not-accessible
      STATUS current
	DESCRIPTION  "An entry in table."
	INDEX {prtT1E1FdlMsgPrtIdx, prtT1E1FdlMsgFdlType}
      ::= { prtT1E1FdlMsgTable 1}

PrtT1E1FdlMsgEntry ::=
      SEQUENCE {
      prtT1E1FdlMsgPrtIdx    Integer32,
      prtT1E1FdlMsgFdlType   INTEGER,
      prtT1E1FdlMsgSlt       INTEGER,
      prtT1E1FdlMsg          OCTET STRING   
      }

prtT1E1FdlMsgPrtIdx OBJECT-TYPE
      SYNTAX  Integer32
      MAX-ACCESS  read-only
      STATUS  current
      DESCRIPTION
      "This attribute indicates a unique  port number.
    The same numbering as for prtGenPrtIdx.
       The valid port number depends on the IO slot no.,  the 
       installed card type and the port type: outside, inside. 
      * The outside ports will be the T1/E1 cards ports. 
        The convention used will be (for DXC):
      - first two digits will be: (IO slot number+10)
         - last one/two digits will be the port number within the 
           card, in odd numbers:
     port1 = 1
     port2 = 3
     port3 = 5 
     etc...
   Example: port2 of IO slot 11 will be: 213 ."
      ::= { prtT1E1FdlMsgEntry 1}

prtT1E1FdlMsgFdlType OBJECT-TYPE
      SYNTAX  INTEGER
       {
          send    (1),
    receive (2)
    }
      MAX-ACCESS  read-only
      STATUS  current
      DESCRIPTION
   "The Fdl type reference of the Fdl message."
      ::= { prtT1E1FdlMsgEntry 2}

prtT1E1FdlMsgSlt    OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       io13 (17),
       io14 (18),
       io15 (19),
       standAlone (255)
      }
      MAX-ACCESS  read-only
      STATUS  current
      DESCRIPTION
      "This attribute indicates a unique number to identify the slot where
       the card is inserted in.
       When the unit is stand-alone, this object is not applicable
       and 255 will be used."
      ::= { prtT1E1FdlMsgEntry 3}

prtT1E1FdlMsg  OBJECT-TYPE
   SYNTAX  OCTET STRING
      MAX-ACCESS  read-only
      STATUS  current
      DESCRIPTION
      "FDL message."
      ::= { prtT1E1FdlMsgEntry 4}


--prtHS specific parameters (configuration & status) table

prtHSParamTable  OBJECT-TYPE
      SYNTAX SEQUENCE OF PrtHSParamEntry
      MAX-ACCESS not-accessible
      STATUS current
	DESCRIPTION  "A table."
	::=  { prtHS 1 }

prtHSParamEntry OBJECT-TYPE
      SYNTAX PrtHSParamEntry
      MAX-ACCESS not-accessible
      STATUS current
	DESCRIPTION  "An entry in table."
	INDEX { prtHSCnfgIdx, prtHSPrtIdx }
      ::= { prtHSParamTable 1}

PrtHSParamEntry ::=
      SEQUENCE {
      prtHSCnfgIdx               Integer32,
      prtHSPrtIdx                Integer32,
      prtHSSlt                   INTEGER,
      prtHSRate                  INTEGER,
      prtHSFifoSize              INTEGER,
      prtHSClkMode               INTEGER,
      prtHSCTS                   INTEGER,
      prtHSRtsState              INTEGER,
      prtHSInbandLoopback        INTEGER,
	  prtHSInbandLoopPatternCfg	 INTEGER,
	  prtHSInbandLoopActPattern  DisplayString,
	  prtHSInbandLoopDeactPattern DisplayString,
	  prtHSDCD			 INTEGER 
   }    
   
prtHSCnfgIdx OBJECT-TYPE
      SYNTAX  Integer32 (1..255)
      MAX-ACCESS  read-only
      STATUS  current
      DESCRIPTION
      "This attribute indicates the Idx of the Config being accessed.
       Idx of 255 relates to the Temporary (Scratch) Config. "
      ::= { prtHSParamEntry 1}

prtHSPrtIdx OBJECT-TYPE
      SYNTAX  Integer32
      MAX-ACCESS  read-only
      STATUS  current
      DESCRIPTION
      "This attribute indicates a unique number to identify a port. 
       The valid port number depends on the IO slot no.,  the 
       installed card type and the port type: outside, inside, 
       SP.
    * The inside ports will be the HS cards ports. The 
      convention used will be (for DXC):
      - first two digits will be: (IO slot number+10)
         - last one/two digits will be the port number within the 
           card, in even numbers:
     port1 = 2
     port2 = 4
     port3 = 6 
     etc...
   Example: port2 of IO slot 11 will be: 214 ."
      ::= { prtHSParamEntry 2}

prtHSSlt      OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       io13 (17),
       io14 (18),
       io15 (19),
       standAlone (255)
       }
      MAX-ACCESS  read-only
      STATUS  current
      DESCRIPTION
      "This attribute indicates a unique number to identify the slot where
       the card is inserted in.
       When the unit is stand-alone, this object is not applicable
       and 255 will be used."
      ::= { prtHSParamEntry 3}

prtHSRate     OBJECT-TYPE
      SYNTAX  INTEGER {
        r0x56eq0Kbps     (1),
        r1x56eq56Kbps    (2),
        r2x56eq112Kbps   (3),
        r3x56eq168Kbps   (4),
        r4x56eq224Kbps   (5),
        r5x56eq280Kbps   (6),
        r6x56eq336Kbps   (7),
        r7x56eq392Kbps   (8),
        r8x56eq448Kbps   (9),
        r9x56eq504Kbps  (10),
        r10x56eq560Kbps (11),
        r11x56eq616Kbps (12),
        r12x56eq672Kbps (13),
        r13x56eq728Kbps (14),
        r14x56eq784Kbps (15),
        r15x56eq840Kbps (16),
        r16x56eq896Kbps (17),
        r17x56eq952Kbps (18),
        r18x56eq1008Kbps(19),
        r19x56eq1064Kbps(20),
        r20x56eq1120Kbps(21),
        r21x56eq1176Kbps(22),
        r22x56eq1232Kbps(23),
        r23x56eq1288Kbps(24),
        r24x56eq1344Kbps(25),
        r25x56eq1400Kbps(26),
        r26x56eq1456Kbps(27),
        r27x56eq1512Kbps(28),
        r28x56eq1568Kbps(29),
        r29x56eq1624Kbps(30),
        r30x56eq1680Kbps(31),
        r31x56eq1736Kbps(32),
        r0x64eq0Kbps    (33),
        r1x64eq64Kbps   (34),
        r2x64eq128Kbps  (35),
        r3x64eq192Kbps  (36),
        r4x64eq256Kbps  (37),
        r5x64eq320Kbps  (38),
        r6x64eq384Kbps  (39),
        r7x64eq448Kbps  (40),
        r8x64eq512Kbps  (41),
        r9x64eq576Kbps  (42),
        r10x64eq640Kbps (43),
        r11x64eq704Kbps (44),
        r12x64eq768Kbps (45),
        r13x64eq832Kbps (46),
        r14x64eq896Kbps (47),
        r15x64eq960Kbps (48),
        r16x64eq1024Kbps(49),
        r17x64eq1088Kbps(50),
        r18x64eq1152Kbps(51),
        r19x64eq1216Kbps(52),
        r20x64eq1280Kbps(53),
        r21x64eq1344Kbps(54),
        r22x64eq1408Kbps(55),
        r23x64eq1472Kbps(56),
        r24x64eq1536Kbps(57),
        r25x64eq1600Kbps(58),
        r26x64eq1664Kbps(59),
        r27x64eq1728Kbps(60),
        r28x64eq1792Kbps(61),
        r29x64eq1856Kbps(62),
        r30x64eq1920Kbps(63),
        r31x64eq1984Kbps(64),
        r32x64eq2048Kbps(65),

        r32x56eq1792Kbps(66),
        r64x64eq4096Kbps(67),

        auto           (200)
     }
      MAX-ACCESS  read-write
      STATUS  current
      DESCRIPTION
      "This object indicates the port rate (speed).
       auto - rate is selected automatically by system."
      ::= { prtHSParamEntry 4}

prtHSFifoSize OBJECT-TYPE
      SYNTAX  INTEGER {
   auto    (1),
   b32bit  (2),
   b60bit  (3),
   b104bit (4),
   b144bit (5),
   notApplicable (255)
   }
      MAX-ACCESS  read-write
      STATUS  current
      DESCRIPTION
   "This object selects the size of the user data channel buffer
    FIFO used in the DTE2 mode. In the other modes, buffer 
    size is automatically set by the DACS agent. 
    Buffer FIFO size in bits, corresponds to FIFO lengths of 
    +/-16, +/-30, +/-52, +/-72 bits."
      ::= { prtHSParamEntry 5}

prtHSClkMode OBJECT-TYPE
      SYNTAX  INTEGER {
   dce   (1),
   dte1  (2),
   dte2  (3),
   notApplicable (255)
   }
      MAX-ACCESS  read-write
      STATUS  current
      DESCRIPTION
   "Clock Mode of the user data channel. 
    dce - DACS operates as a DCE and provides transmit 
          and receive clocks to the synchronous user DTE.
    dte1- DACS supplies the receive clock to the user 
          equipment and accepts the user transmit clock.
    dte2- DACS requires transmit and receive clocks from 
          the user equipment."
      ::= { prtHSParamEntry 6}

prtHSCTS OBJECT-TYPE
      SYNTAX  INTEGER {
   on   (1),
   rts  (2),
   notApplicable (255)
   }
      MAX-ACCESS  read-write
      STATUS  current
      DESCRIPTION
    "Selection of CTS line state in the user data channel.
     on  - CTS continuously ON.
     rts - CTS line follows the RTS line."
      ::= { prtHSParamEntry 7}

prtHSRtsState OBJECT-TYPE
      SYNTAX  INTEGER {
   off   (2),
   on    (3),
   notApplicable (255)
   }
      MAX-ACCESS  read-only
      STATUS  current
      DESCRIPTION
      "RTS state of the port." 
      ::= { prtHSParamEntry 8}

prtHSInbandLoopback OBJECT-TYPE
      SYNTAX  INTEGER
       {
       notApplicable   (1),
       disabled        (2),
       enabled         (3)
       }
      MAX-ACCESS  read-write
      STATUS  current
      DESCRIPTION
      "This object indicates if Inband Loopback from the Network
       should be enabled or disabled."
      ::= {prtHSParamEntry 9}

prtHSInbandLoopPatternCfg OBJECT-TYPE
      SYNTAX  INTEGER
       {
       notApplicable   (1),
       rdlLoop         (2),
       userConfig      (3)
       }
      MAX-ACCESS  read-write
      STATUS  current
      DESCRIPTION
      "This object indicates if Inband Loop polynomial pattern
       will be according to RDL Loop (the standard) or User Configurated
       according to prtHSActivatePolyPattern and prtHSDeactivatePolyPattern."
      ::= {prtHSParamEntry 10}

prtHSInbandLoopActPattern OBJECT-TYPE
      SYNTAX DisplayString
      MAX-ACCESS read-write
      STATUS current
      DESCRIPTION
      "This object is a binary string of up to 8 bits.
	   Though the syntax allows for any ASCII characters, for this object
	   only '0' or '1' characters are valid.
       The string determines coefficients of the polynomial pattern
       sent to the port in order to Activate the Inband Loop.
       This object is relevant only when prtHSInbandLoopPatternCfg=userConfig."
      ::= {prtHSParamEntry 11}

prtHSInbandLoopDeactPattern OBJECT-TYPE
      SYNTAX DisplayString
      MAX-ACCESS read-write
      STATUS current
      DESCRIPTION
      "This object is a binary string of up to 8 bits.
	   Though the syntax allows for any ASCII characters, for this object
	   only '0' or '1' characters are valid.
       The string determines coefficients of the polynomial pattern
       sent to the port in order to Deactivate the Inband Loop.
       This object is relevant only when prtHSInbandLoopPatternCfg=userConfig."
      ::= {prtHSParamEntry 12}

prtHSDCD OBJECT-TYPE
      SYNTAX  INTEGER {
      notApplicable (1),
      linkOK  (2),
      on   (3)
      }
      MAX-ACCESS  read-write
      STATUS  current
      DESCRIPTION
      "Selection of DCD line state in the user data channel.
       linkOK - DCD line is ON only when active link is OK.
       on  - DCD continuously ON."
      ::= { prtHSParamEntry 13}



prtHSBertTable  OBJECT-TYPE
      SYNTAX SEQUENCE OF PrtHSBertEntry
      MAX-ACCESS not-accessible
      STATUS current
	DESCRIPTION  "A table."
	::=  { prtHS 2 }

prtHSBertEntry OBJECT-TYPE
      SYNTAX PrtHSBertEntry
      MAX-ACCESS not-accessible
      STATUS current
	DESCRIPTION  "An entry in table."
	INDEX { prtHSBertPrtIdx }
      ::= { prtHSBertTable 1}

PrtHSBertEntry ::=
     SEQUENCE {
  prtHSBertPrtIdx        Integer32,
  prtHSBertSlt           INTEGER,
  prtHSBertCountClr      INTEGER,
  prtHSBertTestResult    Integer32 
	}

prtHSBertPrtIdx OBJECT-TYPE
      SYNTAX  Integer32
      MAX-ACCESS  read-only
      STATUS  current
      DESCRIPTION
      "This attribute indicates a unique number to identify a port. 
       The valid port number depends on the IO slot no.,  the 
       installed card type and the port type: outside, inside, 
       SP.
    * The inside ports will be the HS cards ports. The 
      convention used will be (for DXC):
      - first two digits will be: (IO slot number+10)
         - last one/two digits will be the port number within the 
           card, in even numbers:
     port1 = 2
     port2 = 4
     port3 = 6 
     etc...
   Example: port2 of IO slot 11 will be: 214 ."
      ::= { prtHSBertEntry 1}

prtHSBertSlt  OBJECT-TYPE
      SYNTAX  INTEGER
       {
       io1   (5),
       io2   (6),
       io3   (7),
       io4   (8),
       io5   (9),
       io6  (10),
       io7  (11),
       io8  (12),
       io9  (13),
       io10 (14),
       io11 (15),
       io12 (16),
       io13 (17),
       io14 (18),
       io15 (19),
       standAlone (255)
       }
      MAX-ACCESS  read-only
      STATUS  current
      DESCRIPTION
      "This attribute indicates a unique number to identify the slot where
       the card is inserted in.
       When the unit is stand-alone, this object is not applicable
       and 255 will be used."
      ::= { prtHSBertEntry 2}


prtHSBertCountClr OBJECT-TYPE
      SYNTAX  INTEGER {
     off(2),
     on (3)
      }
      MAX-ACCESS  read-write
      STATUS  current
      DESCRIPTION
      "Setting this object (to on) initiate bert counter clear 
       operation.
       Valid only when bert test is active on the specific port.
       (Every time a new bert test starts, the counter is 
       automatically cleared; this command enables clearing 
       the counter while the test is running)."
      ::= { prtHSBertEntry 3}

prtHSBertTestResult   OBJECT-TYPE
      SYNTAX  Integer32
      MAX-ACCESS  read-only
      STATUS  current
      DESCRIPTION
      "This object indicates the number of Bit Error Rate indicated 
       during the BERT test.
       Active only when bert test is running on the selected port."
      ::= { prtHSBertEntry 4}



--prt SP specific configuration parameters

prtSpCnfgTable OBJECT-TYPE
      SYNTAX SEQUENCE OF PrtSpCnfgEntry
      MAX-ACCESS not-accessible
      STATUS current
	DESCRIPTION  "A table."
	::=  {prtSP 1}

prtSpCnfgEntry OBJECT-TYPE
      SYNTAX PrtSpCnfgEntry
      MAX-ACCESS not-accessible
      STATUS current
      DESCRIPTION
      "All the entries at this table are identical(have the same value)
       at all the configurations(1..255) except at the TmpCnfg.
       - For products supporting more than one configuration, the write operation 
         into the Table Objects is valid only at the TmpCnfg entry.
       - For products that do not support configurations, the write operation 
         into the Table Objects will be to prtSpCnfgIdx=1."
      INDEX {prtSpCnfgIdx, prtSpPrtIdx }
      ::= { prtSpCnfgTable 1}

PrtSpCnfgEntry ::=
      SEQUENCE {
   prtSpCnfgIdx     Integer32,
   prtSpPrtIdx      Integer32,
   prtSpUsage       INTEGER,
   prtSpRate        INTEGER,
   prtSpDataBits    INTEGER,
   prtSpParity      INTEGER,
   prtSpCallOutMode INTEGER,
   prtSpInterface   INTEGER,
   prtSpCTS         INTEGER,
   prtSpDcdDelay    INTEGER,
   prtSpDsr         INTEGER,
   prtSpNoOfRetries Integer32,
   prtSpWaitForConnect INTEGER,
   prtSpDialMode    INTEGER,
   prtSpAltNumMode  INTEGER,
   prtSpPrimaryNum  DisplayString,
   prtSpAltNum      DisplayString,
   prtSpRoutProtocol INTEGER,
   prtSpCmd          OCTET STRING,
   prtSpActCallOut   INTEGER,
   prtSpAlrRelayMode INTEGER,
   prtSpStopBits     INTEGER
      }      
       

prtSpCnfgIdx OBJECT-TYPE
      SYNTAX  Integer32 (1..255)
      MAX-ACCESS  read-only
      STATUS  current
      DESCRIPTION
      "This attribute indicates the Idx of the Cnfg(1..255) being 
       accessed.
       Idx of 255 relates to the TmpCnfg."
      ::= { prtSpCnfgEntry 1}

prtSpPrtIdx OBJECT-TYPE
      SYNTAX  Integer32
      MAX-ACCESS  read-only
      STATUS  current
      DESCRIPTION
      "This attribute indicates a unique port number of the SPor DP port.
       For DXC, it is the port in the active DCL card: 
       - SP = 1
       - NP ; DP = 2 
                
       For Kilomux, the port index is calculated as follows:
       100*Slot+Ch.
       
       For FCD, PRBi,  the SP port index=1.
       For Optimux-T3, the SP port index=71."
      ::= { prtSpCnfgEntry 2}

prtSpUsage OBJECT-TYPE
      SYNTAX  INTEGER
       {
  unknown (1),
  noUse   (2),
  nmsSlip (3),
  nmsPpp  (4),
  muxSlip (5),
  muxPpp  (6),
  terminal(7),
  dialOut (8)
       }
      MAX-ACCESS  read-write
      STATUS  current
      DESCRIPTION
      "This attribute indicates what is the usage of the port."
      ::= { prtSpCnfgEntry 3}

prtSpRate     OBJECT-TYPE
      SYNTAX  INTEGER
       {
        auto      (1),
        s300bps   (2),
        s1200bps  (3),
        s2400bps  (4),
        s4800bps  (5),
        s9600bps  (6),
        s19200bps (7),
        s38400bps (8),
        s57600bps (9),
		s115200bps(10)
       }
      MAX-ACCESS  read-write
      STATUS  current
      DESCRIPTION
      "This attribute indicates the operation rate (speed) of the port.
       auto - automatic rate selection, by the agent."
      ::= { prtSpCnfgEntry 4}

prtSpDataBits OBJECT-TYPE
      SYNTAX  INTEGER
       {
        dataBits7 (1),
        dataBits8 (2)
       }
      MAX-ACCESS  read-write
      STATUS  current
      DESCRIPTION
      "This attribute indicates the number of data bits in async 
       frame"
      ::= { prtSpCnfgEntry 5}

prtSpParity OBJECT-TYPE
      SYNTAX  INTEGER
       {
        none  (1),
        odd   (2),
        even  (3)
       }
      MAX-ACCESS  read-write
      STATUS  current
      DESCRIPTION
      "This attribute indicates the parity mode in async frame"
      ::= { prtSpCnfgEntry 6}

prtSpCallOutMode OBJECT-TYPE
      SYNTAX  INTEGER
       {
        notApplicable  (1),
        none           (2),
        all            (3),
        major          (4)
       }
      MAX-ACCESS  read-write
      STATUS  current
      DESCRIPTION
      "This attribute indicates the call-out mode.
       For DXC - this object is applicable only for the DP port (2)."
      ::= { prtSpCnfgEntry 7}


prtSpInterface OBJECT-TYPE
      SYNTAX  INTEGER
       {
          dce  (1),
          dte  (2)
       }
      MAX-ACCESS  read-write
      STATUS  current
      DESCRIPTION
      "This attribute indicates the supervisory port interface.
       dce - the DACS appears as a DCE for the port.
       dte - the DACS operates as a DTE, for connection via modem,
             for the port."
      ::= { prtSpCnfgEntry 8}

prtSpCTS OBJECT-TYPE
      SYNTAX  INTEGER
       {
          notApplicable (1),
          on            (2),
          rts           (3)
       }
      MAX-ACCESS  read-write
      STATUS  current
      DESCRIPTION
   "CTS line state. This object is applicable only for 
    port (1) = SP"
      ::= { prtSpCnfgEntry 9}

prtSpDcdDelay OBJECT-TYPE
      SYNTAX  INTEGER
       {
          notApplicable (1),
          d0   (2),
          d10  (3),
          d50  (4),
          d100 (5),
          d200 (6),
          d300 (7)
       }
      MAX-ACCESS  read-write
      STATUS  current
      DESCRIPTION
   "DCD delay in msec. 
    d10 = delay of 10msec.
    This object is applicable only for  port (1) = SP"
      ::= { prtSpCnfgEntry 10}

prtSpDsr OBJECT-TYPE
      SYNTAX  INTEGER
       {
          notApplicable (1),
          on   (2),
          dtr  (3)
       }
      MAX-ACCESS  read-write
      STATUS  current
      DESCRIPTION
   "DSR line state. This object is applicable only for 
    port (1) = SP"
      ::= { prtSpCnfgEntry 11}

prtSpNoOfRetries OBJECT-TYPE
      SYNTAX  Integer32  (0..8)
      MAX-ACCESS  read-write
      STATUS  current
      DESCRIPTION
   "For DXC - this object is applicable only for port (2) = DP.
    The number of dialing retries requested.
    Default = 0"
      ::= { prtSpCnfgEntry 12}

prtSpWaitForConnect OBJECT-TYPE
      SYNTAX  INTEGER
       {
          notApplicable (1),
          t30sec        (2),
          t45sec        (3), 
          t60sec        (4)
       }
      MAX-ACCESS  read-write
      STATUS  current
      DESCRIPTION
   "For DXC - this object is applicable only for port (2) = DP.
    Waiting time for connect, in seconds.
    Default = 30 sec."
      ::= { prtSpCnfgEntry 13}

prtSpDialMode OBJECT-TYPE
      SYNTAX  INTEGER
       {
          notApplicable (1),
          tone          (2),
          pulse         (3)
    }
      MAX-ACCESS  read-write
      STATUS  current
      DESCRIPTION
   "For DXC - this object is applicable only for port (2) = DP.
    Dialing mode.
    Default=tone"
      ::= { prtSpCnfgEntry 14}

prtSpAltNumMode OBJECT-TYPE
      SYNTAX  INTEGER
       {
          no  (2),
          yes (3)
       }
      MAX-ACCESS  read-write
      STATUS  current
      DESCRIPTION
   "For DXC - this object is applicable only for port (2) = DP.
    It determines wether to use the alternate number or not.
    Default = no."
      ::= { prtSpCnfgEntry 15}

prtSpPrimaryNum OBJECT-TYPE
      SYNTAX  DisplayString (SIZE(0..20))
      MAX-ACCESS  read-write
      STATUS  current
      DESCRIPTION
   "For DXC - this object is applicable only for port (2) = DP.
    It is the Primary dialing number. "
      ::= { prtSpCnfgEntry 16}

prtSpAltNum OBJECT-TYPE
      SYNTAX  DisplayString (SIZE(0..20))
      MAX-ACCESS  read-write
      STATUS  current
      DESCRIPTION
   "For DXC - this object is applicable only for port (2) = DP.
    It is the Alternate dialing number. This number 
    is applicable only if prtSpAltNumMode is 'yes'."
      ::= { prtSpCnfgEntry 17}

prtSpRoutProtocol     OBJECT-TYPE
      SYNTAX  INTEGER
       {
        notApplicable (1),
        none          (2),
        proprietary   (3),
        rip2          (4)
       }
      MAX-ACCESS  read-write
      STATUS  current
      DESCRIPTION
      "This attribute indicates the routing protocol of the port.
       notApplicable - for DP."
      ::= { prtSpCnfgEntry 18}

prtSpCmd     OBJECT-TYPE
      SYNTAX OCTET STRING  (SIZE (20))
      MAX-ACCESS  read-write
      STATUS  current
      DESCRIPTION
      "SP Command.
      For LRS this parameter will be used for a Modem Command. 
      Upon NMS's Get operation for devices that this parameter 
      is notApplicable, agent will send NULL string."
      ::= { prtSpCnfgEntry 19}

prtSpActCallOut     OBJECT-TYPE
      SYNTAX  INTEGER
       {
        notApplicable (1),
        always        (2),
        linkFail      (3)
       }
      MAX-ACCESS  read-write
      STATUS  current
      DESCRIPTION
      "This object indicates when to Activate Call-Out.
	   It is used by FCD-T1/E1.
       always - to activate call-out always.
       linkFail - to activate call-out only when Link of Inband Management fails."
      ::= { prtSpCnfgEntry 20}


prtSpAlrRelayMode OBJECT-TYPE
      SYNTAX  INTEGER
       {
  	    notApplicable (1),	
  		normal        (2),
        invert        (3)
       }
      MAX-ACCESS  read-write
      STATUS  current
      DESCRIPTION
      "This attribute indicates the Alarm Relay Mode.
       notApplicable - for DP."
      ::= { prtSpCnfgEntry 21}


prtSpStopBits OBJECT-TYPE
      SYNTAX  INTEGER
	      {
		notApplicable  (1),
        stopBits1      (2),
        stopBits1dot5  (3),
        stopBits2      (4)
	      }
      MAX-ACCESS  read-write
      STATUS  current
      DESCRIPTION
      "This attribute indicates number of stop bits in an async frame."
      ::= { prtSpCnfgEntry 22}





--prt DIM (DXC Inverse Multiplexer) specific parameters

prtDimCnfgTable OBJECT-TYPE
      SYNTAX SEQUENCE OF PrtDimCnfgEntry
      MAX-ACCESS not-accessible
      STATUS current
	DESCRIPTION  "A table."
	::=  {prtDim 1}

prtDimCnfgEntry OBJECT-TYPE
      SYNTAX PrtDimCnfgEntry
      MAX-ACCESS not-accessible
      STATUS current
      DESCRIPTION
      "The write operation into the Table Objects is valid only
       for the TmpCnfg entry (prtDimCnfgIdx=255)."
      INDEX {prtDimCnfgIdx, prtDimIdx }
      ::= { prtDimCnfgTable 1}

PrtDimCnfgEntry ::=
      SEQUENCE {
   prtDimCnfgIdx  Integer32,
   prtDimIdx      Integer32,
   prtDimTxMode   INTEGER,
   prtDimPolarity INTEGER,
   prtDimClkMode  INTEGER,
   prtDimMaxDelay INTEGER,
   prtDimMng      INTEGER
   }      
       

prtDimCnfgIdx OBJECT-TYPE
      SYNTAX  Integer32 (1..255)
      MAX-ACCESS  read-only
      STATUS  current
      DESCRIPTION
      "This attribute indicates the Idx of the Cnfg(1..255) being 
       accessed.
       Idx of 255 relates to the TmpCnfg."
      ::= { prtDimCnfgEntry 1}

prtDimIdx OBJECT-TYPE
      SYNTAX  Integer32
      MAX-ACCESS  read-only
      STATUS  current
      DESCRIPTION
      "This attribute indicates a unique  port number of the
       DIM card. 
       The convention used for DXC:
       (IO slot number+10)*10 + 1
       Example: port1 of IO slot 11 will be: 211 ."
      ::= { prtDimCnfgEntry 2}


prtDimTxMode OBJECT-TYPE
      SYNTAX  INTEGER
       {
       regularTx   (2),
       broadcast   (3)
       }
      MAX-ACCESS  read-write
      STATUS  current
      DESCRIPTION
      "Tx mode.
       regularTx - the links are connected to a similar outfit on 
                   the other side. In this mode, if a link fails, 
                   the transmitted bandwidth is decreased 
                   accordingly.
       broadcast - the links are connected to MORE than one similar
                   outfit on the other side. In this mode, if a link 
                   fails, the transmitted bandwidth is not affected "
      ::= { prtDimCnfgEntry 3}

prtDimPolarity OBJECT-TYPE
      SYNTAX  INTEGER
       {
       normalClk (2),
       inverted  (3)
       }
      MAX-ACCESS  read-write
      STATUS  current
      DESCRIPTION
      "Polarity."
      ::= { prtDimCnfgEntry 4}

prtDimClkMode OBJECT-TYPE
      SYNTAX  INTEGER
       {
       extDce   (2),
       dce      (3),
	   smooth   (4),
	   extSmooth(5)
       }
      MAX-ACCESS  read-write
      STATUS  current
      DESCRIPTION
      "Clock Mode.
       smooth - a clock that is not 'pulsed'(has no 'gaps'). In this mode
	            the DXC does NOT receive back the clock signal.
       extSmooth - same as 'smooth' but in this mode, the DXC receives back
                the clock signal."
      ::= { prtDimCnfgEntry 5}

prtDimMaxDelay OBJECT-TYPE
      SYNTAX  INTEGER
       {
       t16msec (2),
       t64msec (3)
       }
      MAX-ACCESS  read-write
      STATUS  current
      DESCRIPTION
      "Max Delay permitted between the links, in msec."
      ::= { prtDimCnfgEntry 6}

prtDimMng OBJECT-TYPE
      SYNTAX  INTEGER
       {
       disabled (2),
       ts1      (3)
       }
      MAX-ACCESS  read-write
      STATUS  current
      DESCRIPTION
      "Use of DIM port for management.
       disabled - no management on DIM
       ts1      - 1 bit of TS1 is used for management."
      ::= { prtDimCnfgEntry 7}


prtDimDestTable OBJECT-TYPE
      SYNTAX SEQUENCE OF PrtDimDestEntry
      MAX-ACCESS not-accessible
      STATUS current
	DESCRIPTION  "A table."
	::=  {prtDim 2}

prtDimDestEntry OBJECT-TYPE
      SYNTAX PrtDimDestEntry
      MAX-ACCESS not-accessible
      STATUS current
      DESCRIPTION
      "The write operation is valid only for the TmpCnfg entry 
       (prtDimDestCnfgIdx=255)."
      INDEX {prtDestCnfgIdx, prtDestDimIdx, prtDestIdx }
      ::= { prtDimDestTable 1}

PrtDimDestEntry ::=
      SEQUENCE {
   prtDestCnfgIdx Integer32,
   prtDestDimIdx  Integer32,
   prtDestIdx     Integer32,
   prtDest        Integer32,
   prtDestConnect INTEGER
   }      
       

prtDestCnfgIdx OBJECT-TYPE
      SYNTAX  Integer32 (1..255)
      MAX-ACCESS  read-only
      STATUS  current
      DESCRIPTION
      "This attribute indicates the Idx of the Cnfg(1..255) being 
       accessed.
       Idx of 255 relates to the TmpCnfg."
      ::= { prtDimDestEntry 1}

prtDestDimIdx OBJECT-TYPE
      SYNTAX  Integer32
      MAX-ACCESS  read-only
      STATUS  current
      DESCRIPTION
      "This attribute indicates a unique  port number of the
       DIM card. 
       The convention used for DXC:
       (IO slot number+10) & 1
       Example: port1 of IO slot 11 will be: 211 ."
      ::= { prtDimDestEntry 2}

prtDestIdx OBJECT-TYPE
      SYNTAX  Integer32 (1..8)
      MAX-ACCESS  read-only
      STATUS  current
      DESCRIPTION
      "This attribute indicates a destination number of the
       DIM card. "
      ::= { prtDimDestEntry 3}


prtDest OBJECT-TYPE
      SYNTAX  Integer32
      MAX-ACCESS  read-write
      STATUS  current
      DESCRIPTION
      "Destination port,(of a T1/E1 port), that is connected to the 
    DIM card, for the specified Destination number.
    0 = No destination port.
    Else:
	For external ports:
    (IO Slot+10) & 1    for port 1 
    (IO Slot+10) & 3    for port 2 
       Example: port2 of IO slot 12 will be: 223 .
    For internal ports :
    (IO Slot+10) & 2    for port 1
    (IO Slot+10) & 4    for port 2
    (IO Slot+10) & 6    for port 3
    (IO Slot+10) & 8    for port 4, etc..."
      ::= { prtDimDestEntry 4}

prtDestConnect OBJECT-TYPE
      SYNTAX  INTEGER
       {
       no (2),
       yes(3)
       }
      MAX-ACCESS  read-only
      STATUS  current
      DESCRIPTION
      "Connection Status of the specified destination number.
    For a specified destination port, it depends both on the 
    status of the port and on the status of the far-end port.
    Since this is a RO object, same value will be received for
    all configurations."
      ::= { prtDimDestEntry 5}


--prtI - ISDN specific parameters table

prtICnfgTable  OBJECT-TYPE
      SYNTAX SEQUENCE OF PrtICnfgEntry
      MAX-ACCESS not-accessible
      STATUS current
	DESCRIPTION  "A table."
	::=  { prtI 1 }

prtICnfgEntry OBJECT-TYPE
      SYNTAX PrtICnfgEntry
      MAX-ACCESS not-accessible
      STATUS current
	DESCRIPTION  "An entry in table."
	INDEX { prtICnfgIdx, prtIIdx }
      ::= { prtICnfgTable 1}

PrtICnfgEntry ::=
      SEQUENCE {
      prtICnfgIdx  Integer32,
      prtIIdx      Integer32,
      prtIRate     INTEGER,
      prtIConnect  INTEGER
      }    

   
prtICnfgIdx OBJECT-TYPE
      SYNTAX  Integer32 (1..255)
      MAX-ACCESS  read-only
      STATUS  current
      DESCRIPTION
      "This attribute indicates the Idx of the Config being accessed.
       Idx of 255 relates to the Temporary (Scratch) Config. "
      ::= {prtICnfgEntry 1}

prtIIdx OBJECT-TYPE
      SYNTAX  Integer32
      MAX-ACCESS  read-only
      STATUS  current
      DESCRIPTION
      "This attribute indicates a unique number to identify a port. 
       The valid port number depends on the IO slot no.,  the 
       installed card type and the port type: outside, inside, 
       SP.
    * The ISDN B1, B2, D channels will be inside ports. 
      For port index, see product specification."
      ::= {prtICnfgEntry 2}

prtIRate     OBJECT-TYPE
      SYNTAX  INTEGER {
        notApplicable (1),
        nc            (2),
        r2bit         (3),
        r4bit         (4),
        r8bit         (5)
        }
      MAX-ACCESS  read-write
      STATUS  current
      DESCRIPTION
      "This object indicates the port rate in bits.
       Each TS contains 8 bits. Thus, 1 bit is equivalent to 8Kbps
       rate."
      ::= {prtICnfgEntry 3}

prtIConnect     OBJECT-TYPE
      SYNTAX  INTEGER {
        notApplicable (1),
        no            (2),
        yes           (3)
        }
      MAX-ACCESS  read-write
      STATUS  current
      DESCRIPTION
      "D channel connection.
       no  - disconnected
       yes - connected. "
      ::= {prtICnfgEntry 4}


--prtHdsl - HDSL specific parameters table

prtHdslTable  OBJECT-TYPE
      SYNTAX SEQUENCE OF PrtHdslEntry
      MAX-ACCESS not-accessible
      STATUS current
	  DESCRIPTION  "HDSL port table."
	::=  { prtHdsl 1 }

prtHdslEntry OBJECT-TYPE
      SYNTAX PrtHdslEntry
      MAX-ACCESS not-accessible
      STATUS current
	  DESCRIPTION  "An entry in table."
	  INDEX { prtHdslIdx }
      ::= { prtHdslTable 1}

PrtHdslEntry ::=
      SEQUENCE {
      prtHdslIdx       Integer32,
      prtHdslMode      INTEGER,
      prtHdslRptrType  INTEGER,
	  prtHdslMaxRate   INTEGER,
	  prtHdslLinkType  INTEGER,
	  prtHdslCompSwVer DisplayString,
	  prtHdslCompHwVer DisplayString
      }    
   
prtHdslIdx OBJECT-TYPE
      SYNTAX  Integer32
      MAX-ACCESS  read-only
      STATUS  current
      DESCRIPTION
      "This attribute indicates a unique number to identify a port. 
       The valid port number depends on the IO slot no.,  the 
       installed card type and the port type: outside, inside.
    * The HDSL ports will be external. 
      For port index, see product specification."
      ::= {prtHdslEntry 1}

prtHdslMode   OBJECT-TYPE
      SYNTAX  INTEGER {
        notApplicable (1),
        central       (2),
        remote        (3)
        }
      MAX-ACCESS  read-write
      STATUS  current
      DESCRIPTION
      "This object indicates the HDSL mode."
      ::= {prtHdslEntry 2}

prtHdslRptrType     OBJECT-TYPE
      SYNTAX  INTEGER {
      notApplicable (1),
      none    (2), 
      hrpt    (3)
        }
      MAX-ACCESS  read-only
      STATUS  current
      DESCRIPTION
      "The Repeater between Near and Far modem.
       none - no repeater exists between the modems
       hrpt - HRPT repeater exists between the modems."
      ::= {prtHdslEntry 3}

prtHdslMaxRate     OBJECT-TYPE
      SYNTAX  INTEGER {
      notApplicable (1),
      r192          (2), 
      r256          (3),
	  r320          (4),
	  r384          (5),
      r448          (6), 
      r512          (7),
	  r576          (8),
	  r640          (9),
      r768          (10), 
      r896          (11),
	  r1024         (12),
	  r1152         (13),
      r1280         (14), 
      r1536         (15),
	  r1920         (16),
	  r2048         (17)
        }
      MAX-ACCESS  read-write
      STATUS  current
      DESCRIPTION
      "Maximum Rate of the xDSL Line, in Kbps units.
       This object can be Set only for a Central unit."
      ::= {prtHdslEntry 4}

prtHdslLinkType     OBJECT-TYPE
      SYNTAX  INTEGER {
      notApplicable (1),
      msdsl2w       (2), 
      hdsl2w        (3),
	  hdsl4w        (4),
	  gDsl          (5)
        }
      MAX-ACCESS  read-only
      STATUS  current
      DESCRIPTION
      "The Link Type.
       msdsl2w - MSDSL 2 Wire
       hdsl2w  - HDSL  2 Wire
       hdsl4w  - HDSL  4 Wire
       gDsl    - G.DSL "
      ::= {prtHdslEntry 5}

prtHdslCompSwVer OBJECT-TYPE
      SYNTAX  DisplayString (SIZE (0..255))
      MAX-ACCESS  read-only
      STATUS  current
      DESCRIPTION
      "This object indicates the Software Version of the 
       component (Piggyback card) supporting this interface."
      ::= {prtHdslEntry 6}

prtHdslCompHwVer OBJECT-TYPE
      SYNTAX  DisplayString (SIZE (0..255))
      MAX-ACCESS  read-only
      STATUS  current
      DESCRIPTION
      "This object indicates the Hardware Version of the 
       component (Piggyback card) supporting this interface."
      ::= {prtHdslEntry 7}


--DACS T3/E3 port configuration parameters. Applicable also for Optimux-T3 Links.
--
--These objects were entered in this private MIB, because they do not 
--appear in RFC1407 (except prtT3E3LineLength which appears in meters) and in
--RFC-1407 MIB there is no reference to configuration number.


prtT3E3CnfgTable OBJECT-TYPE
  SYNTAX  SEQUENCE OF PrtT3E3CnfgEntry
  MAX-ACCESS  not-accessible
  STATUS  current
  DESCRIPTION
  "T3/E3 port configuration table."
  ::= { prtT3E3 1}

prtT3E3CnfgEntry   OBJECT-TYPE
  SYNTAX  PrtT3E3CnfgEntry
  MAX-ACCESS  not-accessible
  STATUS  current
  DESCRIPTION
  " An entry in the T3/E3 port configuration table."
  INDEX { prtT3E3CnfgIdx, prtT3E3PrtIdx }
  ::= { prtT3E3CnfgTable 1}

PrtT3E3CnfgEntry ::=
     SEQUENCE {
  prtT3E3CnfgIdx
  Integer32,
  prtT3E3PrtIdx
  Integer32,
  prtT3E3Slt
  INTEGER,
  prtT3E3LineLength
  INTEGER,
  prtT3E3InbandMng
  INTEGER,
  prtT3E3AisFrame
  INTEGER,
  prtT3E3TxClockSource
  INTEGER,
  prtT3E3RoutProt
  INTEGER
  }
 
prtT3E3CnfgIdx OBJECT-TYPE
      SYNTAX  Integer32 (1..255)
      MAX-ACCESS  read-only
      STATUS  current
      DESCRIPTION
      "This attribute indicates the Idx of the Config being accessed.
       Idx of 255 relates to the Temporary (Scratch) Config.
       For DXC, write operations can be performed only on the Temp Config.
       For products that do not support configurations, always 1 will be used."
      ::= { prtT3E3CnfgEntry 1}

prtT3E3PrtIdx OBJECT-TYPE
      SYNTAX  Integer32
      MAX-ACCESS  read-only
      STATUS  current
      DESCRIPTION
      "This attribute indicates a unique  port number.
	   For DXC:
          The same numbering as for prtGenPrtIdx.
          The valid port number depends on the IO slot no.,  the 
          installed card type and the port type: outside, inside. 
          * The external ports convention used will be (for DXC):
           - first two digits will be: (IO slot number+10)
           - last one/two digits will be the port number within the 
               card, in odd numbers:
               port1 = 1
               port2 = 3
               port3 = 5 
               etc...
               Example: port2 of IO slot 11 will be: 213 .
       For Optimux-T3:
          Link-A: 51 
          Link-B: 61 . "
      ::= { prtT3E3CnfgEntry 2}

prtT3E3Slt     OBJECT-TYPE
      SYNTAX  INTEGER
       {
       clA   (3),
       clB   (4),
       io1   (5),
       io2   (6),
       io3   (7),
       io4   (8),
       io5   (9),
       io6  (10),
       io7  (11),
       io8  (12),
       io9  (13),
       io10 (14),
       io11 (15),
       io12 (16),
       io13 (17),
       io14 (18),
       io15 (19),
       standAlone (255)
       }
      MAX-ACCESS  read-only
      STATUS  current
      DESCRIPTION
      "This attribute indicates a unique number to identify the slot where
       the card is inserted in.
       When the unit is stand-alone, this object is not applicable
       and 255 will be used."
      ::= { prtT3E3CnfgEntry 3}

prtT3E3LineLength  OBJECT-TYPE
      SYNTAX  INTEGER
       {
        notApplicable(1),
        len0p450ft   (2),
        len451p900ft (3)
       }
      MAX-ACCESS  read-write
      STATUS  current
      DESCRIPTION
      "This object is the length of the ds3 line in feet.  
       It provides information for line build out circuitry if it exists 
       and can use this object to adjust the line build out. 
       len0p450ft   = 0   - 450 feet
       len451p900ft = 451 - 900 feet."
   ::= { prtT3E3CnfgEntry 4}

prtT3E3InbandMng  OBJECT-TYPE
      SYNTAX  INTEGER
       {
          notApplicable(1),
          off          (2),
          cBit         (3), --Cbit-Tx-Rx
          cBitTxRxMng  (4),
          cBitTx       (5),
          cBitTxMng    (6),
          m13          (7) 
       }
      MAX-ACCESS  read-write
      STATUS  current
      DESCRIPTION
      "A unique number to identify the Frame Type over the link.
       For Optimux-T3: only values (4), (7) are supported."
      ::= {prtT3E3CnfgEntry 5}

prtT3E3AisFrame  OBJECT-TYPE
      SYNTAX  INTEGER
       {
        notApplicable(1),
        unframed     (2),
        framed       (3)
       }
      MAX-ACCESS  read-write
      STATUS  current
      DESCRIPTION
      "This object is applicable only for Optimux-T3.  
       It allows user to select whether the AIS sent will be framed or unframed."
   ::= { prtT3E3CnfgEntry 6}

prtT3E3TxClockSource  OBJECT-TYPE
      SYNTAX  INTEGER
       {
        external(1),  -- loopTiming
        internal(2),  -- localTiming
        notApplicable(255)
       }
      MAX-ACCESS  read-write
      STATUS  current
      DESCRIPTION
      "Tx Clock Source."
   ::= { prtT3E3CnfgEntry 7}

prtT3E3RoutProt  OBJECT-TYPE
      SYNTAX  INTEGER
       {
        notApplicable (1),
        none          (2),  
        proprietary   (3),
        rip2          (4)
       }
      MAX-ACCESS  read-write
      STATUS  current
      DESCRIPTION
      "Routing Protocol of the port.
       This object is applicable only for T3 ports."             
      ::= { prtT3E3CnfgEntry 8}



--DACS General data, unrelated to a specific level or unit type

--Compressed data table - applicable for all the MIB leafs,
--Used only by NMS station

cmprTable  OBJECT-TYPE
      SYNTAX SEQUENCE OF CmprEntry
      MAX-ACCESS not-accessible
      STATUS current
	DESCRIPTION  "A table."
	::=  { genDacsMux 1 }

cmprEntry OBJECT-TYPE
      SYNTAX CmprEntry
      MAX-ACCESS not-accessible
      STATUS current
	DESCRIPTION  "An entry in table."
	INDEX {cmprTypeIdx, cmprCnfgIdx,cmprVersion,cmprSltIdx,cmprPrtIdx}
      ::= {cmprTable  1}

CmprEntry ::=
      SEQUENCE {
  cmprTypeIdx      Integer32,
  cmprCnfgIdx      Integer32,
  cmprVersion      Integer32,
  cmprSltIdx       INTEGER,
  cmprPrtIdx       Integer32,
  cmprObj          OCTET STRING
      }

cmprTypeIdx OBJECT-TYPE
      SYNTAX  Integer32
      MAX-ACCESS  read-only
      STATUS  current
      DESCRIPTION
      "This object indicates the Type of the Compressed 
       data referred (which table, which level, etc).
       The type is a code according to a convention between
       agent and NMS."
      ::= { cmprEntry 1}

cmprCnfgIdx OBJECT-TYPE
      SYNTAX  Integer32
      MAX-ACCESS  read-only
      STATUS  current
      DESCRIPTION
      "This object indicates the configuration number the
       Compressed information relates to."
      ::= { cmprEntry 2}

cmprVersion OBJECT-TYPE
      SYNTAX  Integer32
      MAX-ACCESS  read-only
      STATUS  current
      DESCRIPTION
      "This object indicates the version of the internal format of
       the Compressed data (the version of the convention used)."
      ::= { cmprEntry 3}

cmprSltIdx  OBJECT-TYPE
     SYNTAX  INTEGER
         {
         psA   (1),
         psB   (2),
         clA   (3),
         clB   (4),
         io1   (5),
         io2   (6),
         io3   (7),
         io4   (8),
         io5   (9),
         io6  (10),
         io7  (11),
         io8  (12),
         io9  (13),
         io10 (14),
         io11 (15),
         io12 (16),
         io13 (17),
         io14 (18),
         io15 (19),
         notApplicable (255)
         }
     MAX-ACCESS  read-only
     STATUS  current
     DESCRIPTION
     "This attribute indicates a unique number of  the slot  
      position where the card is inserted.
      When the unit is stand-alone or this object is not applicable,
      255 will be used."
     ::= { cmprEntry 4}


cmprPrtIdx  OBJECT-TYPE
      SYNTAX  Integer32
      MAX-ACCESS  read-only
      STATUS  current
      DESCRIPTION
      "This object indicates a unique identifier of the port,
       the compressed information relates to.
    For DXC - according to the order in the card of cmprSltIdx:
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 .
    For FCD: see product's specification.
       If the port number is irrelevant to this parameter (if it is
       a system/card level alarm) the value will be 9999."
      ::= { cmprEntry 5}

cmprObj OBJECT-TYPE
      SYNTAX  OCTET STRING
      MAX-ACCESS  read-write
      STATUS  current
      DESCRIPTION
      "This object is the compressed information itself, 
       according to a predefined format, both agent and NMS agreed
       about."
      ::= { cmprEntry 6}


--mapLinkTable

mapLinkTable OBJECT-TYPE
      SYNTAX SEQUENCE OF MapLinkEntry
      MAX-ACCESS not-accessible
      STATUS current
	DESCRIPTION  "A table."
	::=  { genDacsMux 2}

mapLinkEntry OBJECT-TYPE
      SYNTAX MapLinkEntry
      MAX-ACCESS not-accessible
      STATUS current
	DESCRIPTION  "An entry in table."
	INDEX {mapLinkIdx}
      ::= {mapLinkTable 1}

MapLinkEntry ::=
      SEQUENCE {
      mapLinkIdx               Integer32,
      mapLinkSlotIdx           INTEGER,
      mapLinkPortIdx           Integer32,
      mapLinkState             INTEGER
      }

mapLinkIdx     OBJECT-TYPE
      SYNTAX  Integer32
      MAX-ACCESS  read-only
      STATUS  current
      DESCRIPTION
      "A unique identifier of the link"
::=  {mapLinkEntry 1}

mapLinkSlotIdx    OBJECT-TYPE
      SYNTAX  INTEGER
        {
         io1   (5),
         io2   (6),
         io3   (7),
         io4   (8),
         io5   (9),
         io6  (10),
         io7  (11),
         io8  (12),
         io9  (13),
         io10 (14),
         io11 (15),
         io12 (16),
         io13 (17),
         io14 (18),
         io15 (19),
         standAlone (255)
     }
      MAX-ACCESS  read-write
      STATUS  current
      DESCRIPTION
      "This attribute indicates a unique  slot  position where
       the module is inserted."       
::=  {mapLinkEntry 2}

mapLinkPortIdx  OBJECT-TYPE
      SYNTAX  Integer32
      MAX-ACCESS  read-write
      STATUS  current
      DESCRIPTION
      "This attribute indicates a unique  port number.
       The valid port number depends on the IO slot no.,  the 
       installed card type and the port type: outside, inside, 
       SP.
       In the DXC :
      - first two digits will be: (IO slot number+10)
      - last one/two digits will be the port number within the 
        card in odd or even numbers, as follows:
      * For the outside/external ports, in odd numbers:
        port1 = 1
        port2 = 3
        port3 = 5 
        etc...
        Example: port2 of IO slot 11 will be: 213 .
      * The inside/internal ports, in even numbers:
        port1 = 2
        port2 = 4
        port3 = 6 
        etc...
        Example: port2 of IO slot 11 will be: 214 ."
::=  {mapLinkEntry 3}

mapLinkState   OBJECT-TYPE
      SYNTAX  INTEGER
 {
 unknown(1),
 down(2),
 up(3)
 }
      MAX-ACCESS  read-only
      STATUS  current
      DESCRIPTION
      "This attribute indicates the status of the link between 
       the two muxes"
::=  {mapLinkEntry 4}

 
--Alarms List - 
--              
--              

alrGenTable  OBJECT-TYPE
      SYNTAX SEQUENCE OF AlrGenEntry
      MAX-ACCESS not-accessible
      STATUS current
	DESCRIPTION  "A table."
	::=  { genDacsMux 3 }

alrGenEntry OBJECT-TYPE
      SYNTAX AlrGenEntry
      MAX-ACCESS not-accessible
      STATUS current
	DESCRIPTION  "An entry in table."
	INDEX { alrGenCode }
      ::= { alrGenTable 1}

AlrGenEntry ::=
      SEQUENCE {
     alrGenCode          Integer32,
     alrGenDescription  DisplayString (SIZE (0..255)),
     alrGenLevel         INTEGER,
	 alrGenSlotType      INTEGER,
	 alrGenSeverity      INTEGER,
	 alrGenDebounce      Integer32,
	 alrGenDefSeverity   INTEGER
      }

alrGenCode OBJECT-TYPE
      SYNTAX  Integer32
      MAX-ACCESS  read-only
      STATUS  current
      DESCRIPTION
      "This object is a unique code number, identifying 
       a certain alarm."
    ::= { alrGenEntry 1}

alrGenDescription  OBJECT-TYPE
      SYNTAX  DisplayString (SIZE (0..255))
      MAX-ACCESS  read-only
      STATUS  current
      DESCRIPTION
      "This entry is a unique text description, of the alarm 
       corresponding to the specified code."
       ::= { alrGenEntry 2}
       
alrGenLevel   OBJECT-TYPE
      SYNTAX  INTEGER
      {
       notApplicable(1),
       system       (2),
       card         (3),
       port         (4)
      }
      MAX-ACCESS  read-only
      STATUS  current
      DESCRIPTION
      "Alarm level."
      ::=  {alrGenEntry 3}

alrGenSlotType   OBJECT-TYPE
      SYNTAX  INTEGER
      {
       notApplicable(1),
       ps           (2),
       cl           (3),
       io           (4),
	   clAndIo      (5)
      }
      MAX-ACCESS  read-only
      STATUS  current
      DESCRIPTION
      "Slot type that the alarm is relevant to.
       clAndIo - an alarm that is relevant for both CL and IO slots."
      ::=  {alrGenEntry 4}

alrGenSeverity   OBJECT-TYPE
      SYNTAX  INTEGER
      {
       notApplicable (1),
       event    (3),
       minor    (4),
       major    (5),
       warning  (6),
       critical (7)
       }
      MAX-ACCESS  read-write
      STATUS  current
      DESCRIPTION
      "This object enables the user to select a severity for each alarm.
       The severity is set per alarm code (same for all slots/ports
       using this code)."
      ::=  {alrGenEntry 5}

alrGenDebounce   OBJECT-TYPE
      SYNTAX  Integer32 (0..255)
      MAX-ACCESS  read-write
      STATUS  current
      DESCRIPTION
      "Debounce time for each alarm code, in seconds.
       The meaning is, that an alarm will be 'declared' as ON (or OFF), only 
       after it was actually ON/OFF the Debouncing time selected by user.
       0 = default debounce selection (each alarm has a default value).
	   250 = maximum value of seconds for debounce.
	   253 = mask = the alarm will Never be reported.
	   254 = default debounce selection (each alarm has a default value).
	   255 = not applicable "
      ::=  {alrGenEntry 6}

alrGenDefSeverity OBJECT-TYPE
      SYNTAX  INTEGER
       {
      notApplicable (1),
      event    (3),
      minor    (4),
      major    (5)
       }
      MAX-ACCESS  read-only
      STATUS  current
      DESCRIPTION
      "This object reports the default severity of each alarm.
       User can change the  severity of the alarms defined by
       this default via the alrGenSeverity object."
      ::= {alrGenEntry 7}



-- Traps

--NOTIFICATIONS

     dacsMuxEvents OBJECT-IDENTITY
	    STATUS  current
	    DESCRIPTION
	    "The events for DACS MUX."
	    ::= { dacsMux 0 }

     sanityCheckTrap  NOTIFICATION-TYPE
        OBJECTS { sysSSanityCheckStatus, sysDbaseDownloadCnfgIdxCmd }
        STATUS current
        DESCRIPTION     
        "This trap is sent after a data base download attempt. 
         It returns the sanity result status and the configuration
         no.checked."
        ::= { dacsMuxEvents 1 }

     dacsMuxAlarmsTrap  NOTIFICATION-TYPE
       STATUS current
       DESCRIPTION     
       "This trap is sent when an alarm occurs."
       ::= { dacsMuxEvents 2 }

     mdlConnectTrap  NOTIFICATION-TYPE
       OBJECTS       {mdlSCardType, mdlSActivity}
       STATUS current
       DESCRIPTION     
       "This trap is sent when a card is removed."
       ::= { dacsMuxEvents 3 }

     sysAlrStatusTrap  NOTIFICATION-TYPE
       OBJECTS       { sysSAlrStatusAll, sysSAlrStatus }
       STATUS current
       DESCRIPTION     
       "This trap is sent upon any change in the value of any of 
        the variables."
       ::= { dacsMuxEvents 4 }
 

     sysStatusChangedTrap  NOTIFICATION-TYPE
       OBJECTS       {agnLed}
       STATUS current
       DESCRIPTION     
       "This trap is sent when Leds status is changed."
       ::= { dacsMuxEvents 5 }


     cnfgUpdateTrap  NOTIFICATION-TYPE
       STATUS current
       DESCRIPTION     
       "This trap is sent upon change of the active Configuration DB."  
       ::= { dacsMuxEvents 6 }
-- 
-- file :v:\doc\rdv\mib\ver470\kmux.txt
-- 
--                RAD-KMUX MIB    (Kilomux)

--Title:     RAD's Kilomux PRODUCT MIB
--Version:   1.0
--Date:      29.8.96
--By:        Yair Arian, Smadar Tauber and Yaira Gabay
--File:      kmux.txt
--
--Last update: 20-03-2001  by Smadar Tauber


kmux  OBJECT IDENTIFIER  ::=  {radWan 6}


systemKmux  OBJECT IDENTIFIER  ::=  {kmux 1}

generalKmux  OBJECT IDENTIFIER  ::=  {systemKmux 1}

sysGenKmuxTable  OBJECT-TYPE
      SYNTAX SEQUENCE OF SysGenKmuxEntry
      MAX-ACCESS not-accessible
      STATUS  current
      DESCRIPTION
      "A table containing the general Kmux parameters."
       ::= { generalKmux 1 }

sysGenKmuxEntry OBJECT-TYPE
      SYNTAX SysGenKmuxEntry
      MAX-ACCESS not-accessible
      STATUS current
	DESCRIPTION  "An entry in table."
	INDEX {sysGenConfigIdx}
      ::= {sysGenKmuxTable 1}

SysGenKmuxEntry ::=
      SEQUENCE {
   sysGenConfigIdx              Integer32,
   sysGenFlipIntegration        INTEGER,
   sysGenMlMode                 INTEGER,
   sysGenFaType                 INTEGER,
   sysGenLinkRecovery           INTEGER,
   sysGenLinkSourceClock        INTEGER,
   sysGenMngBwA                 Integer32,
   sysGenMngBwB                 Integer32,
   sysGenAutoDialSlot           Integer32,
   sysGenResetBypassEnable      INTEGER
   }

sysGenConfigIdx OBJECT-TYPE
      SYNTAX  Integer32 (1..255)
      MAX-ACCESS  read-only
      STATUS  current
      DESCRIPTION
      "This object indicates the Configuration number (1..255) 
       referred.
       Value of  255 specifies the TmpCnfg (Scratch).
       The write operation in this Table is valid only to the 
       TmpCnfg entry."
      ::= { sysGenKmuxEntry 1}

sysGenFlipIntegration OBJECT-TYPE
      SYNTAX INTEGER { notApplicable(1),
                       short        (2),
                       long         (3)
      }
      MAX-ACCESS read-write
      STATUS current
      DESCRIPTION
      "The parameter is relevant only for KM-2100 and only when 
       sysGenMlMode=redundancy, switchBackup, or priorityBumping."
      ::= { sysGenKmuxEntry 2}

sysGenMlMode OBJECT-TYPE
      SYNTAX INTEGER { single         (2),
                       redundancy     (3),
                       dualLink       (4),
                       priorityBumping(5),
                       switchBackup   (6)
      }
      MAX-ACCESS read-write
      STATUS current
      DESCRIPTION
      "The Main Link operation mode. Determines how many links are
       used (one/two) and how they are used."
      ::= { sysGenKmuxEntry 3}

sysGenFaType OBJECT-TYPE
      SYNTAX INTEGER { auto   (2),
                       manual (3)
      }
      MAX-ACCESS read-write
      STATUS current
      DESCRIPTION
      "Frame Allocation type:
       auto - automatic frame allocation (by Kmux)
       manual - manually configured frame allocation (by user)."
      ::= { sysGenKmuxEntry 4}

sysGenLinkRecovery OBJECT-TYPE
      SYNTAX INTEGER { 
                       notApplicable (1),
                       auto          (2),
                       manual        (3)
      }
      MAX-ACCESS read-write
      STATUS current
      DESCRIPTION
      "The parameter determines the Link Recovery mode.
       The parameter is relevant only when the sysGenMlMode is either 
       switchBackup or priorityBumping."
      ::= { sysGenKmuxEntry 5}

sysGenLinkSourceClock OBJECT-TYPE
      SYNTAX INTEGER { none       (1),
                       kmxMlA  (103),
                       kmxMlB  (104)
      }
      MAX-ACCESS read-write
      STATUS current
      DESCRIPTION
      "The source clock for the links. The parameter is relevant 
       only for KM-2100 having a KDI or KDI/CH cards. ML-A or ML-B 
       are selectable only when sysGenMlMode=dual or priorityBumping."
      ::= { sysGenKmuxEntry 6}

sysGenMngBwA OBJECT-TYPE
      SYNTAX Integer32 
      MAX-ACCESS read-write
      STATUS current
      DESCRIPTION
      "The required management rate for ML-A, in bps. It is very important when a remote 
       unit is managed. 
       The selected value must be < ML-A Rate value.
       0 = None or not applicable
       800   bps = minimum value
       19200 bps = maximum value"
      ::= { sysGenKmuxEntry 7}

sysGenMngBwB OBJECT-TYPE
      SYNTAX Integer32 
      MAX-ACCESS read-write
      STATUS current
      DESCRIPTION
      "The required management rate for ML-B, in bps. It is very important when a remote 
       unit is managed. 
       The selected value must be < ML-B Rate value.
       0 = None or not applicable
       800   bps = minimum value
       19200 bps = maximum value"
      ::= { sysGenKmuxEntry 8}
 
sysGenAutoDialSlot OBJECT-TYPE
      SYNTAX Integer32 
      MAX-ACCESS read-write
      STATUS current
      DESCRIPTION
      "This object indicates the IO-SLOTs that can be used to initiate Automatic 
      DialUp.
      This field will be applicable when KML.10 is a ML and its
      prtIsdnSwitchMode=auto.
      Each IO Slot is represented by a bit:   11 .............0
                                        MSB(IO12)       LSB(IO1)
      bit 0 (LSB) kmxIO1: '1'- used
                       '0'- not used
      bit 1       kmxIO2: '1'- used
                      '0'- not used
      bit 2       kmxIO3: '1'- used
      .       '0'- not used
      .
      bit 11(MSB) kmxIO12: '1'- used
                       '0'- not used
      
      The value will be: SUM of [2**n] ; n=bit number." 
      ::= { sysGenKmuxEntry 9}

sysGenResetBypassEnable OBJECT-TYPE
      SYNTAX INTEGER {
       notApplicable(1),
       disabled     (2),
       enabled      (3)
      }
      MAX-ACCESS read-write
      STATUS current
      DESCRIPTION
      "Enable/Disable Reset Bypass operation when a KDI card exists
       and one of its links failed.
       notApplicable - when no KDI card exists in the Hub."
      ::= { sysGenKmuxEntry 10}

 
 
sysGenLinkRecoveryCmd OBJECT-TYPE
      SYNTAX INTEGER { 
                       noOp (1),
                       off  (2),
                       on   (3)
      }
      MAX-ACCESS read-write
      STATUS current
      DESCRIPTION
      "Command to recover from ML failure.
       When 'on', the agent will perform manual link recovery and 
       reset the variable to 'off'. 
       The conditions for this action are: 
       sysGenMlMode= priorityBumping or switchBackup and also 
       sysGenLinkRecovery=manual(3)."
      ::= { generalKmux 2}

sysGenFlipMlCmd OBJECT-TYPE
      SYNTAX INTEGER { 
                       noOp (1),
                       off  (2),
                       on   (3)
      }
      MAX-ACCESS read-write
      STATUS current
      DESCRIPTION
      "Command to flip the ML when sysGenMlMode=redundancy.
       When 'on', the agent will flip the ML and reset
       the variable to 'off'."
      ::= { generalKmux 3}
  
sysGenMonitorChannel OBJECT-TYPE
      SYNTAX Integer32
      MAX-ACCESS read-write
      STATUS current
      DESCRIPTION
      "The variable specifies the channel to be monitored and 
       presented on the front panel LEDs. The channel will be 
       specified according to: Slot*100+Ch. 
       0 - no monitoring."
      ::= { generalKmux 4}


statusKmux  OBJECT IDENTIFIER  ::=  {systemKmux 2}
  
sysStatusOnLineML OBJECT-TYPE
      SYNTAX INTEGER { both      (1),
                       kmxMlA  (103),
                       kmxMlB  (104)        
      }
      MAX-ACCESS read-only
      STATUS current
      DESCRIPTION
      "The main links which are online."
      ::= { statusKmux 1}

sysKmuxStatus OBJECT-TYPE
      SYNTAX Integer32
      MAX-ACCESS read-only
      STATUS current
      DESCRIPTION
      "A BIT string indicating the system status as follows
       On - the bit is set to '1':
      Bit 0 (LSB): Alarm Relay. 
   Bit 1: SP param. 
             Off- Configure the SP port from the database
             On - Default parameters (9600bps, 8 data bits, 
                  no parity, one stop bit).
   Bit 2: DBinit. 
             The status of the dip switch in the Common Logic Card.
             Off- Configuration parameters were determined by the 
                  user.
             On - Default configuration parameters are loaded on 
                  mux power-on.
   Bit 3: DownloadBw.
             Off - Disable in-band management.
             On  - Enable in-band management.
   Bit 4 (MSB): Passwd.
             Off - No password is required.
             On  - Password is required.
      Example: 8 (10000) means Passwd.=On and all the others off."
      ::= { statusKmux 2}

sysKmuxOffset OBJECT-TYPE
      SYNTAX INTEGER {
                       notApplicable (1),
                       off           (2),
                       on            (3)
      }
      MAX-ACCESS read-only
      STATUS current
      DESCRIPTION
      "'on' - slots 1..4 of KM-2104 match slots 11..14 of KM-2100.
       'off'- slots 1..4 of KM-2104 match slots  7..10 of KM-2100.
       notApplicable - for KM-2100."
      ::= { statusKmux 3}



backupKmux  OBJECT IDENTIFIER  ::=  {systemKmux 3}

sysBackupTable  OBJECT-TYPE
      SYNTAX SEQUENCE OF SysBackupEntry
      MAX-ACCESS not-accessible
      STATUS  current
      DESCRIPTION
      "A table containing the backup parameters."
       ::= { backupKmux 1 }

sysBackupEntry OBJECT-TYPE
      SYNTAX SysBackupEntry
      MAX-ACCESS not-accessible
      STATUS current
	DESCRIPTION  "An entry in table."
	INDEX {sysBackupConfigIdx}
      ::= {sysBackupTable 1}

SysBackupEntry ::=
      SEQUENCE {
   sysBackupConfigIdx            Integer32,
   sysBackupDatabase             INTEGER,
   sysBackupMode                 INTEGER,
   sysBackupDialTimeout          INTEGER,
   sysBackupOptions              INTEGER
   }

sysBackupConfigIdx OBJECT-TYPE
      SYNTAX  Integer32 (1..255)
      MAX-ACCESS  read-only
      STATUS  current
      DESCRIPTION
      "This object indicates the Configuration number (1..255) 
       referred.
       Value of  255 specifies the TmpCnfg (Scratch)."
      ::= { sysBackupEntry 1}

sysBackupDatabase OBJECT-TYPE
      SYNTAX INTEGER { onLine   (2),
                       alternate(3)
      }
      MAX-ACCESS read-write
      STATUS current
      DESCRIPTION
      "Determines the database to switch to, when ML recovery occurs."
      ::= { sysBackupEntry 2}

sysBackupMode OBJECT-TYPE
      SYNTAX INTEGER { isdn(2),
                       pstn(3)
      }			    
      MAX-ACCESS read-write
      STATUS current
      DESCRIPTION
      "isdn - for connection to ISDN network.
       pstn - for connection to PSTN network."
      ::= { sysBackupEntry 3}

sysBackupDialTimeout OBJECT-TYPE
      SYNTAX INTEGER { sec30 (2),
                       sec45 (3),
                       sec60 (4),
                       sec120(5)
      }
      MAX-ACCESS read-write
      STATUS current
      DESCRIPTION
      "The dial timeout in seconds (when backup is attempted)."
      ::= { sysBackupEntry 4}


sysBackupOptions OBJECT-TYPE
      SYNTAX INTEGER { noBackup (2),
                       line     (3),
                       path     (4)
      }
      MAX-ACCESS read-write
      STATUS current
      DESCRIPTION
      "The Backup options:
       noBackup - No backup is applicable
       line - Line Data backup
       path - Line Mng backup ."
      ::= { sysBackupEntry 5}


sysBackupAgendaTable  OBJECT-TYPE
      SYNTAX SEQUENCE OF SysBackupAgendaEntry
      MAX-ACCESS not-accessible
      STATUS  current
      DESCRIPTION
      "A table containing the backup schedule. It is possible to
       define 4 different time zone schedules per day of the week."
       ::= { backupKmux 2 }

sysBackupAgendaEntry OBJECT-TYPE
      SYNTAX SysBackupAgendaEntry
      MAX-ACCESS not-accessible
      STATUS current
	DESCRIPTION  "An entry in table."
	INDEX {sysBackupCfgIdx,sysBackupDay,sysBackupZone}
      ::= {sysBackupAgendaTable 1}

SysBackupAgendaEntry ::=
      SEQUENCE {
   sysBackupCfgIdx       INTEGER,
   sysBackupDay          INTEGER,
   sysBackupZone         INTEGER, 
   sysBackupEndTime      DisplayString,
   sysBackupStatus       INTEGER 
   }

sysBackupCfgIdx OBJECT-TYPE
      SYNTAX  INTEGER 
           {
            active      (1),
            temporary (255)
           }  
      MAX-ACCESS  read-only
      STATUS  current
      DESCRIPTION
      "This object indicates the Configuration number (1,255) 
       referred.
       Write operation for the table entries is allowed only to
       the temporary configuration (255)."
      ::= { sysBackupAgendaEntry 1}

sysBackupDay OBJECT-TYPE
      SYNTAX INTEGER {sunday   (1),
                      monday   (2),
                      tuesday  (3),
                      wednesday(4),
                      thursday (5),
                      friday   (6),
                      saturday (7)
        }
      MAX-ACCESS read-only
      STATUS current
      DESCRIPTION
      "Day of the week."
      ::= { sysBackupAgendaEntry 2}

sysBackupZone OBJECT-TYPE
      SYNTAX INTEGER {zone1(1),
                      zone2(2),
                      zone3(3),
                      zone4(4),
					  zone5(5)
        }
      MAX-ACCESS read-only
      STATUS current
      DESCRIPTION
      "The time zone."
      ::= { sysBackupAgendaEntry 3}


sysBackupEndTime OBJECT-TYPE
      SYNTAX DisplayString (SIZE(0..255))
      MAX-ACCESS read-write
      STATUS current
      DESCRIPTION
      "The end time for this time zone. The format is HH:MM. For
       example 23:59.
       For Zone 4, End Time = 23:59 (constant)."
      ::= { sysBackupAgendaEntry 4}

sysBackupStatus OBJECT-TYPE
      SYNTAX INTEGER { enable (1),
                       disable(2)
     }
      MAX-ACCESS read-write
      STATUS current
      DESCRIPTION
      "Enable or disable this backup schedule entry."
      ::= { sysBackupAgendaEntry 5}


frameAllocationKmux  OBJECT IDENTIFIER  ::=  {systemKmux 4}


sysFrameAllocationTable  OBJECT-TYPE
      SYNTAX SEQUENCE OF SysFrameAllocationEntry
      MAX-ACCESS not-accessible
      STATUS  current
      DESCRIPTION
      "A table for manually configuring the frame allocation.
       The table will contain always all the programmed cards' 
       ports. sysFaNumOfBits"
       ::= { frameAllocationKmux 1 }

sysFrameAllocationEntry OBJECT-TYPE
      SYNTAX SysFrameAllocationEntry
      MAX-ACCESS not-accessible
      STATUS current
	DESCRIPTION  "An entry in table."
	INDEX {sysFaConfigIdx, sysFaLink, sysFaPrt}
      ::= {sysFrameAllocationTable 1}

SysFrameAllocationEntry ::=
      SEQUENCE {
   sysFaConfigIdx   Integer32,
   sysFaLink        INTEGER, 
   sysFaPrt         Integer32,
   sysFaStartingBit Integer32,
   sysFaNumOfBits   Integer32 
	}

sysFaConfigIdx OBJECT-TYPE
      SYNTAX  Integer32 (1..255)
      MAX-ACCESS  read-only
      STATUS  current
      DESCRIPTION
      "This object indicates the Configuration number (1..255) 
       referred.
       Value of  255 specifies the TmpCnfg (Scratch).
       Write operation for the table entries is allowed only to 
       Config=255."
      ::= { sysFrameAllocationEntry 1}

sysFaLink OBJECT-TYPE
      SYNTAX INTEGER { 
                    kmxMlA  (103),
                    kmxMlB  (104)
      }
      MAX-ACCESS read-only
      STATUS current
      DESCRIPTION
      "The main link on which frame allocation is done."
      ::= { sysFrameAllocationEntry 2}

sysFaPrt OBJECT-TYPE
      SYNTAX Integer32 
      MAX-ACCESS read-only
      STATUS current
      DESCRIPTION
      "The Frame Allocation (FA) port.
       The ports will be specified by:
          Slot*100+Ch.
       - for Bypass  of KDI or KDI/CH the port will be:
          Slot*100+11 (internal-1=non-existent port ; just for use
                       of the same MIB table)
       - for all the programmed cards, there will be an artificial
         port entry that will represent the card, in order to 
         specify  the Control Signal Bits that are at card level:
          Slot*100+0 . "
      ::= { sysFrameAllocationEntry 3}

sysFaStartingBit OBJECT-TYPE
      SYNTAX Integer32 (0..239)
      MAX-ACCESS read-write
      STATUS current
      DESCRIPTION
      "The data starting bit for the channel.
       - for Bypass of KDI or KDI/CH, this will be the Starting Bit 
         of the Bypass Window on the specific sysFaLink.
       - for Control Signals of a card  ( sysFaPrt=Slot*100+0)
         this will be the Starting Bit of the Control Signals of the 
         card."
      ::= { sysFrameAllocationEntry 4}

sysFaNumOfBits OBJECT-TYPE
      SYNTAX Integer32 (0..239)
      MAX-ACCESS read-write
      STATUS current
      DESCRIPTION
      "The data size in number of bits for the channel.
       - for Bypass of KDI or KDI/CH, this will be the Bypass Window 
         size. In this case, this value must be the same  for both 
   MLs.
       - for Control Signals of a card  ( sysFaPrt=Slot*100+0)
         this will be the number of Control Signal Bits of the 
         card."
      ::= { sysFrameAllocationEntry 5}


-- Disconnect Supervision Event Table.
-- This table contains all the Disconnect Supervision Events
-- that occurred on the KVF.6 and KVF.8 cards of the KM.

sysDisconnectSupervisionEventTable  OBJECT-TYPE
      SYNTAX SEQUENCE OF SysDisconnectSupervisionEventEntry
      MAX-ACCESS not-accessible
      STATUS current
	  DESCRIPTION  "Disconnect Supervision Event table."
    ::=  {systemKmux 5}

sysDisconnectSupervisionEventEntry OBJECT-TYPE
      SYNTAX SysDisconnectSupervisionEventEntry
      MAX-ACCESS not-accessible
      STATUS current
	  DESCRIPTION  "An entry in the table."
	  INDEX { sysDsEventIdx }
      ::= { sysDisconnectSupervisionEventTable 1}

SysDisconnectSupervisionEventEntry ::=
      SEQUENCE {
      sysDsEventIdx            Integer32,
      sysDsEventSlot           INTEGER,
	  sysDsEventTS			   Integer32,
	  sysDsEventDescr		   DisplayString,
	  sysDsEventDateAndTime	   DisplayString
        }

sysDsEventIdx OBJECT-TYPE
      SYNTAX  Integer32
      MAX-ACCESS  read-only
      STATUS  current
      DESCRIPTION
      "This object indicates a unique Event Index."
      ::= { sysDisconnectSupervisionEventEntry 1}

sysDsEventSlot OBJECT-TYPE
      SYNTAX  INTEGER
      {
      kmxIO1 (107),
      kmxIO2 (108),
      kmxIO3 (109),
      kmxIO4 (110),
      kmxIO5 (111),
      kmxIO6 (112),
      kmxIO7 (113),
      kmxIO8 (114),
      kmxIO9 (115),
      kmxIO10(116),
      kmxIO11(117),
      kmxIO12(118)
      }
      MAX-ACCESS  read-only
      STATUS  current
      DESCRIPTION
      "This object indicates a unique number of the slot position,
       where the KVF.6 or KVF.8 card is inserted, 
       and the Disconnect Supervision Event occurred."
      ::= { sysDisconnectSupervisionEventEntry 2}

sysDsEventTS OBJECT-TYPE
      SYNTAX  Integer32 (1..31)
      MAX-ACCESS  read-only
      STATUS  current
      DESCRIPTION
      "This object defines the Time Slot number, 
       where the Disconnect Supervision Event occurred."
      ::= { sysDisconnectSupervisionEventEntry 3}

sysDsEventDescr OBJECT-TYPE
      SYNTAX  DisplayString
      MAX-ACCESS  read-only
      STATUS  current
      DESCRIPTION
      "This object defines the Description
       of the Disconnect Supervision Event."
      ::= { sysDisconnectSupervisionEventEntry 4}

sysDsEventDateAndTime OBJECT-TYPE
      SYNTAX  DisplayString
      MAX-ACCESS  read-only
      STATUS  current
      DESCRIPTION
      "This object defines the Date and Time,
       when the Disconnect Supervision Event occurred.
       It will be displayed in the following format: YYYY-MM-DD HH:MM:SS."
      ::= { sysDisconnectSupervisionEventEntry 5}


mdlKmux  OBJECT IDENTIFIER  ::=  {kmux 2}

mdlKmxTable  OBJECT-TYPE
      SYNTAX SEQUENCE OF MdlKmxEntry
      MAX-ACCESS not-accessible
      STATUS current
	DESCRIPTION  "A table."
	::=  { mdlKmux 2 }

mdlKmxEntry OBJECT-TYPE
      SYNTAX MdlKmxEntry
      MAX-ACCESS not-accessible
      STATUS current
	DESCRIPTION  "An entry in table."
	INDEX { mdlKmxConfigIdx, mdlKmxSlotIdx  }
      ::= { mdlKmxTable 1}

MdlKmxEntry ::=
      SEQUENCE {
      mdlKmxConfigIdx         Integer32,
      mdlKmxSlotIdx           INTEGER,
      mdlKmxOperatedMl        INTEGER,
      mdlKmxMlAtoMlBPrio      INTEGER,
      mdlKmxMlBtoMlAPrio      INTEGER,
      mdlKmxOutSrvMethod      INTEGER,
      mdlKmxV54Config         INTEGER,
      mdlKmxTiming            INTEGER
      }

mdlKmxConfigIdx OBJECT-TYPE
      SYNTAX  Integer32 (1..255)
      MAX-ACCESS  read-only
      STATUS  current
      DESCRIPTION
      "This object indicates the Configuration number (1..255) 
       referred.
       Value of  255 specifies the TmpCnfg (Scratch).
       Write operation for the table entries is allowed only to 
       Config=255."
      ::= { mdlKmxEntry 1}

mdlKmxSlotIdx OBJECT-TYPE
      SYNTAX  INTEGER
       {
    kmxPsA (101),
    kmxPsB (102),
    kmxMlA (103),
    kmxMlB (104),
    kmxCl  (105),
    kmxOpt (106),
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118)
       }
      MAX-ACCESS  read-only
      STATUS  current
      DESCRIPTION
      "This object indicates a unique number of the slot position 
       in which the module is inserted."
      ::= { mdlKmxEntry 2}

mdlKmxOperatedMl OBJECT-TYPE
      SYNTAX  INTEGER {
                      notApplicable(1),
                      kmxMlA       (103),
                      kmxMlB       (104),
					  kmxMlAandMlB (119)    -- for KVF.6 and KMBE/NEW
        }
      MAX-ACCESS  read-write
      STATUS  current
      DESCRIPTION
      "The main link for this card.
       The field is relevant only for ML modes of Dual, Priority 
       Bumping and Switched Backup."
      ::= { mdlKmxEntry 3}

mdlKmxMlAtoMlBPrio OBJECT-TYPE
      SYNTAX  INTEGER {notApplicable(1),
                       low          (2),
                       high         (3)
        }
      MAX-ACCESS  read-write
      STATUS  current
      DESCRIPTION
      "ML-A to ML-B Priority.
       The field is relevant only for ML modes of Priority Bumping
       and Switched Backup."
      ::= { mdlKmxEntry 4}

mdlKmxMlBtoMlAPrio OBJECT-TYPE
      SYNTAX  INTEGER  {notApplicable(1),
                        low          (2),
                        high         (3)
        }
      MAX-ACCESS  read-write
      STATUS  current
      DESCRIPTION
      "ML-B to ML-A Priority.
       The field is relevant only for ML modes of Priority Bumping."
      ::= { mdlKmxEntry 5}

mdlKmxOutSrvMethod OBJECT-TYPE
      SYNTAX  INTEGER {notApplicable(1),
                    idleBusy     (2),
        forcedIdle   (3),
        busyIdle     (4),
        forcedBusy   (5)
        }
      MAX-ACCESS  read-write
      STATUS  current
      DESCRIPTION
      "Out of service method. For KVC.1 and KVC.1M all values are 
       applicable.
       For KVC.2, KVC.3, KVF.1, KVF.3, KVF.4: only forcedIdle and 
       forcedBusy are applicable."
      ::= { mdlKmxEntry 6}

mdlKmxV54Config OBJECT-TYPE
      SYNTAX  INTEGER {notApplicable(1),
                       dceDce       (2),
                       dceDte       (3),
                       dteDce       (4),
                       dteDte       (5)
                       } 
      MAX-ACCESS  read-write
      STATUS  current
      DESCRIPTION
      "Relevant only for KLS.1/New card."
      ::= { mdlKmxEntry 7}

mdlKmxTiming OBJECT-TYPE
      SYNTAX  INTEGER {notApplicable(1),
                       lt           (2),
                       nt           (3),
                       te           (4)
                       } 
      MAX-ACCESS  read-only
      STATUS  current
      DESCRIPTION
      "Applicable only for KHSU.1, KHSU.2, KVF.4/S0, KVC.3/S0 cards.
       lt - local timing
       nt - network timing
       te - terminal equipment "
      ::= { mdlKmxEntry 8}




mdlKvf5PbxTable  OBJECT-TYPE
      SYNTAX SEQUENCE OF MdlKvf5PbxEntry
      MAX-ACCESS not-accessible
      STATUS  current
      DESCRIPTION
      "Parameters specific to KVF.5, KVF.6 and KVF.8 PBX cards."
      ::= { mdlKmux 3 }

mdlKvf5PbxEntry OBJECT-TYPE
      SYNTAX MdlKvf5PbxEntry
      MAX-ACCESS not-accessible
      STATUS current
	DESCRIPTION  "An entry in table."
	INDEX { mdlKvf5PbxConfigIdx, mdlKvf5PbxSlotIdx  }
      ::= { mdlKvf5PbxTable 1}

MdlKvf5PbxEntry ::=
      SEQUENCE {
      mdlKvf5PbxConfigIdx         Integer32,
      mdlKvf5PbxSlotIdx           INTEGER,
      mdlKvf5PbxSig               INTEGER,
      mdlKvf5PbxSigMode           INTEGER,
      mdlKvf5PbxTsAssign          INTEGER,
      mdlKvf5PbxCcsTs             Integer32,
      mdlKvf5PbxOos               INTEGER,
      mdlKvf5PbxSigTxPbx          INTEGER,
      mdlKvf5PbxSigRxPbx          INTEGER,
      mdlKvf5PbxDefABCD           OCTET STRING,
      mdlKvf5PbxFramerSlot        INTEGER,
	  mdlKvf5PbxCcsRate           INTEGER,
	  mdlKvf5PbxTxAbcdBit         OCTET STRING,
      mdlKvf5PbxHdlcCrc           INTEGER			
     }

mdlKvf5PbxConfigIdx OBJECT-TYPE
      SYNTAX  Integer32 (1..255)
      MAX-ACCESS  read-only
      STATUS  current
      DESCRIPTION
      "This object indicates the Configuration number (1..255) 
       referred.
       Value of  255 specifies the TmpCnfg (Scratch).
       Write operation for the table entries is allowed only to 
       Config=255."
      ::= { mdlKvf5PbxEntry 1}

mdlKvf5PbxSlotIdx OBJECT-TYPE
      SYNTAX  INTEGER
       {
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118)
       }
      MAX-ACCESS  read-only
      STATUS  current
      DESCRIPTION
      "This object indicates a unique number of the slot position 
       in which the module is inserted."
      ::= { mdlKvf5PbxEntry 2}

mdlKvf5PbxSig OBJECT-TYPE
      SYNTAX  INTEGER { 
        notApplicable(1),      
        a    (2),
        aANDb(3),
        b    (4),
        ccs  (5),
		cas  (6)
        }
      MAX-ACCESS  read-write
      STATUS  current
      DESCRIPTION
      "Signaling  type.
       When 'mdlKvf5PbxSig' is valid, 'mdlKvf5PbxSigTxPbx' and 'mdlKvf5PbxSigRxPbx' 
       are not valid.
       mdlKvf5PbxSig  - is supported by KVF.5 OLD SW ver and KVF.6 card.
       mdlKvf5PbxSigTxPbx and mdlKvf5PbxSigRxPbx - are supported by KVF.5 NEW SW ver
       and KVF.6."
      ::= { mdlKvf5PbxEntry 3}

mdlKvf5PbxSigMode OBJECT-TYPE
      SYNTAX  INTEGER {
        notApplicable(1),      
        direct (2),
        inverse(3)
        }
      MAX-ACCESS  read-write
      STATUS  current
      DESCRIPTION
      "Signaling Mode."
	  ::= { mdlKvf5PbxEntry 4}

mdlKvf5PbxTsAssign OBJECT-TYPE
      SYNTAX  INTEGER {
        s1s2s3s4     (2),
        s5s6s7s8     (3),
        s9s10s11s12  (4),
        s13s14s15s16 (5),
        s17s18s19s20 (6),
        s21s22s23s24 (7),

        s13s14s15s17 (8),
        s18s19s20s21 (9),
        s22s23s24s25(10),
        s26s27s28s29(11),
        s30s31      (12)
        }
      MAX-ACCESS  read-write
      STATUS  current
      DESCRIPTION
      "Ts Assignment group. Each KVF.5 card of the Mux should have 
       a different value.
       For KVF.5/E1 values: 2,3,4,8,9,10,11,12 are applicable.
       For KVF.5/T1 values: 2,3,4,5,6,7  are applicable."
      ::= { mdlKvf5PbxEntry 5}

mdlKvf5PbxCcsTs  OBJECT-TYPE
      SYNTAX  Integer32
      MAX-ACCESS  read-write
      STATUS  current
      DESCRIPTION
      "CCS TS of the KVF.5/T1/E1 and KVF.6/T1/E1 card.
       It is applicable for Kmux KVF.5 Framer cards and KVF.6 cards
       when mdlKvf5PbxSig=ccs.
       Valid values:
       1..24 - CCS TS of T1
       1..31 - CCS TS of E1
       255   - notApplicable (for agents that do not support this 
               feature or for irrelevant cards)
    Other values are invalid.
    The value selected should not be the same as one of the TSs assigned for
    any card of the same group via mdlKvf5PbxTsAssign."
      ::= { mdlKvf5PbxEntry 6}

mdlKvf5PbxOos  OBJECT-TYPE
      SYNTAX  INTEGER
       {
        notSupported  (2),
        forcedIdle    (3),
        forcedBusy    (4)
       }
      MAX-ACCESS  read-write
      STATUS  current
      DESCRIPTION
      "'idle' = '0' = on-hook, idle state
       'busy' = '1' = off-hook, busy state
       'forcedIdle' = SP = both A and B signaling bits are forced
                      to '0' during out-of-service periods.
       'forcedBusy' = MK = both A and B signaling bits are forced
                      to '1' during out-of-service periods.
       - for T1:    '0'=0   ;  '1'=1                         
       - for E1:    '0'=1   ;  '1'=0   "
   ::= { mdlKvf5PbxEntry 7}

mdlKvf5PbxSigTxPbx  OBJECT-TYPE
      SYNTAX  INTEGER
       {
        notApplicable(1),      
        a            (2), 
        b            (3),
        aANDb        (4),
        crossAandB   (5),
        ccs          (6),
		aEqualsB     (7) 
       }
      MAX-ACCESS  read-write
      STATUS  current
      DESCRIPTION
      "TxPbx signaling means transmit signaling from KM to PBX (KM-->PBX)
       When 'mdlKvf5PbxSigTxPbx' is valid, 'mdlKvf5PbxSig' field is not valid. 
       mdlKvf5PbxSig  - is supported by KVF.5 OLD SW ver.
       mdlKvf5PbxSigTxPbx and mdlKvf5PbxSigRxPbx - are supported by KVF.5 NEW SW ver."
   ::= { mdlKvf5PbxEntry 8}

mdlKvf5PbxSigRxPbx  OBJECT-TYPE
      SYNTAX  INTEGER
       {
        notApplicable(1),      
        a            (2), 
        b            (3),
        aANDb        (4),
        ccs          (6)
       }
      MAX-ACCESS  read-write
      STATUS  current
      DESCRIPTION
      "RxPbx signaling means receive signaling from PBX to KM (PBX-->KM-->KM)
       When 'mdlKvf5PbxSigRxPbx' is valid, 'mdlKvf5PbxSig' field is not valid. 
       mdlKvf5PbxSig - is supported by KVF.5 OLD SW ver.
       mdlKvf5PbxSigTxPbx and mdlKvf5PbxSigRxPbx - are supported by KVF.5 NEW SW ver."
   ::= { mdlKvf5PbxEntry 9}

mdlKvf5PbxDefABCD  OBJECT-TYPE
      SYNTAX  OCTET STRING (SIZE (0..1))
      MAX-ACCESS  read-write
      STATUS  current
      DESCRIPTION
      "This object determines what KM will send for the ABCD Bits that
       are not 'filled' by the dynamic signaling. This field is applicable
       only for  signaling transmit to PBX ('mdlKvf5PbxSigTxPbx'). 
       For KVF.5 cards: valid range (00 - 0F HEX) - ABCD Bits."
   ::= { mdlKvf5PbxEntry 10}

mdlKvf5PbxFramerSlot  OBJECT-TYPE
      SYNTAX  INTEGER
       { 
        kmxIO1 (107),
        kmxIO2 (108),                        
        kmxIO3 (109),
        kmxIO4 (110),
        kmxIO5 (111),
        kmxIO6 (112),
        kmxIO7 (113),
        kmxIO8 (114),
        kmxIO9 (115),
        kmxIO10(116),
        kmxIO11(117),
        kmxIO12(118),
        notApplicable (255)
       }
      MAX-ACCESS  read-write
      STATUS  current
      DESCRIPTION
      "This object indicates the Framer's slot number this card belongs to.
       Several cards having the same mdlKvf5PbxFramerSlot value, work together
       as a group."
   ::= { mdlKvf5PbxEntry 11}

mdlKvf5PbxCcsRate  OBJECT-TYPE
      SYNTAX  INTEGER
       {
	   notConnected(1),
       bps4800(2),
	   bps6400(3),
       bps9600(4),
	   bps12800(5),
       bps16000(6),
	   bps19200(7),
       bps32000(8),
       bps64000(9)
       }
      MAX-ACCESS  read-write
      STATUS  current
      DESCRIPTION
      "Determines the Ccs speed - for KVF.6 and KVF.5 cards."
   ::= { mdlKvf5PbxEntry 12}

mdlKvf5PbxTxAbcdBit OBJECT-TYPE
      SYNTAX  OCTET STRING
      MAX-ACCESS  read-write
      STATUS  current
      DESCRIPTION
      "This object is applicable only for KVF.6 and KVF.8 cards, when mdlKvf5PbxSig=cas(6).
       It represents 4 parameters, by 2 Octets :
       D Bit Code-MSB nibble,
       C Bit Code-    nibble,
       B Bit Code-    nibble,
       A Bit Code-LSB nibble.

       Each of A,B,C,D Bit Code nibble represents:
    0 hex = 0000 = 0
    1 hex = 0001 = 1
    2 hex = 0010 = A bit
    3 hex = 0011 = B bit
    4 hex = 0100 = C bit
    5 hex = 0101 = D bit
    6 hex = 0110 = A bit inverse
    7 hex = 0111 = B bit inverse
    8 hex = 1000 = C bit inverse
    9 hex = 1001 = D bit inverse
    A-E hex - not used (invalid values)
    
    When the object is not applicable, 0 Octets will be sent."
      ::= { mdlKvf5PbxEntry 13}

mdlKvf5PbxHdlcCrc  OBJECT-TYPE
      SYNTAX  INTEGER
       {
	   notApplicable(1),
       crc16(2),
	   crc32(3)
       }
      MAX-ACCESS  read-write
      STATUS  current
      DESCRIPTION
      "Determines the CRC type of HDLC protocol, that CCS signaling 
       is working with. Applicable for KVF.6 cards when Signaling
       is CCS (only)."
   ::= { mdlKvf5PbxEntry 14}



-- Disconnect Supervision (Ds) Table.
-- Applicable for KVF.6 and KVF.8 cards.

mdlDisconnectSupervisionTable  OBJECT-TYPE
      SYNTAX SEQUENCE OF MdlDisconnectSupervisionEntry
      MAX-ACCESS not-accessible
      STATUS current
	  DESCRIPTION  "Disconnect Supervision table."
	::=  { mdlKmux 4 }

mdlDisconnectSupervisionEntry OBJECT-TYPE
      SYNTAX MdlDisconnectSupervisionEntry
      MAX-ACCESS not-accessible
      STATUS current
	  DESCRIPTION  "An entry in the table."
	  INDEX { mdlDsConfigIdx, mdlDsSlotIdx  }
    ::= { mdlDisconnectSupervisionTable 1}

MdlDisconnectSupervisionEntry ::=
      SEQUENCE {
      mdlDsConfigIdx           Integer32,
      mdlDsSlotIdx             INTEGER,
      mdlDs                    INTEGER,
	  mdlDsUserLoc             INTEGER,
	  mdlDsMode                INTEGER,
	  mdlDsSilence             Integer32,
	  mdlDsClrFwSig            OCTET STRING,
	  mdlDsAnswerSig           OCTET STRING,
	  mdlDsClrBwSig            OCTET STRING,
	  mdlDsFbtLowFreq          Integer32,
	  mdlDsFbtHighFreq         Integer32,
	  mdlDsFbtTimeOn1          Integer32,
	  mdlDsFbtTimeOff1         Integer32,
	  mdlDsFbtTimeOn2          Integer32,
	  mdlDsFbtTimeOff2         Integer32,
	  mdlDsFbtLowFreqLevel     Integer32,
	  mdlDsFbtHighFreqLevel    Integer32
     }

mdlDsConfigIdx OBJECT-TYPE
      SYNTAX  Integer32 (1..255)
      MAX-ACCESS  read-only
      STATUS  current
      DESCRIPTION
      "This object indicates the Configuration number (1..255) 
       referred.
       Value of 255 specifies the TmpCnfg (Scratch).
       Write operation for the table entries is allowed only to 
       Config=255."
      ::= { mdlDisconnectSupervisionEntry 1}

mdlDsSlotIdx OBJECT-TYPE
      SYNTAX  INTEGER
      {
      kmxIO1 (107),
      kmxIO2 (108),
      kmxIO3 (109),
      kmxIO4 (110),
      kmxIO5 (111),
      kmxIO6 (112),
      kmxIO7 (113),
      kmxIO8 (114),
      kmxIO9 (115),
      kmxIO10(116),
      kmxIO11(117),
      kmxIO12(118)
      }
      MAX-ACCESS  read-only
      STATUS  current
      DESCRIPTION
      "This object indicates a unique number of the slot position 
       in which the module is inserted."
      ::= { mdlDisconnectSupervisionEntry 2}

mdlDs OBJECT-TYPE
      SYNTAX  INTEGER
      {
      disable                    (1),
      remoteDisconnect           (2),
      remoteDisconnectAndSilence (3),
      silenceOnly                (4),
      fastBusyOnly               (5),
      silenceOrFastBusy          (6)
      }
      MAX-ACCESS  read-write
      STATUS  current
      DESCRIPTION
      "This object defines which terms will cause disconnection of call.
       disable = the Disconnect Supervision feature is disabled. In this case,
       all other objects of this table are irrelevant.

       Remote Sanity - 
       If mdlDsUserLoc = Remote Location , the valid values are :
       disable(1), silenceOnly(4), fastBusyOnly(5), silenceOrFastBusy(6).
       If mdlDsUserLoc = Local , the valid values are 
       disable(1), remoteDisconnect(2), remoteDisconnectAndSilence (3)."

      ::= { mdlDisconnectSupervisionEntry 3}

mdlDsUserLoc OBJECT-TYPE
      SYNTAX  INTEGER
      {
      notApplicable (1),
      remote        (2),
      local         (3)
      }
      MAX-ACCESS  read-write
      STATUS  current
      DESCRIPTION
      "User located in local or remote station.
	   Local station will disconnect the call actually if needed.
	   Applicable only if Disconnect Supervision (mdlDs) is different from disable.
	   Should be a Sanity check between the mdlDs and the mdlDsUserLoc parameters (see mdlDs)."
      ::= { mdlDisconnectSupervisionEntry 4}

mdlDsMode OBJECT-TYPE
      SYNTAX  INTEGER
      {
      notApplicable (1),
      reportOnly    (2),
      disconnect    (3)
      }
      MAX-ACCESS  read-write
      STATUS  current
      DESCRIPTION
      "This object defines the action, which will be done after remote disconnect occurred.
	   This object is relevant only when mdlDsUserLoc = local(3).
       Applicable only if Disconnect Supervision (mdlDs) is different from disable 
       AND User Location (mdlDsUserLoc) = local(3)."
      ::= { mdlDisconnectSupervisionEntry 5}

mdlDsSilence OBJECT-TYPE
      SYNTAX  Integer32
      MAX-ACCESS  read-write
      STATUS  current
      DESCRIPTION 
      "This object defines the silence period needed for an indication (seconds).
       Applicable only if Disconnect Supervision (mdlDs) is different from disable
	   AND includes 'Silence', i.e. is one of the following:
	   remoteDisconnectAndSilence(3), silenceOnly(4), silenceOrFastBusy(6).
       Valid values: 0,20,40..(every 20 seconds)..300, 0 = notApplicable.
       notApplicable = silence disabled when mdlDs doesn't include 'silence'."
      ::= { mdlDisconnectSupervisionEntry 6}

mdlDsClrFwSig OBJECT-TYPE
      SYNTAX  OCTET STRING
      MAX-ACCESS  read-write
      STATUS  current
      DESCRIPTION
      "This object defines the Clear FWD Signal (A,B,C,D bits) for KVF.6 cards.
       This object is an indication of Near PBX to the Far PBX, 
       that it wants to disconnect the call.
       Applicable only if Disconnect Supervision (mdlDs) is different from disable.
       Applicable only for KVF.6 cards.
       
       It represents 4 parameters, by an Octet:
	   ( Bit 7 = MSB, Bit 0 = LSB )
       D Bit - bits 6,7 of the MSB nibble,
	   C Bit - bits 4,5 of the MSB nibble,
	   B Bit - bits 2,3 of the LSB nibble,
	   A Bit - bits 0,1 of the LSB nibble.     
       
       For each of A,B,C,D Bits:
       00 = 0,
       01 = 1,
       10 = reserved,
       11 = x.

	   For A,B Bits - only one of them can be 'x' (not both at the same time).
	   For C,D Bits - 'x' won't be in use.
       
       When the object is not applicable, a 0 Octet will be sent."
      ::= { mdlDisconnectSupervisionEntry 7}

mdlDsAnswerSig OBJECT-TYPE
      SYNTAX  OCTET STRING
      MAX-ACCESS  read-write
      STATUS  current
      DESCRIPTION
      "This object defines the Clear FWD Signal (A,B,C,D bits) for KVF.6 cards.
       This object is an indication of Near PBX to the Far PBX,
	   taht a call is present now on the line.
       Applicable only if Disconnect Supervision (mdlDs) is different from disable.
       Applicable only for KVF.6 cards.
       
       It represents 4 parameters, by an Octet:
	   ( Bit 7 = MSB, Bit 0 = LSB )
       D Bit - bits 6,7 of the MSB nibble,
	   C Bit - bits 4,5 of the MSB nibble,
	   B Bit - bits 2,3 of the LSB nibble,
	   A Bit - bits 0,1 of the LSB nibble.     
       
       For each of A,B,C,D Bits:
       00 = 0,
       01 = 1,
       10 = reserved,
       11 = x.

	   For A,B Bits - only one of them can be 'x' (not both at the same time).
	   For C,D Bits - 'x' won't be in use.
       
       When the object is not applicable, a 0 Octet will be sent."
      ::= { mdlDisconnectSupervisionEntry 8}

mdlDsClrBwSig OBJECT-TYPE
      SYNTAX  OCTET STRING
      MAX-ACCESS  read-write
      STATUS  current
      DESCRIPTION
      "This object defines the Clear FWD Signal (A,B,C,D bits) for KVF.6 cards.
       This object is an indication of Far PBX to the Near PBX,
	   that the call was disconnected (on the Far side).
       Applicable only if Disconnect Supervision (mdlDs) is different from disable.
       Applicable only for KVF.6 cards.
       
       It represents 4 parameters, by an Octet:
	   ( Bit 7 = MSB, Bit 0 = LSB )
       D Bit - bits 6,7 of the MSB nibble,
	   C Bit - bits 4,5 of the MSB nibble,
	   B Bit - bits 2,3 of the LSB nibble,
	   A Bit - bits 0,1 of the LSB nibble.     
       
       For each of A,B,C,D Bits:
       00 = 0,
       01 = 1,
       10 = reserved,
       11 = x.

	   For A,B,C,D Bits - 'x' won't be in use.
       
       When the object is not applicable, a 0 Octet will be sent."
      ::= { mdlDisconnectSupervisionEntry 9}

mdlDsFbtLowFreq OBJECT-TYPE
      SYNTAX  Integer32
      MAX-ACCESS  read-write
      STATUS  current
      DESCRIPTION
      "First frequency in Fast Busy Tone (Fbt) combination (Hz).
       Valid values: 0..4000,4095. 4095 = notApplicable.
       Available only if Disconnect Supervision (mdlDs) is different from disable
	   AND includes 'Tones' (Fast Busy), i.e. is one of the following:
	   fastBusyOnly(5), silenceOrFastBusy(6)."
      ::= { mdlDisconnectSupervisionEntry 10}

mdlDsFbtHighFreq OBJECT-TYPE
      SYNTAX  Integer32
      MAX-ACCESS  read-write
      STATUS  current
      DESCRIPTION
      "Second frequency in Fast Busy Tone (Fbt) combination (Hz).
       Valid values: 0..4000,4095. 4095 = notApplicable.
       Available only if Disconnect Supervision (mdlDs) is different from disable
	   AND includes 'Tones' (Fast Busy), i.e. is one of the following:
	   fastBusyOnly(5), silenceOrFastBusy(6)."
      ::= { mdlDisconnectSupervisionEntry 11}

mdlDsFbtTimeOn1 OBJECT-TYPE
      SYNTAX  Integer32
      MAX-ACCESS  read-write
      STATUS  current
      DESCRIPTION
      "This object defines the Time On 1 cadence (in msec).
       Valid values: 0,10,20..(every 10 msec)..10000,10230. 
       0 = disable, 10230 = notApplicable.
       Available only if Disconnect Supervision (mdlDs) is different from disable
	   AND includes 'Tones' (Fast Busy), i.e. is one of the following:
	   fastBusyOnly(5), silenceOrFastBusy(6)."
      ::= { mdlDisconnectSupervisionEntry 12}

mdlDsFbtTimeOff1 OBJECT-TYPE
      SYNTAX  Integer32
      MAX-ACCESS  read-write
      STATUS  current
      DESCRIPTION
      "This object defines the Time Off 1 cadence (in msec).
       Valid values: 0,10,20..(every 10 msec)..10000,10230.
	   0 = disable, 10230 = notApplicable.
	   Available only if Disconnect Supervision (mdlDs) is different from disable
	   AND includes 'Tones' (Fast Busy), i.e. is one of the following:
	   fastBusyOnly(5), silenceOrFastBusy(6)."
      ::= { mdlDisconnectSupervisionEntry 13}

mdlDsFbtTimeOn2 OBJECT-TYPE
      SYNTAX  Integer32
      MAX-ACCESS  read-write
      STATUS  current
      DESCRIPTION
      "This object defines the Time On 2 cadence (in msec).
       Valid values: 0,10,20..(every 10 msec)..10000,10230.
	   0 = disable, 10230 = notApplicable.
	   Available only if Disconnect Supervision (mdlDs) is different from disable
	   AND includes 'Tones' (Fast Busy), i.e. is one of the following:
	   fastBusyOnly(5), silenceOrFastBusy(6)."
      ::= { mdlDisconnectSupervisionEntry 14}

mdlDsFbtTimeOff2 OBJECT-TYPE
      SYNTAX  Integer32
      MAX-ACCESS  read-write
      STATUS  current
      DESCRIPTION
      "This object defines the Time Off 2 cadence (in msec).
       Valid values: 0,10,20..(every 10 msec)..10000,10230.
	   0 = disable, 10230 = notApplicable.
	   Available only if Disconnect Supervision (mdlDs) is different from disable
	   AND includes 'Tones' (Fast Busy), i.e. is one of the following:
	   fastBusyOnly(5), silenceOrFastBusy(6)."
      ::= { mdlDisconnectSupervisionEntry 15}

mdlDsFbtLowFreqLevel OBJECT-TYPE
      SYNTAX  Integer32
      MAX-ACCESS  read-write
      STATUS  current
      DESCRIPTION
      "First frequency level for Fast Busy Tone (Fbt) in dBm units.
       Valid values: -32..31.
       Available only if Disconnect Supervision (mdlDs) is different from disable
	   AND includes 'Tones' (Fast Busy), i.e. is one of the following:
	   fastBusyOnly(5), silenceOrFastBusy(6)."
      ::= { mdlDisconnectSupervisionEntry 16}

mdlDsFbtHighFreqLevel OBJECT-TYPE
      SYNTAX  Integer32
      MAX-ACCESS  read-write
      STATUS  current
      DESCRIPTION
      "Second frequency level for Fast Busy Tone (Fbt) in dBm units.
       Valid values: -32..31.
       Available only if Disconnect Supervision (mdlDs) is different from disable
	   AND includes 'Tones' (Fast Busy), i.e. is one of the following:
	   fastBusyOnly(5), silenceOrFastBusy(6)."
      ::= { mdlDisconnectSupervisionEntry 17}


prtKmux  OBJECT IDENTIFIER  ::=  {kmux 3}

prtMainLink  OBJECT IDENTIFIER  ::=  {prtKmux 1}

prtMlFrameStatsTable  OBJECT-TYPE
      SYNTAX SEQUENCE OF PrtMlFrameStatsEntry
      MAX-ACCESS not-accessible
      STATUS  current
      DESCRIPTION
      "Frame diagnostics for the main links."
      ::= { prtMainLink 1 }

prtMlFrameStatsEntry OBJECT-TYPE
      SYNTAX PrtMlFrameStatsEntry
      MAX-ACCESS not-accessible
      STATUS current
	DESCRIPTION  "An entry in table."
	INDEX { prtMlFrameIdx }
      ::= { prtMlFrameStatsTable 1}

PrtMlFrameStatsEntry ::=
     SEQUENCE {
  prtMlFrameIdx           Integer32,
  prtMlFrameSlt           INTEGER,
  prtMlBitWeight          INTEGER,
  prtMlDataUsage          Integer32,
  prtMlControlSig         Integer32,
  prtMlDownload           Integer32,
  prtMlSync               Integer32,
  prtMlTotalUsage         Integer32,
  prtMlTotalFree          Integer32 
	}

prtMlFrameIdx OBJECT-TYPE
      SYNTAX  Integer32
      MAX-ACCESS  read-only
      STATUS  current
      DESCRIPTION
      "The prtGenPrtIdx index of this link.
       Slot*100+1."
      ::= { prtMlFrameStatsEntry 1}

prtMlFrameSlt     OBJECT-TYPE
      SYNTAX  INTEGER
       {
       kmxMlA  (103),
       kmxMlB  (104)
       }
      MAX-ACCESS  read-only
      STATUS  current
      DESCRIPTION
      "This attribute indicates a unique number to identify the slot 
       where the ML card is inserted."
      ::= { prtMlFrameStatsEntry 2}

prtMlBitWeight     OBJECT-TYPE
      SYNTAX  INTEGER
       {
       bps400  (1),
       bps800  (2),
       bps1600 (3),
       bps3200 (4),
	   bps6400 (5)
       }
      MAX-ACCESS  read-only
      STATUS  current
      DESCRIPTION
      "This attribute indicates the Bit Weight [bps/bit] used for
       the selected prtMlFrameSlt. The Bit Weight is according to 
       the ML Speed."
      ::= { prtMlFrameStatsEntry 3}

prtMlDataUsage OBJECT-TYPE
      SYNTAX  Integer32
      MAX-ACCESS  read-only
      STATUS  current
      DESCRIPTION
      "Data usage in [bits].
       In order to convert it to 'bps' units, the 'bits' should be multiplied
       by prtMlBitWeight value."
      ::= { prtMlFrameStatsEntry 4}

prtMlControlSig OBJECT-TYPE
      SYNTAX  Integer32
      MAX-ACCESS  read-only
      STATUS  current
      DESCRIPTION
      "Control Signals usage of the ML in [bits].
       In order to convert it to 'bps' units, the 'bits' should be multiplied
       by prtMlBitWeight value."
      ::= { prtMlFrameStatsEntry 5}

prtMlDownload OBJECT-TYPE
      SYNTAX  Integer32
      MAX-ACCESS  read-only
      STATUS  current
      DESCRIPTION
      "Download bandwidth usage of the ML in [bits].
       In order to convert it to 'bps' units, the 'bits' should be multiplied
       by prtMlBitWeight value."
      ::= { prtMlFrameStatsEntry 6}

prtMlSync OBJECT-TYPE
      SYNTAX  Integer32
      MAX-ACCESS  read-only
      STATUS  current
      DESCRIPTION
      "Sync bandwidth usage of the ML in [bits].
       In order to convert it to 'bps' units, the 'bits' should be multiplied
       by prtMlBitWeight value."
      ::= { prtMlFrameStatsEntry 7}

prtMlTotalUsage OBJECT-TYPE
      SYNTAX  Integer32
      MAX-ACCESS  read-only
      STATUS  current
      DESCRIPTION
      "Total bandwidth usage of the ML in [bits].
       In order to convert it to 'bps' units, the 'bits' should be multiplied
       by prtMlBitWeight value."
      ::= { prtMlFrameStatsEntry 8}

prtMlTotalFree OBJECT-TYPE
      SYNTAX  Integer32
      MAX-ACCESS  read-only
      STATUS  current
      DESCRIPTION
      "Free bandwidth of the ML in [bits].
       In order to convert it to 'bps' units, the 'bits' should be multiplied
       by prtMlBitWeight value."
      ::= { prtMlFrameStatsEntry 9}


prtMlTable  OBJECT-TYPE
      SYNTAX SEQUENCE OF PrtMlEntry
      MAX-ACCESS not-accessible
      STATUS  current
      DESCRIPTION
      "Parameters for the main links. 
       KML.1 - KML.6, KML.7(T1), KML.8(E1), KML.10(ISDN) and 
       KML.F(KML.11 Fiber-optic)."
      ::= { prtMainLink 2 }

prtMlEntry OBJECT-TYPE
      SYNTAX PrtMlEntry
      MAX-ACCESS not-accessible
      STATUS current
	DESCRIPTION  "An entry in table."
	INDEX { prtMlCnfgIdx, prtMlIdx }
      ::= { prtMlTable 1}

PrtMlEntry ::=
     SEQUENCE {
  prtMlCnfgIdx  Integer32,
  prtMlIdx           Integer32,
  prtMlSlt           INTEGER,
  prtMlTiming        INTEGER,
  prtMlBufferSize    INTEGER,
  prtMlDsrCts        INTEGER,
  prtMlSpeed         INTEGER,
  prtMlStartTS       Integer32,
  prtMlBypassTs16    INTEGER,
  prtMlCallMode      INTEGER,
  prtMlBondingEnable INTEGER
  }

prtMlCnfgIdx OBJECT-TYPE
      SYNTAX  Integer32 (1..255)
      MAX-ACCESS  read-only
      STATUS  current
      DESCRIPTION
      "This attribute indicates the Idx of the Config being accessed.
       Idx of 255 relates to the Temporary (Scratch) Config.
       Write operation for the table entries is allowed only to 
       Config=255. "
      ::= { prtMlEntry 1}

prtMlIdx OBJECT-TYPE
      SYNTAX  Integer32
      MAX-ACCESS  read-only
      STATUS  current
      DESCRIPTION
   "The prtGenPrtIdx index of this link.
    Slot*100+1 ."
      ::= { prtMlEntry 2}

prtMlSlt     OBJECT-TYPE
      SYNTAX  INTEGER
       {
     kmxMlA  (103),
     kmxMlB  (104)
       }
      MAX-ACCESS  read-only
      STATUS  current
      DESCRIPTION
      "This attribute indicates a unique number to identify the slot where
       the ML card is inserted in."
      ::= { prtMlEntry 3}

prtMlTiming     OBJECT-TYPE
      SYNTAX  INTEGER
       {
    notApplicable(1),
       dte   (2),
       dce   (3),
       eDce  (4),
       int   (5),
       lbt   (6),
	   adaptive (7)
       }
      MAX-ACCESS  read-write
      STATUS  current
      DESCRIPTION
      "The clock source for this link.
       For KML.1-KML.4, valid values: dte, eDce, or dce. 
       For KML.5-KML.8, valid values: int or lbt.
       notApplicable - for KML.10 and KML.F."
      ::= { prtMlEntry 4}

prtMlBufferSize     OBJECT-TYPE
      SYNTAX  INTEGER
       {
       notApplicable(1),
       bits8        (2),
       bits256      (3)
       }
      MAX-ACCESS  read-write
      STATUS  current
      DESCRIPTION
      "The buffer size in bits for absorbing timing jitters."
      ::= { prtMlEntry 5}

prtMlDsrCts     OBJECT-TYPE
      SYNTAX  INTEGER
       {
       notApplicable(1),
       internal     (2),
       external     (3)
       }
      MAX-ACCESS  read-write
      STATUS  current
      DESCRIPTION
      "Determines the DSR and CTS signal handling.
       notApplicable - for KML.4-KML.6."
      ::= { prtMlEntry 6}

prtMlSpeed     OBJECT-TYPE
      SYNTAX  INTEGER
       {
       bps9600(2),
       bps14400(3),
       bps19200(4),
       bps28800(5),
       bps32000(6),
       bps48000(7),
       bps56000(8),
       bps64000(9),
       bps128000(10),
       bps192000(11),
       bps256000(12),
       bps384000(13),
       bps512000(14),
       bps768000(15),
	   bps1024000(16),
	   bps1536000(17)
       }
      MAX-ACCESS  read-write
      STATUS  current
      DESCRIPTION
      "Determines the Main Link port speed.
       KML.1, KML.3, KML.4 support (Kbps): 9.6, 14.4, 19.2, 28.8, 32, 48, 56,
                                          64, 128, 192, 256, 384, 512, 768, 1024, 1536.
	   KML.2 supports (Kbps): 9.6, 14.4, 19.2, 28.8, 32, 48, 56, 64, 128
	   KML.5 supports (Kbps): 64, 128.
       KML.6 supports (Kbps): 9.6, 19.2, 56.
    KML.7-KML.8 support (Kbps): 56, 64, 128, 192, 256, 384, 512, 
                                768, 1024, 1536.
    KML.10 supports (Kbps): 64, 128.
    KML.F  supports (Kbps): 128, 256, 384, 512, 768, 1024, 1536."
      ::= { prtMlEntry 7}

prtMlStartTS     OBJECT-TYPE
      SYNTAX  Integer32  (0..31)
      MAX-ACCESS  read-write
      STATUS  current
      DESCRIPTION
      "0=notApplicable - for all cards except  KML.7, KML.8
       For KML.7 - valid values: 1..24
       For KML.8 - valid values: 1..31."
      ::= { prtMlEntry 8}

prtMlBypassTs16     OBJECT-TYPE
      SYNTAX  INTEGER  { 
                 notApplicable(1), 
                 no           (2), 
                 yes          (3) 
                 }
      MAX-ACCESS  read-write
      STATUS  current
      DESCRIPTION
      "notApplicable - for all cards except KML.8."
      ::= { prtMlEntry 9}

prtMlCallMode     OBJECT-TYPE
      SYNTAX  INTEGER  { 
                 notApplicable(1), 
                 initiate     (2), 
                 listen       (3) 
                 }
      MAX-ACCESS  read-write
      STATUS  current
      DESCRIPTION
      "This object will be used when using an external modem linked to the 
       KML.1-KML.4 or KML.10 cards.
       Initiate - KML card can initiate calls to the modem
       Listen   - KML card listens only ; cannot initiate a call."
      ::= { prtMlEntry 10}

prtMlBondingEnable     OBJECT-TYPE
      SYNTAX  INTEGER  { 
                 notApplicable(1), 
                 disabled     (2), 
                 enabled      (3) 
                 }
      MAX-ACCESS  read-write
      STATUS  current
      DESCRIPTION
      "Disable/Enable applying the Bonding process, for KML.10 cards.
       notApplicable - for all cards except KML.10."
      ::= { prtMlEntry 11}

 
prtMlIsdnTable  OBJECT-TYPE
      SYNTAX SEQUENCE OF PrtMlIsdnEntry
      MAX-ACCESS not-accessible
      STATUS  current
      DESCRIPTION
      "Parameters for ISDN main links: KML.10."
      ::= { prtMainLink 3 }

prtMlIsdnEntry OBJECT-TYPE
      SYNTAX PrtMlIsdnEntry
      MAX-ACCESS not-accessible
      STATUS current
	DESCRIPTION  "An entry in table."
	INDEX { prtMlIsdnCnfgIdx, prtMlIsdnIdx }
      ::= { prtMlIsdnTable 1}

PrtMlIsdnEntry ::=
     SEQUENCE {
  prtMlIsdnCnfgIdx       Integer32,
  prtMlIsdnIdx           Integer32,
  prtMlIsdnSlt           INTEGER,
  prtMlIsdnMode          INTEGER,
  prtMlIsdnStandard       INTEGER,
  prtMlIsdnLocSubNum      DisplayString,
  prtMlIsdnLocNum         DisplayString,
  prtMlIsdnOutSubNum      DisplayString,
  prtMlIsdnBackupCallNum  DisplayString,
  prtMlIsdnInNumMode      INTEGER
  }

prtMlIsdnCnfgIdx OBJECT-TYPE
      SYNTAX  Integer32 (1..255)
      MAX-ACCESS  read-only
      STATUS  current
      DESCRIPTION
      "This attribute indicates the Idx of the Config being accessed.
       Idx of 255 relates to the Temporary (Scratch) Config. 
       Write operation for the table entries is allowed only to 
       Config=255. "
      ::= { prtMlIsdnEntry 1}

prtMlIsdnIdx OBJECT-TYPE
      SYNTAX  Integer32
      MAX-ACCESS  read-only
      STATUS  current
      DESCRIPTION
   "The prtGenPrtIdx index of this link.
    Slot*100+1 ."
      ::= { prtMlIsdnEntry 2}

prtMlIsdnSlt     OBJECT-TYPE
      SYNTAX  INTEGER
       {
           kmxMlA  (103),
           kmxMlB  (104)
       }
      MAX-ACCESS  read-only
      STATUS  current
      DESCRIPTION
      "This attribute indicates a unique number to identify the slot where
       the ML card is inserted in."
      ::= { prtMlIsdnEntry 3}

prtMlIsdnMode OBJECT-TYPE
      SYNTAX  INTEGER  { 
                 leased  (2), 
                 switched(3)
                       }
      MAX-ACCESS  read-write
      STATUS  current
      DESCRIPTION
   "ISDN Mode.
    switched - when ML Mode is Switched Backup.
    leased   - in all other cases."
      ::= { prtMlIsdnEntry 4}

prtMlIsdnStandard OBJECT-TYPE
      SYNTAX  INTEGER  { european      (2),
                         israeli       (3),
                         ess5Multipoint(4),
                         ess5Ptp       (5),
                         dms100        (6),
                         ntt           (7),
                         nationalIsdn1 (8)
                       }
      MAX-ACCESS  read-write
      STATUS  current
      DESCRIPTION
   "The ISDN standard."
      ::= { prtMlIsdnEntry 5}

prtMlIsdnLocSubNum OBJECT-TYPE
      SYNTAX  DisplayString (SIZE(0..25))
      MAX-ACCESS  read-write
      STATUS  current
      DESCRIPTION
   "Local sub-number. 4 chars (digits 0..9)."
      ::= { prtMlIsdnEntry 6}

prtMlIsdnLocNum OBJECT-TYPE
      SYNTAX  DisplayString (SIZE(0..25))
      MAX-ACCESS  read-write
      STATUS  current
      DESCRIPTION
   "Local number. 20 chars (digits: 0..9)."
      ::= { prtMlIsdnEntry 7}

prtMlIsdnOutSubNum OBJECT-TYPE
      SYNTAX  DisplayString (SIZE(0..25))
      MAX-ACCESS  read-write
      STATUS  current
      DESCRIPTION
   "Out sub-number. 4 chars (digits 0..9)."
      ::= { prtMlIsdnEntry 8}

prtMlIsdnBackupCallNum OBJECT-TYPE
      SYNTAX  DisplayString (SIZE(0..25))
      MAX-ACCESS  read-write
      STATUS  current
      DESCRIPTION
   "Backup call number. 20 chars (digits: 0..9)."
      ::= { prtMlIsdnEntry 9}

prtMlIsdnInNumMode OBJECT-TYPE
      SYNTAX  INTEGER  { none (2), 
                         all  (3),
                         local(4)
                       }
      MAX-ACCESS  read-write
      STATUS  current
      DESCRIPTION
   "In number mode."
      ::= { prtMlIsdnEntry 10}



prtHsLs  OBJECT IDENTIFIER  ::=  {prtKmux 2}

prtHsLsTable  OBJECT-TYPE
      SYNTAX SEQUENCE OF PrtHsLsEntry
      MAX-ACCESS not-accessible
      STATUS  current
      DESCRIPTION
      "Parameters for the High and Low speed channels. 
       Cards: KLS.1,KLS.2, KHS.1, KHS.2, KDI/CH, KHSU.1, KHSU.2, KHS.703."
      ::= { prtHsLs 1 }

prtHsLsEntry OBJECT-TYPE
      SYNTAX PrtHsLsEntry
      MAX-ACCESS not-accessible
      STATUS current
	DESCRIPTION  "An entry in table."
	INDEX { prtHsLsCnfgIdx, prtHsLsIdx }
      ::= { prtHsLsTable 1}

PrtHsLsEntry ::=
     SEQUENCE {
  prtHsLsCnfgIdx       Integer32,
  prtHsLsIdx           Integer32,
  prtHsLsSlt           INTEGER,
  prtHsLsCommProtocol  INTEGER,
  prtHsLsAsyncDataLen  INTEGER,
  prtHsLsTiming        INTEGER,
  prtHsLsCtrlSignal    INTEGER,
  prtHsLsCts           INTEGER,
  prtHsLsRtsCtsDelay   INTEGER,
  prtHsLsDsrMode       INTEGER,
  prtHsLsSpeed         INTEGER,
  prtHsLsUType         INTEGER 
  }

prtHsLsCnfgIdx OBJECT-TYPE
      SYNTAX  Integer32 (1..255)
      MAX-ACCESS  read-only
      STATUS  current
      DESCRIPTION
      "This attribute indicates the Idx of the Config being accessed.
       Idx of 255 relates to the Temporary (Scratch) Config.
       Write operation for the table entries is allowed only to 
       Config=255. "
      ::= { prtHsLsEntry 1}

prtHsLsIdx OBJECT-TYPE
      SYNTAX  Integer32
      MAX-ACCESS  read-only
      STATUS  current
      DESCRIPTION
   "The prtGenPrtIdx index of this channel.
    In KHSU.1 and KHSU.2 there are three ISDN sub-channels on 
    each port (2B+D).The sub-channels are numbered:  
    Slot*100+11 ; Slot*100+12 ; Slot*100+13 (First Port), 
    Slot*100+14 ; Slot*100+15 ; Slot*100+16 (Second Port)."
      ::= { prtHsLsEntry 2}

prtHsLsSlt     OBJECT-TYPE
      SYNTAX  INTEGER
       {
	kmxOpt (106),	-- For KDI/CH card type
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118)
       }
      MAX-ACCESS  read-only
      STATUS  current
      DESCRIPTION
      "This attribute indicates a unique number to identify the slot where
       the card is inserted in.
       In the 2104 Unit the entries kmxIO5(111)..kmxIO12(118) are not valid.
       The entry kmxOpt(106) is valid only for KDI/CH card."
      ::= { prtHsLsEntry 3}

prtHsLsCommProtocol OBJECT-TYPE
      SYNTAX  INTEGER  { notApplicable(1),
                         async        (2),
                      sync         (3)
        }
      MAX-ACCESS  read-write
      STATUS  current
      DESCRIPTION
   "The communication protocol."
      ::= { prtHsLsEntry 4}

prtHsLsAsyncDataLen OBJECT-TYPE
      SYNTAX  INTEGER   
        { notApplicable(1),
          bit6         (2),
          bit7         (3),
          bit8         (4),
          bit9         (5)
        } 
      MAX-ACCESS  read-write
      STATUS  current
      DESCRIPTION
   "Async Data Length in Bits.
    notApplicable - when prtHsLsCommProtocol=sync or 
                    notApplicable."
      ::= { prtHsLsEntry 5}

prtHsLsTiming OBJECT-TYPE
      SYNTAX  INTEGER  {
      notApplicable(1),
      dce   (2),
      dte1  (3),
      dte2  (4)
              }
      MAX-ACCESS  read-write
      STATUS  current
      DESCRIPTION
   "The variable is RW only if the communications protocol is 
    sync. 
    When the comm protocol is async, the variable is RO and its 
    value is DCE."
      ::= { prtHsLsEntry 6}

prtHsLsCtrlSignal OBJECT-TYPE
      SYNTAX  INTEGER  { notApplicable(1),
                         local        (2),
                         dtrAndRts    (3),
                         rts          (4)
        }
      MAX-ACCESS  read-write
      STATUS  current
      DESCRIPTION
   "Control signals."
      ::= { prtHsLsEntry 7}

prtHsLsCts OBJECT-TYPE
      SYNTAX  INTEGER { notApplicable(1),
                        equalRts     (2),
                        on           (3)
       }
      MAX-ACCESS  read-write
      STATUS  current
      DESCRIPTION
   "CTS Signal."
      ::= { prtHsLsEntry 8}

prtHsLsRtsCtsDelay OBJECT-TYPE
      SYNTAX  INTEGER  {
       notApplicable(1),
       min  (2),
       ms10 (3),
       ms50 (4),
       ms100(5),
       ms200(6)
        }
      MAX-ACCESS  read-write
      STATUS  current
      DESCRIPTION
   "RTS-CTS delay in ms.
    notApplicable - when prtHsLsCts=on."
      ::= { prtHsLsEntry 9}

prtHsLsDsrMode OBJECT-TYPE
      SYNTAX  INTEGER { notApplicable(1),
                        permanentOn  (2),
                        sync         (3)
       }
      MAX-ACCESS  read-write
      STATUS  current
      DESCRIPTION
   "DSR Mode."
      ::= { prtHsLsEntry 10}

prtHsLsSpeed OBJECT-TYPE
      SYNTAX  INTEGER {
      notConnected(1),
      bps300   (2),
      bps600   (3),
      bps1200  (4),
      bps2400  (5),
      bps4800  (6),
      bps7200  (7),
      bps8000  (8),
      bps9600  (9),
      bps12000(10),
      bps14400(11),
      bps16000(12),
      bps16800(13),
      bps19200(14),
      bps21600(15),
      bps24000(16),
      bps26400(17),
      bps28800(18),
      bps31200(19),
      bps32000(20),
      bps33600(21),
      bps36000(22),
      bps38400(23),
      bps40800(24),
      bps43200(25),
      bps45600(26),
      bps48000(27),
      bps50400(28),
      bps52800(29),
      bps55200(30),
      bps56000(31),
      bps57600(32),
      bps60000(33),
      bps62400(34),
      bps64000(35),
      bps64800(36),
      bps67200(37),
      bps69600(38),
      bps72000(39),
      bps74400(40),
      bps76800(41),
      bps79200(42),
      bps81600(43),
      bps84000(44),
      bps86400(45),
      bps88800(46),
      bps91200(47),
      bps93600(48),
      bps96000(49),
      bps98400(50),
      bps100800(51),
      bps103200(52),
      bps105600(53),
      bps108000(54),
      bps110400(55),
      bps112800(56),
      bps115200(57),
      bps117600(58),
      bps120000(59),
      bps122400(60),
      bps124800(61),
      bps127200(62),
      bps128000(63),
      bps129600(64),
      bps134400(65),
      bps139200(66),
      bps144000(67),
      bps148800(68),
      bps153600(69),
      bps158400(70),
      bps163200(71),
      bps168000(72),
      bps172800(73),
      bps177600(74),
      bps182400(75),
      bps187200(76),
      bps192000(77),
      bps196800(78),
      bps201600(79),
      bps206400(80),
      bps211200(81),
      bps216000(82),
      bps220800(83),
      bps225600(84),
      bps230400(85),
      bps235200(86),
      bps240000(87),
      bps244800(88),
      bps249600(89),
      bps254400(90),
      bps256000(91),
      bps259200(92),
      bps264000(93),
      bps268800(94),
      bps273600(95),
      bps278400(96),
      bps283200(97),
      bps288000(98),
      bps292800(99),
      bps297600(100),
      bps302400(101),
      bps307200(102),
      bps316800(103),
      bps326400(104),
      bps336000(105),
      bps345600(106),
      bps355200(107),
      bps364800(108),
      bps374400(109),
      bps384000(110),
      bps393600(111),
      bps403200(112),
      bps412800(113),
      bps422400(114),
      bps432000(115),
      bps441600(116),
      bps451200(117),
      bps460800(118),
      bps470400(119),
      bps480000(120),
      bps489600(121),
      bps499200(122),
      bps508800(123),
      bps518400(124),
      bps528000(125),
      bps537600(126),
      bps547200(127),
      bps556800(128),
      bps566400(129),
      bps576000(130),
      bps585600(131),
      bps595200(132),
      bps604800(133),
      bps614400(134)
       }
      MAX-ACCESS  read-write
      STATUS  current
      DESCRIPTION
   "KLS.1 supports (Kbps): 0.3, 0.6, 1.2, 2.4, 4.8, 9.6, 19.2, 38.4.
    KLS.1/New, KDI/CH support (Kbps): 
                               Group 1: 0.3, 0.6, 1.2, 2.4, 4.8, 9.6, 
                                       19.2, 38.4
                               Group 2: 7.2, 14.4, 28.8, 57.6
                               Group 3: 8, 16, 24, 32, 48, 56, 64 
    KLS.2 supports (Kbps): 2.4, 4.8, 9.6, 19.2.
    KHS.1 supports (Kbps): 32, 48, 56, 64, 128, 192, 256, 384
    KHS.2 supports (Kbps): ...
    KHSU.1/2 support (Kbps): 16, 32, 64.
    KHS.703 support (Kbps): 64."
      ::= { prtHsLsEntry 11}

prtHsLsUType OBJECT-TYPE
      SYNTAX  INTEGER {
      notApplicable(1), 
      regular(2),
      type1  (3)
       }
      MAX-ACCESS  read-write
      STATUS  current
      DESCRIPTION
      "U Interface Type. Applicable for KHSU.1/2 cards.
       The value will be the same for B1 and B2 pair; B3 and B4."
      ::= { prtHsLsEntry 12}



prtTreMbe  OBJECT IDENTIFIER  ::=  {prtKmux 3}

prtTreMbeTable OBJECT-TYPE
      SYNTAX SEQUENCE OF PrtTreMbeEntry
      MAX-ACCESS not-accessible
      STATUS  current
      DESCRIPTION
       "The write operation into the Table Objects is valid only
        to the TmpCnfg entry. Parameters for the channels of the
        TRE and MBE cards: KTRE, KMBE, KMBE/NEW."
      ::= {prtTreMbe 2}

prtTreMbeEntry OBJECT-TYPE
      SYNTAX PrtTreMbeEntry
      MAX-ACCESS not-accessible
      STATUS current
	DESCRIPTION  "An entry in table."
	INDEX {prtTreMbeCnfgIdx, prtTreMbeIdx }
      ::= { prtTreMbeTable 1}

PrtTreMbeEntry ::=
      SEQUENCE {
        prtTreMbeCnfgIdx     Integer32,
        prtTreMbeIdx         Integer32,
        prtTreMbeSlt         INTEGER,
        prtTreMbeLan         INTEGER,
        prtTreMbeLanRate     INTEGER,
        prtTreMbeLinkSpeed   INTEGER
      }

prtTreMbeCnfgIdx OBJECT-TYPE
      SYNTAX  Integer32  (1..255)
      MAX-ACCESS  read-only
      STATUS  current
      DESCRIPTION
      "This attribute indicates the Idx of the Cnfg (1..100) being
       accessed.
       Idx 255 relates to the TmpCnfg."
      ::= {prtTreMbeEntry 1}

prtTreMbeIdx OBJECT-TYPE
      SYNTAX  Integer32
      MAX-ACCESS  read-only
      STATUS  current
      DESCRIPTION
      "A unique port identifier within the card.
       Slot*100+11 ."
      ::= {prtTreMbeEntry 2}

prtTreMbeSlt OBJECT-TYPE
      SYNTAX  INTEGER
     {
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118)
       }
      MAX-ACCESS  read-only
      STATUS  current
      DESCRIPTION
      "This attribute indicates a unique number to identify the slot where
       the card is inserted in.
       In the 2104 Unit the entries kmxIO5(111)..kmxIO12(118) are not valid."
      ::= {prtTreMbeEntry 3}

prtTreMbeLan OBJECT-TYPE
      SYNTAX  INTEGER
       {
        notApplicable(1),
        main         (2),
        remote       (3)
		
       }
      MAX-ACCESS  read-write
      STATUS  current
      DESCRIPTION
      "This attribute indicates whether the TRE/MBE port is operated 
       as main or remote bridge.
       Default=remote."
      ::= {prtTreMbeEntry 4}

prtTreMbeLanRate OBJECT-TYPE
      SYNTAX  INTEGER
       {
        notApplicable(1),
        r4M  (2),
        r16M (3)
       }
      MAX-ACCESS  read-write
      STATUS  current
      DESCRIPTION
      "This attribute indicates the Rate of the TRE port 
       in Mbit/sec. Default-r4M."
      ::= {prtTreMbeEntry 5}

prtTreMbeLinkSpeed OBJECT-TYPE
      SYNTAX  INTEGER
       {
  notConnected(1),
  bps9600   (2),
  bps19200  (3),
  bps28800  (4),
  bps38400  (5),
  bps48000  (6),
  bps57600  (7),
  bps67200  (8),
  bps76800  (9),
  bps86400 (10),
  bps96000 (11),
  bps105600(12),
  bps115200(13),
  bps124800(14),
  bps128000(15),
  bps160000(16),
  bps192000(17),
  bps224000(18),
  bps240000(19),
  bps272000(20),
  bps304000(21),
  bps336000(22),
  bps368000(23)
       }
      MAX-ACCESS  read-write
      STATUS  current
      DESCRIPTION
      "The Link Speed."
      ::= {prtTreMbeEntry 6}


prtVoiceFax  OBJECT IDENTIFIER  ::=  {prtKmux 4}

prtVoiceFaxTable OBJECT-TYPE
      SYNTAX SEQUENCE OF PrtVoiceFaxEntry
      MAX-ACCESS not-accessible
      STATUS  current
      DESCRIPTION
       "The write operation into the Table Objects is valid only
        to the TmpCnfg entry. Parameters for the channels of the
        Voice and Fax channels. 
        Cards: KVC.1/E&M,  KVC.1/FXO,  KVC.1/FXS,
               KVC.1M/E&M, KVC.1M/FXO, KVC.1M/FXS, KVC.1M/FXSW, 
               KVC.2/E&M,  KVC.2/FXO,  KVC.2/FXS, 
               KVC.2/1/E&M,KVC.2/1/FXO,KVC.2/1/FXS, 
               KVC.3/E&M,  KVC.3/FXO,  KVC.3/FXS, KVC.3/S0
               KVF.1/E&M,  KVF.1/FXO,  KVF.1/FXS, 
               KVF.3/E&M,  KVF.3/FXO,  KVF.3/FXS, 
               KVF.4/E&M,  KVF.4/FXO,  KVF.4/FXS, KVF.4/FXSW, KVF.4/S0,
               KVF.4/FXO3, KVF.4/FXS3, KVF.4/NS0     
               KVF.5 family, KVF.6 family, KVF.8 family."
      ::= { prtVoiceFax 1}

prtVoiceFaxEntry OBJECT-TYPE
      SYNTAX PrtVoiceFaxEntry
      MAX-ACCESS not-accessible
      STATUS current
	DESCRIPTION  "An entry in table."
	INDEX {prtVoiceFaxCnfgIdx, prtVoiceFaxIdx }
      ::= { prtVoiceFaxTable 1}

PrtVoiceFaxEntry ::=
      SEQUENCE {
        prtVoiceFaxCnfgIdx         Integer32,
        prtVoiceFaxIdx             Integer32,
        prtVoiceFaxSlt             INTEGER,
        prtVoiceFaxTransGain       Integer32,
        prtVoiceFaxReceiveGain     Integer32,
        prtVoiceFaxWire            INTEGER,
        prtVoiceFaxTimeOut         INTEGER,
        prtVoiceFaxEchoCanceler    INTEGER,
        prtVoiceFaxSpeed           INTEGER,
        prtVoiceFaxMeterRate       INTEGER,
        prtVoiceFaxCodingLaw       INTEGER,
		prtVoiceFaxOperMode	       INTEGER,
		prtVoiceFaxSigInOutband    OCTET STRING,
		prtVoiceFaxTsGroup         INTEGER,
		prtVoiceFaxRxFaxGain       Integer32,
		prtVoiceFaxSigHold         INTEGER,
		prtVoiceFaxIfSignaling     INTEGER,
		prtVoiceFaxEMTypes         INTEGER,
		prtVoiceFaxRingFrequency   INTEGER,
		prtVoiceFaxSignalingStatus OCTET STRING

      }

prtVoiceFaxCnfgIdx OBJECT-TYPE
      SYNTAX  Integer32  (1..255)
      MAX-ACCESS  read-only
      STATUS  current
      DESCRIPTION
      "This attribute indicates the Idx of the Cnfg (1..100) being 
       accessed.
       Idx  255 relates to the TmpCnfg."
      ::= {prtVoiceFaxEntry 1}

prtVoiceFaxIdx OBJECT-TYPE
      SYNTAX  Integer32
      MAX-ACCESS  read-only
      STATUS  current
      DESCRIPTION
      "A unique identifier of the port, within the card.
       Slot*100+Ch
       external ports:  Ch=1..10
       internal ports (sub-channels): Ch=11..20."
      ::= {prtVoiceFaxEntry 2}

prtVoiceFaxSlt OBJECT-TYPE
      SYNTAX  INTEGER
 {
    kmxIO1 (107),
    kmxIO2 (108),
    kmxIO3 (109),
    kmxIO4 (110),
    kmxIO5 (111),
    kmxIO6 (112),
    kmxIO7 (113),
    kmxIO8 (114),
    kmxIO9 (115),
    kmxIO10(116),
    kmxIO11(117),
    kmxIO12(118)
       }
      MAX-ACCESS  read-only
      STATUS  current
      DESCRIPTION
      "This attribute indicates a unique number to identify the slot where
       the card is inserted in.
       In the 2104 Unit the entries kmxIO5(111)..kmxIO12(118) are not valid."
      ::= {prtVoiceFaxEntry 3}

prtVoiceFaxTransGain OBJECT-TYPE
      SYNTAX  Integer32          
      MAX-ACCESS  read-write
      STATUS  current
      DESCRIPTION
      "Transmit gain in dBm. A value of 255 is for notApplicable.
       The value will be:  real value+50dBm (in order to avoid
       negative values)."
      ::= {prtVoiceFaxEntry 4}

prtVoiceFaxReceiveGain OBJECT-TYPE
      SYNTAX  Integer32       
      MAX-ACCESS  read-write
      STATUS  current
      DESCRIPTION
      "Receive gain in dBm. A value of 255 is for notApplicable.
       The value will be:  real value+50dBm (in order to avoid
       negative values)."
      ::= {prtVoiceFaxEntry 5}

prtVoiceFaxWire OBJECT-TYPE
      SYNTAX  INTEGER
       {notApplicable(1),
           w2wire   (2),
           w4wire   (3)
       }
      MAX-ACCESS  read-write
      STATUS  current
      DESCRIPTION
      "Applicable only for E&M cards."
      ::= {prtVoiceFaxEntry 6}

prtVoiceFaxTimeOut OBJECT-TYPE
      SYNTAX  INTEGER
       {notApplicable(1),
     manual(2),
     sec30 (3),
     sec60 (4),
     sec90 (5)
       }
      MAX-ACCESS  read-write
      STATUS  current
      DESCRIPTION
      "Fax timeout in seconds."
      ::= {prtVoiceFaxEntry 7}

prtVoiceFaxEchoCanceler OBJECT-TYPE
      SYNTAX  INTEGER
       {notApplicable(1),
           off    (2),
           on     (3)
       }
      MAX-ACCESS  read-write
      STATUS  current
      DESCRIPTION
      "Echo canceler activation."
      ::= {prtVoiceFaxEntry 8}

prtVoiceFaxSpeed OBJECT-TYPE
      SYNTAX  INTEGER
      {notConnected(1),
    bps4800(2),
    bps6400(3),
    bps7200(4),
    bps8000(5),
    bps9600(6),
    bps12800(7),
    bps16000(8),
    bps24000(9),
    bps32000(10),
    bps64000(11),
	bps11200(12)
      }
      MAX-ACCESS  read-write
      STATUS  current
      DESCRIPTION
      "The channel speed.
       For KVF.6 and KVF.8 cards, each value will represent [4 x value], since each
       channel (Internal or External) is comprised of 4 sub-channels having the selected value."
      ::= {prtVoiceFaxEntry 9}

prtVoiceFaxMeterRate OBJECT-TYPE
      SYNTAX  INTEGER
      {
        notApplicable(1),
        r16Khz (2),
        r12Khz (3)
      }
      MAX-ACCESS  read-write
      STATUS  current
      DESCRIPTION
      "This entry is valid to KVF.4/FXO3 and KVF.4/FXS3.
       Meter Rate means rate of Call Meter in Public Phones, in KHz units.
       Must be equal for both channels."
      ::= {prtVoiceFaxEntry 10}

prtVoiceFaxCodingLaw OBJECT-TYPE
      SYNTAX  INTEGER
      {
        notApplicable(1),
        aLaw         (2),
        uLaw         (3)
      }
      MAX-ACCESS  read-write
      STATUS  current
      DESCRIPTION
      "Coding Law. This entry is valid for KVF.4/NS0 external channel and 
       KVF.6 internal channels."
      ::= {prtVoiceFaxEntry 11}

prtVoiceFaxOperMode OBJECT-TYPE
      SYNTAX  INTEGER
      {
        notApplicable      (1),
        voiceANDfax        (2),
        voice              (3),
		voiceAndFaxAndData (4)
      }
      MAX-ACCESS  read-write
      STATUS  current
      DESCRIPTION
      "Operation Mode. This parameter is valid for KVF.6 and KVF.8 family."
      ::= {prtVoiceFaxEntry 12}

prtVoiceFaxSigInOutband OBJECT-TYPE
      SYNTAX  OCTET STRING	 (SIZE(2))
      MAX-ACCESS  read-write
      STATUS  current
      DESCRIPTION
      "This object is applicable for KVF.4/FXO3, KVF.4/FXS3, KVF.8 family cards.

	   For KVF.4/FXO3, KVF.4/FXS3:
	   Octet 1 for Receive parameters.
	   Octet 2 for Transmit parameters. 
       It represents 4 parameters, in each Octet :
	   Bit 7     6     5     4     3     2     1     0
	       |_____|     |_____|     |_____|     |_____|
	   MSB  Spare    On/Off Hook   Metering    Polarity LSB   

       Each parameter's bits represent:
       00 = NC
       01 = Inband(A/B)
       10 = Outband(A)	
       11 = Outband(B)
    

	  For KVF.8 family:
	   It represents 4 parameters, by 2 Octets :
       General Bit Code-    MSB nibble,
       On/Off Hook Bit Code-    nibble,
       Metering Bit Code-       nibble,
       Polarity Bit Code-   LSB nibble.

       Each of General, On/Off Hook, Metering, Polarity Bit Code nibble represents:
       0 hex = 0000 = 0
       1 hex = 0001 = 1
       2 hex = 0010 = A bit
       3 hex = 0011 = B bit
       4 hex = 0100 = C bit
       5 hex = 0101 = D bit
       6 hex = 0110 = A bit inverse
       7 hex = 0111 = B bit inverse
       8 hex = 1000 = C bit inverse
       9 hex = 1001 = D bit inverse
       A-E hex - not used (invalid values)


       When the object is not applicable, 0 Octets will be sent."
      ::= {prtVoiceFaxEntry 13}

prtVoiceFaxTsGroup OBJECT-TYPE
      SYNTAX  INTEGER
      {
		notApplicable(1),
        s1s2s3s4     (2),
        s5s6s7s8     (3),
        s9s10s11s12  (4),
        s13s14s15s16 (5),
        s17s18s19s20 (6),
        s21s22s23s24 (7),
        s25s26s27s28 (8),
        s29s30s31    (9)
        }
      MAX-ACCESS  read-write
      STATUS  current
      DESCRIPTION
      "Ts Assignment group. Each KVF.6 internal channel should have 
       a different value.
	   's21s22s23s24' = TSs: 21, 22, 23, 24
   	   For KVF.6/E1/16, KVF.6/E1/31 values: 2..9 are applicable.
       For KVF.6/T1/12, KVF.6/T1/24 values: 2..7 are applicable."
      ::= {prtVoiceFaxEntry 14}

prtVoiceFaxRxFaxGain OBJECT-TYPE
      SYNTAX  Integer32       
      MAX-ACCESS  read-write
      STATUS  current
      DESCRIPTION
      "FAX Receive gain in dBm. 
       The value will be:  (real value*10)+500dBm (in order to avoid
       negative and fractional values)."
      ::= {prtVoiceFaxEntry 15}
    
prtVoiceFaxSigHold  OBJECT-TYPE
      SYNTAX  INTEGER
       {
	   notApplicable(1),
       sec0(2),
       sec10(3)
       }
      MAX-ACCESS  read-write
      STATUS  current
      DESCRIPTION
      "Signal Hold in [sec]. Applicable for all KVF.4 cards except S0/NS0.
       When a ML fails, instead of interrupting immediately a 
       conversation and connecting it again when ML operation is resumed, 
       user can select to Hold the signal a few seconds before interruption (ML 
       operation may return during this time).
       sec0 = No Hold = 0 sec
       sec10= 10 sec hold."
   ::= {prtVoiceFaxEntry 16}

															 
prtVoiceFaxIfSignaling OBJECT-TYPE
      SYNTAX  INTEGER
       {notApplicable   (1),
           loopStart    (2),
           groundStart  (3),
		   winkStart    (4)
       }
      MAX-ACCESS  read-write
      STATUS  current
      DESCRIPTION
      "Applicable only for KVF.8/FXO, KVF.8/FXS cards.
       Interface Analog Signaling."
      ::= {prtVoiceFaxEntry 17}


prtVoiceFaxEMTypes OBJECT-TYPE
      SYNTAX  INTEGER
       {notApplicable   (1),
           em1          (2),
           em2          (3),
		   em3          (4),
		   ssdc5   	    (5)
       }
      MAX-ACCESS  read-write
      STATUS  current
      DESCRIPTION
      "Applicable only for KVF.8/E&M card."
      ::= {prtVoiceFaxEntry 18}
      


prtVoiceFaxRingFrequency OBJECT-TYPE
      SYNTAX  INTEGER
	  {
        notApplicable (1),
        f16dot7Hz     (2),
        f20Hz         (3),
		f25Hz         (4),
		f50Hz         (5)
      }
      MAX-ACCESS  read-write
      STATUS  current
      DESCRIPTION
      "Applicable only for KVF.8/E&M card.
       The Ringing Frequency units will be in Hz."
      ::= {prtVoiceFaxEntry 19}

prtVoiceFaxSignalingStatus OBJECT-TYPE	      
      SYNTAX  OCTET STRING	 (SIZE(0..2))
      MAX-ACCESS  read-write
      STATUS  current
      DESCRIPTION
      "For KM-2100 this parameter should be Read Only.
       This object is applicable for KVF.6 and KVF.5 family cards.
	   It shows the status (0 or 1) of each Signaling Bit (A, B, C, D), 
	   for each TS of a TS Group (according to it's position in the group).
       Each nibble represent a TS from the 'TS Group' selected 
       for the channel (two Octets represents 4 TSs of each group):
      
       Bit 7  6  5  4  3  2  1  0  7  6  5  4  3  2  1  0
	       |________|  |________|  |________|  |________|
	   MSB   TS i+3      TS i+2      TS i+1      TS i    LSB   

       It represents 4 parameters for each TS:
		 TS-i          TS-i+1     ..
       0 - A bit       4 - A bit
	   1 - B bit	   5 - B bit
	   2 - C bit	   6 - C bit
	   3 - D bit	   7 - D bit

  	   When the object is not applicable, 0 Octets will be sent."
      ::= {prtVoiceFaxEntry 20}
-- 
-- file :v:\doc\rdv\mib\Before~1\imx.txt
-- 
--RAD-IMX-MIB

--                RAD-IMX MIB    (Inverse Multiplexer)

--Title:     RAD's IMX-64 PRODUCT MIB
--Version:   1.0
--Date:      1.8.96
--By:        Yair Arian
--File:      imx.mib
--
--Update: 16.09.99 by Smadar (corrected conflicts with existing RAD MIB).
--Last Update : 06.01.00 by Smadar (added comments for Traps)


imx  OBJECT IDENTIFIER  ::=  {radWan 7}


systemImx  OBJECT IDENTIFIER  ::=  {imx 1}

generalImx  OBJECT IDENTIFIER  ::=  {systemImx 1}

sysGenClearAlarm OBJECT-TYPE
      SYNTAX INTEGER { on(1),
	                   off(2)
					 }
      MAX-ACCESS read-write
      STATUS current
      DESCRIPTION
      "Clear the alarm buffer. The agent resets the variable automatically
       to off."
      ::= { generalImx 1}

sysGenAlarmBuffTable  OBJECT-TYPE
      SYNTAX SEQUENCE OF SysGenAlarmBuffEntry
      MAX-ACCESS not-accessible
      STATUS  current
      DESCRIPTION
      "The alarm buffer of the imx."
       ::= { generalImx 2 }

sysGenAlarmBuffEntry OBJECT-TYPE
      SYNTAX SysGenAlarmBuffEntry
      MAX-ACCESS not-accessible
      STATUS current
      DESCRIPTION
	  "An entry in table sysGenAlarmBuffTable."
      INDEX {sysGenAlarmBuffIndex}
      ::= { sysGenAlarmBuffTable 1}

SysGenAlarmBuffEntry ::=
      SEQUENCE {
	  sysGenAlarmBuffIndex Integer32,
	  sysGenAlarmDescr     DisplayString
      }

sysGenAlarmBuffIndex OBJECT-TYPE
      SYNTAX Integer32 (1..100)
      MAX-ACCESS read-only
      STATUS current
      DESCRIPTION
      "The index of the alarm buffer Table."
      ::= { sysGenAlarmBuffEntry 1}

sysGenAlarmDescr OBJECT-TYPE
      SYNTAX DisplayString
      MAX-ACCESS read-only
      STATUS current
      DESCRIPTION
      "The description of the alarm. Up to 80 chars."
      ::= { sysGenAlarmBuffEntry 2}

sysGenClearLog OBJECT-TYPE
      SYNTAX INTEGER { on(1),
	                   off(2)
					 }
      MAX-ACCESS read-write
      STATUS current
      DESCRIPTION
      "Clear the log buffer. The agent resets the variable automatically
       to off."
      ::= { generalImx 3}

sysGenLogTable  OBJECT-TYPE
      SYNTAX SEQUENCE OF SysGenLogEntry
      MAX-ACCESS not-accessible
      STATUS  current
      DESCRIPTION
      "The call log buffer of the imx."
       ::= { generalImx 4 }

sysGenLogEntry OBJECT-TYPE
      SYNTAX SysGenLogEntry
      MAX-ACCESS not-accessible
      STATUS current
      DESCRIPTION
	  "An entry in table sysGenLogTable."
      INDEX {sysGenLogIndex}
      ::= { sysGenLogTable 1}

SysGenLogEntry ::=
      SEQUENCE {
	  sysGenLogIndex     Integer32,
	  sysGenLogDescr     DisplayString
      }

sysGenLogIndex OBJECT-TYPE
      SYNTAX Integer32 (1..100)
      MAX-ACCESS read-only
      STATUS current
      DESCRIPTION
      "The index of the log Table."
      ::= { sysGenLogEntry 1}

sysGenLogDescr OBJECT-TYPE
      SYNTAX DisplayString
      MAX-ACCESS read-only
      STATUS current
      DESCRIPTION
      "The description of the entry in the log buffer. Up to 80 chars."
      ::= { sysGenLogEntry 2}


profilesImx  OBJECT IDENTIFIER  ::=  {systemImx 2}

callProfileImx  OBJECT IDENTIFIER  ::=  {profilesImx 1}

sysCallProfileTable  OBJECT-TYPE
      SYNTAX SEQUENCE OF SysCallProfileEntry
      MAX-ACCESS not-accessible
      STATUS  current
      DESCRIPTION
      "A table containing call profile parameters. There are 40 call
       profiles."
       ::= { callProfileImx 1 }

sysCallProfileEntry OBJECT-TYPE
      SYNTAX SysCallProfileEntry
      MAX-ACCESS not-accessible
      STATUS current
      DESCRIPTION
	  "An entry in table sysCallProfileTable."
      INDEX {sysCallProfileIndex}
      ::= {sysCallProfileTable 1}

SysCallProfileEntry ::=
      SEQUENCE {
	  sysCallProfileIndex                  Integer32,
	  sysCallProfileConnectCmd             INTEGER,
	  sysCallProfileDisconnectCmd          INTEGER,
	  sysCallProfileIncrBwCmd              Integer32,
	  sysCallProfileDecrBwCmd              Integer32
      }

sysCallProfileIndex OBJECT-TYPE
      SYNTAX Integer32 (1..40)
      MAX-ACCESS read-only
      STATUS current
      DESCRIPTION
      "A running index for the table."
      ::= { sysCallProfileEntry 1}

sysCallProfileConnectCmd OBJECT-TYPE
      SYNTAX INTEGER { off(1),
	                   on(2)
					}
      MAX-ACCESS read-write
      STATUS current
      DESCRIPTION
      "On(2) - Connect the call profile. The agent will automatically
       reset the variable to off(1) ."
      ::= { sysCallProfileEntry 2}

sysCallProfileDisconnectCmd OBJECT-TYPE
      SYNTAX INTEGER { off(1),
	                   on(2)
					}
      MAX-ACCESS read-write
      STATUS current
      DESCRIPTION
      "On(2) - Disconnect the call profile. The agent will automatically
       reset the variable to off(1)."
      ::= { sysCallProfileEntry 3}

sysCallProfileIncrBwCmd OBJECT-TYPE
      SYNTAX Integer32 (0..6)
      MAX-ACCESS read-write
      STATUS current
      DESCRIPTION
      "Increment bandwidth of a call.
       The number of channels to increment 1..6. The agent will automatically
       reset the variable to 0."
      ::= { sysCallProfileEntry 4}

sysCallProfileDecrBwCmd OBJECT-TYPE
      SYNTAX Integer32 (0..6)
      MAX-ACCESS read-write
      STATUS current
      DESCRIPTION
      "Decrement bandwidth of a call.
       The number of channels to decrement 1..6. The agent will automatically
       reset the variable to 0."
      ::= { sysCallProfileEntry 5}


portImx  OBJECT IDENTIFIER  ::=  {imx 2}

userPortImx  OBJECT IDENTIFIER  ::=  {portImx 1}

prtCnfgTable  OBJECT-TYPE
      SYNTAX SEQUENCE OF PrtCnfgEntry
      MAX-ACCESS not-accessible
      STATUS  current
      DESCRIPTION
      "A table containing configuration parameters for the user ports."
       ::= { userPortImx 1 }

prtCnfgEntry OBJECT-TYPE
      SYNTAX PrtCnfgEntry
      MAX-ACCESS not-accessible
      STATUS current
      DESCRIPTION
	  "An entry in table prtCnfgTable."
      INDEX {prtIndex}
      ::= {prtCnfgTable 1}

PrtCnfgEntry ::=
      SEQUENCE {
	  prtIndex                Integer32,
	  prtCnfgDecrBwChNum      Integer32,	
	  prtCnfgIncrBwChNum      Integer32,	
	  prtCnfgDisconnect       INTEGER,
	  prtCnfgActivateLoop     INTEGER,
	  prtCnfgClearLoop        INTEGER,
	  prtCnfgLoopStatus       Integer32
	  }

prtIndex OBJECT-TYPE
      SYNTAX Integer32 (1..2)
      MAX-ACCESS read-only
      STATUS current
      DESCRIPTION
      "The user port index."
      ::= { prtCnfgEntry 1}

prtCnfgDecrBwChNum OBJECT-TYPE
      SYNTAX Integer32 (0..6)
      MAX-ACCESS read-write
      STATUS current
      DESCRIPTION
      "Decrement the port bandwidth by the specified number of channels.
       The agent resets the variable to 0."
      ::= { prtCnfgEntry 2}

prtCnfgIncrBwChNum OBJECT-TYPE
      SYNTAX Integer32 (0..6)
      MAX-ACCESS read-write
      STATUS current
      DESCRIPTION
      "Increment the port bandwidth by the specified number of channels.
       The agent resets the variable to 0."
      ::= { prtCnfgEntry 3}

prtCnfgDisconnect OBJECT-TYPE
      SYNTAX INTEGER { on(1),
	                   off(2)
					 }
      MAX-ACCESS read-write
      STATUS current
      DESCRIPTION
      "Disconnect the port (on(1)). The agent resets the variable to off(2)."
      ::= { prtCnfgEntry 4}

prtCnfgActivateLoop OBJECT-TYPE
      SYNTAX INTEGER { none(1),
                       local(2),
	                   remote(3),
					   bonding(4)
					 }
      MAX-ACCESS read-write
      STATUS current
      DESCRIPTION
      "Activate the desired loop on the port. 
       The agent will reset the variable to none(1)."
      ::= { prtCnfgEntry 5}

prtCnfgClearLoop OBJECT-TYPE
      SYNTAX INTEGER { none(1),
                       local(2),
	                   remote(3),
					   bonding(4),
					   all(5)
					 }
      MAX-ACCESS read-write
      STATUS current
      DESCRIPTION
      "Clear the desired loop from the port. The agent will
       reset the variable to none(1)"
      ::= { prtCnfgEntry 6}

prtCnfgLoopStatus OBJECT-TYPE
      SYNTAX Integer32 
      MAX-ACCESS read-only
      STATUS current
      DESCRIPTION
      "The loop status at this port. The variable is a sum of 2**n where
       n is as follows:
       0 - Local Loop is on.
       1 - Remote Loop is on.
       2 - BONDING Loop is on.
       If the variable is 0, there is no active loop."
      ::= { prtCnfgEntry 7}


supervisoryPortImx  OBJECT IDENTIFIER  ::=  {portImx 2}

prtSpUsageImx OBJECT-TYPE
      SYNTAX INTEGER { nmsSlip(2),
	                   terminal(3)
					 }
     MAX-ACCESS read-write
      STATUS current
      DESCRIPTION
      "The supervisory port terminal usage definition."
      ::= { supervisoryPortImx 1}


channelImx  OBJECT IDENTIFIER  ::=  {imx 4}

channelCnfgTable  OBJECT-TYPE
      SYNTAX SEQUENCE OF ChannelCnfgEntry
      MAX-ACCESS not-accessible
      STATUS  current
      DESCRIPTION
      "A table containing configuration parameters for the channels."
       ::= { channelImx 1 }

channelCnfgEntry OBJECT-TYPE
      SYNTAX ChannelCnfgEntry
      MAX-ACCESS not-accessible
      STATUS current
      DESCRIPTION
	  "An entry in table channelCnfgTable."
      INDEX {chIndex}
      ::= {channelCnfgTable 1}

ChannelCnfgEntry ::=
      SEQUENCE {
	  chIndex                 Integer32,
	  chCnfgUnlock           INTEGER,
	  chCnfgPing             INTEGER
	  }

chIndex OBJECT-TYPE
      SYNTAX Integer32 (1..6)
      MAX-ACCESS read-only
      STATUS current
      DESCRIPTION
      "The channel index."
      ::= { channelCnfgEntry 1}

chCnfgUnlock OBJECT-TYPE
      SYNTAX INTEGER { on(1),
	                   off(2)
					 }
      MAX-ACCESS read-write
      STATUS current
      DESCRIPTION
      "Unlock the channel (on). The agent resets the variable to off."
      ::= { channelCnfgEntry 2}

chCnfgPing OBJECT-TYPE
      SYNTAX INTEGER  { on(1),
	                   off(2)
					 }
      MAX-ACCESS read-write
      STATUS current
      DESCRIPTION
      "Ping the channel (on). The agent resets the variable to off."
      ::= { channelCnfgEntry 3}


channelStatTable  OBJECT-TYPE
      SYNTAX SEQUENCE OF ChannelStatEntry
      MAX-ACCESS not-accessible
      STATUS  current
      DESCRIPTION
      "A table containing status and statistics information for the channels."
       ::= { channelImx 2 }

channelStatEntry OBJECT-TYPE
      SYNTAX ChannelStatEntry
      MAX-ACCESS not-accessible
      STATUS current
      DESCRIPTION
	  "An entry in table channelStatTable."
      INDEX {chIndex}
      ::= {channelStatTable 1}

ChannelStatEntry ::=
      SEQUENCE {
	  chStatOperStatus		  INTEGER
	  }

chStatOperStatus OBJECT-TYPE
      SYNTAX INTEGER { up(1),
	                   down(2),
					   engaged(3),
					   notDedicated(4)
					 }
      MAX-ACCESS read-only
      STATUS current
      DESCRIPTION
      "The operational state of the channel based on a ping operation."
      ::= { channelStatEntry 1}

-- Traps

imxAlarmTrap NOTIFICATION-TYPE
      STATUS  current
      DESCRIPTION
	  "The trap is sent every time a new alarm is logged into the alarm
	   buffer. The trap may not be sent more than once in a five second
	   interval."
      ::= { radSysWanEvents 2 }

imxCallLogTrap NOTIFICATION-TYPE
      STATUS  current
      DESCRIPTION
	  "The trap is sent every time a new call log entry is logged into the
	   log buffer. The trap may not be sent more than once in a five second
	   interval."
      ::= { radSysWanEvents 3 }

imxPingTrap NOTIFICATION-TYPE
      OBJECTS  {chStatOperStatus}
      STATUS  current
      DESCRIPTION
	  "The trap is sent every time a ping operation is performed on a
	   channel."
      ::= { radSysWanEvents 4 }

-- Traps 5-7 having the same enterprise, are used by ipmux.txt.


-- 
-- file :v:\doc\rdv\mib\ver485\atm\nteprtconfg.txt
-- 
-- *************************
-- file  : NtePrtConfg.txt
--
--Version:   1.0
--Date:      12.11.97
--By:        Ilana Schvetz
--File:      v:\doc\rdv\mib\ver480\atm\NtePrtConfg.txt 

--Last Update: 30-Sep-01 by Ilana Schvetz
-- Copyright 1997 RAD Data Communications, Ltd.
-- All Rights Reserved.

atmNte              OBJECT IDENTIFIER ::= { radAtm 3 }
atmNtePrt		    OBJECT IDENTIFIER ::= { atmNte 2 }
atmNtePrtConfig		OBJECT IDENTIFIER ::= { atmNtePrt 1 }

atmNteEvents OBJECT-IDENTITY
     STATUS  current
     DESCRIPTION
     "The events for RAD ATM products."
     ::= { atmNte 0 }

atmNteConfIfTable OBJECT-TYPE
              SYNTAX  SEQUENCE OF AtmNteConfIfEntry
              MAX-ACCESS  not-accessible
              STATUS  current
              DESCRIPTION
              "The Physical interface configuration table."
              ::= { atmNtePrtConfig 1 }

          atmNteConfIfEntry OBJECT-TYPE
              SYNTAX  AtmNteConfIfEntry
              MAX-ACCESS  not-accessible
              STATUS  current
              DESCRIPTION
              "An entry in the Physical interface configuration table.
               The ifIndex is of the lowest physical layer."
              INDEX   { ifIndex}
              ::= { atmNteConfIfTable 1 }

          AtmNteConfIfEntry ::=
              SEQUENCE {
				atmConfIfTransmitClk
				      INTEGER,
				atmConfIfLoopback
				      INTEGER,
				atmConfIfFrameType
				      INTEGER,
				atmConfIfCardType
				      INTEGER,
				atmConfAtmIfVpiVciLimit
				      INTEGER,
				atmConfIfHwFeatures
				      INTEGER,
				atmConfIfOutputRate
				      Integer32,
				atmConfIfInputRate
				      Integer32,
				atmConfAlarmForwarding
				      INTEGER
                 }

          atmConfIfTransmitClk OBJECT-TYPE
              SYNTAX  INTEGER { internal(2), external(3), loopback(4), adaptive(5) }
              MAX-ACCESS  read-write
              STATUS  current
              DESCRIPTION
              "The transmit clock of the port."
              ::= { atmNteConfIfEntry 1 }

          atmConfIfLoopback OBJECT-TYPE
              SYNTAX  INTEGER { internal(2), external(3), disable(4) }
              MAX-ACCESS  read-write
              STATUS  current
              DESCRIPTION
              "Interface Loopback."
              ::= { atmNteConfIfEntry 2 }

          atmConfIfFrameType OBJECT-TYPE
              SYNTAX  INTEGER {  
              other        (1),
              sonet        (2),
			  sdh          (3),
			  direct       (4),
			  plcpInternal (5),
			  plcpExternal (6),
			  e3           (7),
			  ethCrcTrans  (8),	
			  ethCrcNotTrans          (9),
	          directNoScrmbling       (10),
	          plcpInternalNoScrmbling (11),
	          plcpExternalNoScrmbling (12)
	          }
              MAX-ACCESS  read-write
              STATUS  current
              DESCRIPTION
              "The frame type. Valid values for a 155M interface:
               sonet(2), sdh(3). Valid values for a T3 interface:
               direct(4), plcpInternal(5), plcpExternal(6), 
               directNoScrmbling(10), plcpInternalNoScrmbling(11),
               plcpExternalNoScrmbling(12). Valid values for Ethernet 
               interface: ethCrcTrans (8), ethCrcNotTrans(9). 
               (DS1 interfaces frame type is specified in the DSX1 mib)."
              ::= { atmNteConfIfEntry 3 }

          atmConfIfCardType OBJECT-TYPE
              SYNTAX  INTEGER {
		      notApplicable(1), 
		      sc13m-155(2),
		      st13s-155(3),
		      st13l-155(4),
		      utp-155(5),
		      cx-bnc-155(6),
		      e3(7),
		      t3(8),
			  e1(9),
		      e1-ltu(10),
		      fc13l-155(11),
		      fc13lh-155(12),
		      fc15lh-155(13),
		      fc13l-e3(14),
	          fc13lh-e3(15),
		      fc15lh-e3(16),
		      fc13l-t3(17),
		      fc13lh-t3(18),
		      fc15lh-t3(19)
              }			
         	  MAX-ACCESS  read-only
         	  STATUS  deprecated
         	  DESCRIPTION
         	          "The card type."
         	  ::= { atmNteConfIfEntry 4 }
				
         	  atmConfAtmIfVpiVciLimit OBJECT-TYPE
         	  SYNTAX  INTEGER { 
         	  bits15(2),
			  bits17(3)
			   }
         	  MAX-ACCESS  read-only
         	  STATUS  current
         	  DESCRIPTION
         	  "The limit on the sum of the VPI+VCI bits for this interface."
         	  ::= { atmNteConfIfEntry 5 }
				
              atmConfIfHwFeatures  OBJECT-TYPE
              SYNTAX  INTEGER { 
              disable(1),
			  enable(2)
			  }
              MAX-ACCESS  read-write
              STATUS  current
              DESCRIPTION
              "HW features command."
              ::= { atmNteConfIfEntry 6 }

              atmConfIfOutputRate  OBJECT-TYPE
              SYNTAX  Integer32
              MAX-ACCESS  read-write
              STATUS  current
              DESCRIPTION
              "This parameter indicates the output rate in cells/sec, which is 
              supported per port. Successfully setting this parameter 
              is dependent on all other ports values calculations, 
              which are described in the NMS SRS."
              ::= { atmNteConfIfEntry 7 }

              atmConfIfInputRate  OBJECT-TYPE
              SYNTAX  Integer32
              MAX-ACCESS  read-write
              STATUS  current
              DESCRIPTION
              "This parameter indicates the input rate in cells/sec, which is 
              supported per port. Successfully setting this parameter 
              is dependent on all other ports values calculations, 
              which are described in the NMS SRS."
              ::= { atmNteConfIfEntry 8 }

          atmConfAlarmForwarding OBJECT-TYPE
              SYNTAX  INTEGER { disable(2), enable(3) }
              MAX-ACCESS  read-write
              STATUS  current
              DESCRIPTION
              "Enables Path AIS Alarm forwarding upon a failure detection. The
			  following might be considered as a failure: LOS, LOF, LOC, SLM, 
			  LOP, Path AIS and Line AIS. 
              
              disable(2) -  will not forward an alarm upon a failure on this port.  
              
              enable(3) - will forward an alarm upon a failure on this port."
              ::= { atmNteConfIfEntry 9 }


atmNteAlarmIfTable OBJECT-TYPE
              SYNTAX  SEQUENCE OF AtmNteAlarmIfEntry
              MAX-ACCESS  not-accessible
              STATUS  current
              DESCRIPTION
                      "The interface Alarm table."
              ::= { atmNtePrtConfig 2 }

          atmNteAlarmIfEntry OBJECT-TYPE
              SYNTAX  AtmNteAlarmIfEntry
              MAX-ACCESS  not-accessible
              STATUS  current
              DESCRIPTION
                      "An entry in the interface Alarm table."
              INDEX   { ifIndex}
              ::= { atmNteAlarmIfTable 1 }

          AtmNteAlarmIfEntry ::=
              SEQUENCE {
				atmInterfaceActiveAlarms
				      Integer32,
				atmThresholdSectionBIP
				      Integer32,
				atmThresholdLineBIP
				      Integer32,
				atmThresholdLineFEBE
				      Integer32,
				atmThresholdPathBIP
				      Integer32,
				atmThresholdPathFEBE
				      Integer32,
				atmThresholdErroredCells
				      Integer32,
				atmThresholdLostCells
				      Integer32,
				atmThresholdMisinsertedCells
				      Integer32,
			    atmInterfaceAlarmStatus
				      INTEGER,
                atmInterfaceMaskAlarms
				      Integer32
              }

          atmInterfaceActiveAlarms OBJECT-TYPE
              SYNTAX  Integer32 
              MAX-ACCESS  read-only
              STATUS  current
              DESCRIPTION
                      "A Bit String of the active alarms on this interface.
					   An up bit (1) means there is an active alarm of this
					   type. A down bit (0) means there is no such alarm.
                       The meaning of the bits is as follows:
                       1 - LOS
                       2 - LOF
                       3 - Line AIS (SONET)/ PLCP LOF (DS3)
                       4 - LOP
                       5 - Path AIS
                       6 - SLM
                       7 - LCD
                       8 - Line RDI  (SONET)/ PLCP Yellow (DS3)
                       9 - Path RDI  (SONET)/ RDI (DS3)
					   10 - Section BIP (SONET)/ P1/P2 (DS3) > Threshold
					   11 -	Line BIP (SONET)/ PLCP BIP (DS3) > Threshold
					   12 - Line FEBE (SONET)/ PLCP FEBE (DS3) > Threshold
					   13 - Path BIP > Threshold
					   14 - Path FEBE > Threshold
					   15 - HW Failure
                       "
              ::= { atmNteAlarmIfEntry 1 }

          atmThresholdSectionBIP OBJECT-TYPE
              SYNTAX  Integer32 
              MAX-ACCESS  read-write
              STATUS  current
              DESCRIPTION
                      "When Section BIPs are greater than this threshold,
	an active alarm is raised. N/A for ds3/e3 interface."
              ::= { atmNteAlarmIfEntry 2 }

          atmThresholdLineBIP OBJECT-TYPE
              SYNTAX  Integer32 
              MAX-ACCESS  read-write
              STATUS  current
              DESCRIPTION
                      "When Line BIPs are greater than this threshold,
	an active alarm is raised. N/A for ds3/e3 interface."
              ::= { atmNteAlarmIfEntry 3 }

          atmThresholdLineFEBE OBJECT-TYPE
              SYNTAX  Integer32 
              MAX-ACCESS  read-write
              STATUS  current
              DESCRIPTION
                      "When Line FEBEs are greater than this threshold,
	an active alarm is raised. N/A for ds3/e3 interface."
              ::= { atmNteAlarmIfEntry 4 }

          atmThresholdPathBIP OBJECT-TYPE
              SYNTAX  Integer32 
              MAX-ACCESS  read-write
              STATUS  current
              DESCRIPTION
                      "When Path BIPs are greater than this threshold,
					   an active alarm is raised."
              ::= { atmNteAlarmIfEntry 5 }

          atmThresholdPathFEBE OBJECT-TYPE
              SYNTAX  Integer32 
              MAX-ACCESS  read-write
              STATUS  current
              DESCRIPTION
                      "When Path FEBEs are greater than this threshold,
					   an active alarm is raised."
              ::= { atmNteAlarmIfEntry 6 }

          atmThresholdErroredCells OBJECT-TYPE
              SYNTAX  Integer32 
              MAX-ACCESS  read-write
              STATUS  current
              DESCRIPTION
                      "When Errored Cells are greater than this threshold,
					   an active alarm is raised."
              ::= { atmNteAlarmIfEntry 7 }

          atmThresholdLostCells OBJECT-TYPE
              SYNTAX  Integer32 
              MAX-ACCESS  read-write
              STATUS  current
              DESCRIPTION
                      "When Lost Cells are greater than this threshold,
					   an active alarm is raised."
              ::= { atmNteAlarmIfEntry 8 }

          atmThresholdMisinsertedCells OBJECT-TYPE
              SYNTAX  Integer32 
              MAX-ACCESS  read-write
              STATUS  current
              DESCRIPTION
                      "When Misinserted Cells are greater than this threshold,
					   an active alarm is raised."
              ::= { atmNteAlarmIfEntry 9 }

 

          atmInterfaceAlarmStatus OBJECT-TYPE
              SYNTAX  INTEGER { off(2),
			                    on(3) }
              MAX-ACCESS  read-only
              STATUS  current
              DESCRIPTION
                      "The variable is on(3) when there is any active alarm
                       on this interface."
              ::= { atmNteAlarmIfEntry 10 }

          atmInterfaceMaskAlarms OBJECT-TYPE
              SYNTAX  Integer32 
              MAX-ACCESS  read-write
              STATUS  current
              DESCRIPTION
                      "A Bit String of alarms mask on this interface.
					   An up bit (1) means that the respective alarm is masked.
					   A down bit (0) means no mask.
                       The mask is supported for the following alarms:
                       1 - LOS
                       "
              ::= { atmNteAlarmIfEntry 11 }


          atmNteConfVpTable OBJECT-TYPE
              SYNTAX  SEQUENCE OF AtmNteConfVpEntry
              MAX-ACCESS  not-accessible
              STATUS  current
              DESCRIPTION
                      "The ATM VP configuration table.
                       The table is an extension to the atmVplTable of
                       RFC-1695."
              ::= { atmNtePrtConfig 3 }

          atmNteConfVpEntry OBJECT-TYPE
              SYNTAX  AtmNteConfVpEntry
              MAX-ACCESS  not-accessible
              STATUS  current
              DESCRIPTION
                      "An entry in the ATM VP configuration table.
                       ifIndex of the ATM layer."
              INDEX   { ifIndex, atmVplVpi }
              ::= { atmNteConfVpTable 1 }

          AtmNteConfVpEntry ::=
              SEQUENCE {
			atmConfVpPolicing            INTEGER,
			atmConfVpCCAdminStatus       INTEGER,
			atmConfVpLoopbackAdminStatus INTEGER,
			atmConfVpLoopbackSinkAddress OCTET STRING,
			atmConfVpCongestionControl   OCTET STRING,
			atmConfVpCCDirection         INTEGER,
            atmConfVpCreationTime        DateAndTime,
            atmConfVpOamSupport          INTEGER,
            atmConfVpCCOperStatus        INTEGER,
			atmConfVpLoopbackTraffic     INTEGER,
            atmConfVpLoopbackFailureInd	 INTEGER,
            atmConfVpLoopbackFailureThreshold	 Integer32,
			atmConfVpOamDirection         INTEGER
           }

 atmConfVpPolicing OBJECT-TYPE
              SYNTAX  INTEGER { 
                 none(1), 
                 police(2), 
                 monitor(3), 
                 shaping(4), 
                 policingAndShaping(5) 
              }
              MAX-ACCESS  read-write
              STATUS  current
              DESCRIPTION
                      "Policing method desired for this VPL."
              ::= { atmNteConfVpEntry 1 }

        atmConfVpCCAdminStatus OBJECT-TYPE
             SYNTAX INTEGER {
		            up    (2), 
            		down  (3), 
		            source(4),      -- agent send Oam CC cells 
		            sink  (5),      -- agent check received Oam CC cells
                    listenToActivationCells (6),
                    originateActivationCells(7)     
                            } 
             MAX-ACCESS read-write
             STATUS current
             DESCRIPTION
                     	"up(2) - Activate Continuity Check (CC).
                      	down(3) - Deactivate CC.
		                source(4)      - Activate OAM CC(Continuity Check) of local agent
                        			( start sending Oam cells to the remote side ).
      		            sink(5)          - Activate CC of remote agent ( start receiving Oam cells from
      		             				remote 	side ).
                     listenToActivationCells (6) - Passive listener till gets an activation request
                     originateActivationCells(7) - Sands Activation cell according to atmConfVcCCDirection."
             ::= {atmNteConfVpEntry 2}

	atmConfVpLoopbackAdminStatus OBJECT-TYPE
                    SYNTAX INTEGER {
		            up(2),
		            down(3),
		            llid(4),
		            segment(5),
		            endToEnd(6),
		            segmentLlid(7),
		            endToEndLlid(8)
	                } 
             		MAX-ACCESS read-write
             		STATUS current
             		DESCRIPTION
                        "up(2) - Start loopback OAM cells.
                         down(3) - Stop sending loopback OAM cells.
                   
                         For ace2002:
                         up(2)   - Transmitting LB cells with llid all ones 
                                   (i.e. FFFF..FF)
                         down(3) - Not transmitting LB cells. 
                         llid(4) - Transmitting LB cells with llid indicated 
                                    in the address field.
                         segment(5) - Transmitting Segment LB cells with llid
                                       all ones. 
                         endToEnd(6) - Transmitting End to End LB cells with llid
                                        all ones. 
                         segmentLlid(7) - Transmitting Segment LB cells with
                                           llid indicated in the address field.  
                         endToEndLlid(8) - Transmitting LB cells with llid
                                            indicated in the address field.  
                   
                         This parameter value might be in conflict with 
                         atmConfVpOamSupport value, since this parameter is for LB, 
                         while atmConfVpOamSupport is for any other OAM cells."                   
             ::= {atmNteConfVpEntry 3}

	atmConfVpLoopbackSinkAddress OBJECT-TYPE
             		SYNTAX OCTET STRING  (SIZE(0..20))
             		MAX-ACCESS read-write
             		STATUS current
             		DESCRIPTION
                    	 "Destination address.
                    	 For ace101: 2 bytes are used.
                    	 For ace2002: 16 bytes are used."
             ::= {atmNteConfVpEntry 4}

	atmConfVpCongestionControl OBJECT-TYPE
             		SYNTAX OCTET STRING
             		MAX-ACCESS read-write
             		STATUS current
             		DESCRIPTION
                    	 "Each bit indicates a selection of one option 
                               as the following description.  All combinations 
                               are possible and legal.
                               The codes are: 
                               1 - EPD
                               2 - CLP
                               4 - EFCI"
             ::= {atmNteConfVpEntry 5}

     atmConfVpCCDirection OBJECT-TYPE
             SYNTAX  INTEGER {
		            both  (2), 
		            source(4),      
		            sink  (5)     
                            } 
             MAX-ACCESS read-write
             STATUS current
             DESCRIPTION
                     	"both(2) - Agent send OAM CC cells and check received OAM CC cells
                        source(4)- Agent send OAM CC cells.
      		            sink(5)  - Agent checks received OAM CC cells."    
             ::= {atmNteConfVpEntry 6}

     atmConfVpCreationTime OBJECT-TYPE
         SYNTAX   DateAndTime
         MAX-ACCESS   read-only
         STATUS   current
         DESCRIPTION
            "A date-time in which the VP was created."
         ::= { atmNteConfVpEntry 7 }

     atmConfVpOamSupport OBJECT-TYPE
               SYNTAX  INTEGER {
                          intermediate(1),
                          segmentTermination(2),
                          endToEndTermination(3)
                      }
               MAX-ACCESS  read-write
               STATUS  current
               DESCRIPTION
               "OAM support  mode, which determines the device location
                in a segment wise."
               ::= { atmNteConfVpEntry 8 }


	atmConfVpCCOperStatus OBJECT-TYPE
             SYNTAX INTEGER {
		             initial (1),
		             source(4),       
		             sink  (5),
					 both  (8),
		 			 timeout (9), 
				     denied (10),
					 conflict (11),
					 manual (12)
                            } 
             MAX-ACCESS read-only
             STATUS current
             DESCRIPTION
                     	"
		                initial(1) - The CC activation process is not started.
		                source(4) - Agent sends OAM CC cells.
      		            sink(5)   - Agent checks received OAM CC cells.
						both (8) - OAM CC of local and remote agents activation.
		                timeout (9) - Timeout occured on receiving answer from
                                      the remote agent.
		                denied  (10) - CC activation process rejected by remote agent.
		                conflict (11) - local and remote sides requested activation
                                      simultaneously.
				        manual (12) - OAM CC of local agent activated manually.
                        "
             ::= {atmNteConfVpEntry 9}

	atmConfVpLoopbackTraffic OBJECT-TYPE
             		SYNTAX INTEGER { off(2), on(3) } 
             		MAX-ACCESS read-write
             		STATUS current
             		DESCRIPTION
                    	 "This parameter has both command and status meanings: 
                    	 off(2) - Set to 'Off' will Stop traffic loop. Getting this
                    	          value means that the loop is not running.
                      	 on (3) - Set to 'On' will start traffic loop. Getting 
                      	          this value means that the loop is currently running."
             ::= {atmNteConfVpEntry 10}

	atmConfVpLoopbackFailureInd OBJECT-TYPE
             		SYNTAX INTEGER { 
             		disabled(2), 
             		segmentAis(3),
             		segmentRdi(4),
             		segmentAisAndRdi(5),
             		endToEndAis(6),
             		endToEndRdi(7),
             		endToEndAisAndRdi(8)
             		} 
             		MAX-ACCESS read-write
             		STATUS current
             		DESCRIPTION
    "This object allows user to define the Indication that will be created upon 
     a LB cell failure.
     disabled(2) - no indication will be created.
     segmentAis(3) - will cause Tx of a segment AIS.
     segmentRdi(4) - will cause Tx of a segment RDI.
     segmentAisAndRdi(5) - will cause Tx of a segment AIS & RDI. 
     endToEndAis(6) - will cause Tx of an End to End AIS.
     endToEndRdi(7)	- will cause Tx of an End to End RDI.
     endToEndAisAndRdi(8) - will cause Tx of an End to End AIS & RDI.
     Default: disabled(2)."
             ::= {atmNteConfVpEntry 11}

	atmConfVpLoopbackFailureThreshold OBJECT-TYPE
             		SYNTAX Integer32  
             		MAX-ACCESS read-write
             		STATUS current
             		DESCRIPTION
    "The number of the LB failures before starting transmission of the 
    Indication defined by atmConfVcLoopbackFailureInd.
    Range: 1..16. Default: 1."
             ::= {atmNteConfVpEntry 12}

     atmConfVpOamDirection OBJECT-TYPE
             SYNTAX  INTEGER {
		            notApplicable  (1), 
		            downStream     (2),      
		            upStream       (3)     
                            } 
             MAX-ACCESS read-write
             STATUS current
             DESCRIPTION
     "The direction of OAM cell insertion.
	 downStream(2) - The OAM cell will be inserted in downStream.     
	 upStream(3)   - The OAM cell will be inserted in upStream."    
             ::= {atmNteConfVpEntry 13}


--Alarm Table
          atmNteAlarmVpTable OBJECT-TYPE
              SYNTAX  SEQUENCE OF AtmNteAlarmVpEntry
              MAX-ACCESS  not-accessible
              STATUS  current
              DESCRIPTION
                      "The ATM VP Alarm table."
              ::= { atmNtePrtConfig 5 }

          atmNteAlarmVpEntry OBJECT-TYPE
              SYNTAX  AtmNteAlarmVpEntry
              MAX-ACCESS  not-accessible
              STATUS  current
              DESCRIPTION
                      "An entry in the ATM VP Alarm table.
                       ifIndex of the ATM layer."
              INDEX   { ifIndex, atmNteVpAlarmVpi}
              ::= { atmNteAlarmVpTable 1 }

          AtmNteAlarmVpEntry ::=
              SEQUENCE {
			    atmNteVpAlarmVpi
				      Integer32,
			    atmNteVpActiveAlarms
				      Integer32
              }

          atmNteVpAlarmVpi OBJECT-TYPE
              SYNTAX  Integer32 
              MAX-ACCESS  read-only
              STATUS  current
              DESCRIPTION
                      "The VPI on which there is an active alarm."
              ::= { atmNteAlarmVpEntry 1 }

          atmNteVpActiveAlarms OBJECT-TYPE
              SYNTAX  Integer32 
              MAX-ACCESS  read-only
              STATUS  current
              DESCRIPTION
                      "A Bit String of the active alarms on this VP.
					   An up bit (1) means there is an active alarm of this
					   type. A down bit (0) means there is no such alarm.
                       The meaning of the bits is as follows:
                       1 -	VP AIS
                       2 -	VP Loss Of Continuity
					   3 -  VP RDI Reception
					   4 -	VP Errored Cells > Threshold 
					   5 -	VP Lost Cells > Threshold 
					   6 -	VP Misinserted Cells > Threshold
                       "
              ::= { atmNteAlarmVpEntry 2 }

          atmNteAlarmVcTable OBJECT-TYPE
              SYNTAX  SEQUENCE OF AtmNteAlarmVcEntry
              MAX-ACCESS  not-accessible
              STATUS  current
              DESCRIPTION
                      "The ATM VC Alarm table."
              ::= { atmNtePrtConfig 6 }

          atmNteAlarmVcEntry OBJECT-TYPE
              SYNTAX  AtmNteAlarmVcEntry
              MAX-ACCESS  not-accessible
              STATUS  current
              DESCRIPTION
                      "An entry in the ATM VC Alarm table.
                       ifIndex of the ATM layer."
              INDEX   { ifIndex, atmNteVcAlarmVpi, atmNteVcAlarmVci}
              ::= { atmNteAlarmVcTable 1 }

          AtmNteAlarmVcEntry ::=
              SEQUENCE {
			    atmNteVcAlarmVpi
				      Integer32,
			    atmNteVcAlarmVci
				      Integer32,
			    atmNteVcActiveAlarms
				      Integer32
              }

          atmNteVcAlarmVpi OBJECT-TYPE
              SYNTAX  Integer32 
              MAX-ACCESS  read-only
              STATUS  current
              DESCRIPTION
                      "The VPI of the VC on which there is an active alarm."
              ::= { atmNteAlarmVcEntry 1 }

          atmNteVcAlarmVci OBJECT-TYPE
              SYNTAX  Integer32 
              MAX-ACCESS  read-only
              STATUS  current
              DESCRIPTION
                      "The VCI of the VC on which there is an active alarm."
              ::= { atmNteAlarmVcEntry 2 }

atmNteVcActiveAlarms OBJECT-TYPE
              SYNTAX  Integer32 
              MAX-ACCESS  read-only
              STATUS  current
              DESCRIPTION
                      "A Bit String of the active alarms on this VC.
					   An up bit (1) means there is an active alarm of this
					   type. A down bit (0) means there is no such alarm.
                       The meaning of the bits is as follows:
                       1 -	VC AIS
                       2 -	VC Loss Of Continuity
					   3 -  VC RDI
					   4 -	VC Errored Cells > Threshold 
					   5 -	VC Lost Cells > Threshold 
					   6 -	VC Misinserted Cells > Threshold
					   7 - 	Tx VC AIS
					   8 - 	Tx VC RDI
                       "
              ::= { atmNteAlarmVcEntry 3 }

-- 
-- file :v:\doc\rdv\mib\ver485\atm\ace101.txt
-- 

END
