-- MIB file created 08-Jun-2009 11:37:20, by
--   SMICng version 2.2.11-beta(PRO)(Solaris), January 20, 2001. Enterprise key cisco.com

DOCS-IF-MIB DEFINITIONS ::= BEGIN

-- From file: "DOCS-IF-MIB.my"
-- Compile options "4 7 F H N O W 03 06 0B 0G 0N 0T"

IMPORTS
    transmission
            FROM SNMPv2-SMI
    MacAddress, RowStatus, TruthValue, TimeInterval, TimeStamp, 
    StorageType
            FROM SNMPv2-TC
    ifIndex, InterfaceIndexOrZero
            FROM IF-MIB
    InetAddressType, InetAddress
            FROM INET-ADDRESS-MIB
    IANAifType
            FROM IANAifType-MIB
    Counter, Gauge, IpAddress, TimeTicks
            FROM RFC1155-SMI
    OBJECT-TYPE
            FROM RFC-1212;

docsIfMib OBJECT IDENTIFIER ::= { transmission 127 }
-- MODULE-IDENTITY
--  LastUpdated
--    200605240000Z
--  OrgName
--    IETF IPCDN Working Group
--  ContactInfo
--            David Raftus
--     Postal: ATI Technologies Inc.
--             340 Terry Fox Drive, Suite 202
--             Ottawa Ontario
--             Canada
--     Phone:  +1 613 592 1052 ext.222
--     E-mail: david.raftus@ati.com
--    
--             Eduardo Cardona
--     Postal: Cable Television Laboratories, Inc.
--             858 Coal Creek Circle
--             Louisville, CO 80027-9750
--             U.S.A.
--     Phone:  Tel:    +1 303 661 9100
--             Fax:    +1 303 661 9199
--     E-mail: e.cardona@cablelabs.com;mibs@cablelabs.com
--    
--     IETF IPCDN Working Group
--     General Discussion: ipcdn@ietf.org
--     Subscribe: http://www.ietf.org/mailman/listinfo/ipcdn
--     Archive: ftp://ftp.ietf.org/ietf-mail-archive/ipcdn
--     Co-chairs: Richard Woundy, Richard_Woundy@cable.comcast.com
--                Jean-Francois Mule, jf.mule@cablelabs.com
--  Descr
--    This is the MIB Module for DOCSIS 2.0-compliant Radio
--     Frequency (RF) interfaces in Cable Modems and
--     Cable Modem Termination Systems.
--    
--     Copyright (C) The Internet Society (2006).  This
--     version of this MIB module is part of RFC 4546; see
--     the RFC itself for full legal notices.
--  RevDate
--    200605240000Z
--  RevDescr
--    Revision of the IETF RF MIB module for DOCSIS 2.0.
--     This version published as RFC 4546.
--     This MIB module revision includes the following
--     among others:
--     Usage of ifType (205) for upstream logical channels.
--     Addition of downstream and upstream utilization
--     counters.
--     Additional statistics per upstream interface.
--     Upstream channel offline configuration mechanism.
--     Added MIB support for new DOCSIS 2.0 modulation
--     attributes.
--     Euro-DOCSIS downstream interleave values.
--     Adjustments to RFC 2670 definitions based on
--     the MIB review guidelines from the IETF
--     Operations and Management Area (OPS).
--  RevDate
--    199908190000Z
--  RevDescr
--    Initial version, published as RFC 2670.
--     Modified by Mike St. Johns to fix problems identified by
--     the first pass of the MIB doctor.  Of special note,
--     docsIfRangingResp and docsIfCmtsInsertionInterval were
--     obsoleted and replaced by other objects with the same
--     functionality, but with more appropriate syntax.

docsIfMibObjects OBJECT IDENTIFIER ::= { docsIfMib 1 }
docsIfBaseObjects OBJECT IDENTIFIER ::= { docsIfMibObjects 1 }
docsIfCmObjects OBJECT IDENTIFIER ::= { docsIfMibObjects 2 }
docsIfCmtsObjects OBJECT IDENTIFIER ::= { docsIfMibObjects 3 }
docsIfNotification OBJECT IDENTIFIER ::= { docsIfMib 2 }
docsIfConformance OBJECT IDENTIFIER ::= { docsIfMib 3 }
docsIfCompliances OBJECT IDENTIFIER ::= { docsIfConformance 1 }
docsIfGroups    OBJECT IDENTIFIER ::= { docsIfConformance 2 }

TenthdBmV ::= INTEGER
-- TEXTUAL-CONVENTION
--  DspHint
--    d-1
--  Status
--    mandatory
--  Descr
--    This data type represents power levels that are normally
--     expressed in dBmV.  Units are in tenths of a dBmV;
--     for example, 5.1 dBmV will be represented as 51.

TenthdB ::= INTEGER
-- TEXTUAL-CONVENTION
--  DspHint
--    d-1
--  Status
--    mandatory
--  Descr
--    This data type represents power levels that are normally
--     expressed in dB.  Units are in tenths of a dB;
--     for example, 5.1 dB will be represented as 51.

DocsisVersion ::= INTEGER {
        docsis10(1),
        docsis11(2),
        docsis20(3)
        }
-- TEXTUAL-CONVENTION
--  Status
--    mandatory
--  Descr
--    Indicates the DOCSIS Radio Frequency specification being
--     referenced.
--     'docsis10' indicates DOCSIS 1.0.
--     'docsis11' indicates DOCSIS 1.1.
--     'docsis20' indicates DOCSIS 2.0.

DocsisQosVersion ::= INTEGER {
        docsis10(1),
        docsis11(2)
        }
-- TEXTUAL-CONVENTION
--  Status
--    mandatory
--  Descr
--    Indicates the referenced quality-of-service
--     level.
--     'docsis10 refers to DOCSIS 1.0 Class of
--     Service queuing services, and 'docsis11' refers
--     to DOCSIS 1.1 Quality of Service.

DocsisUpstreamType ::= INTEGER {
        --?? enum value of zero may cause problems
        unknown(0),
        tdma(1),
        atdma(2),
        scdma(3),
        tdmaAndAtdma(4)
        }
-- TEXTUAL-CONVENTION
--  Status
--    mandatory
--  Descr
--    Indicates the DOCSIS Upstream Channel Type.
--     'unknown' means information not available.
--     'tdma' is related to TDMA, Time Division
--     Multiple Access; 'atdma' is related to A-TDMA,
--     Advanced Time Division Multiple Access,
--     'scdma' is related to S-CDMA, Synchronous
--     Code Division Multiple Access.
--     'tdmaAndAtdma is related to simultaneous support of
--     TDMA and A-TDMA modes.

DocsEqualizerData ::= OCTET STRING(SIZE(0|36..260))
-- TEXTUAL-CONVENTION
--  Status
--    mandatory
--  Descr
--    This data type represents the equalizer data
--     as measured at the receiver interface.
--     The format of the equalizer follows the structure of the
--     Transmit Equalization Adjust RNG-RSP TLV of DOCSIS RFI
--     v2.0 :
--     1 byte Main tap location 1..(n + m)
--     1 byte Number of forward taps per symbol
--     1 byte Number of forward taps: n
--     1 byte Number of reverse taps: m
--    
--     Following are the equalizer coefficients:
--     First, forward taps coefficients:
--     2 bytes F1 (real),  2 bytes  F1 (imag)
--     ...
--     2 bytes Fn (real),  2 bytes  Fn (imag)
--    
--     Then, reverse taps coefficients:
--     2 bytes D1 (real),  2 bytes  D1 (imag)
--     ...
--    
--     2 bytes Dm (real),  2 bytes  Dm (imag)
--    
--     The equalizer coefficients are considered signed 16-bit
--     integers in the range from -32768 (0x8000) to 32767
--     (0x7FFF).
--    
--     DOCSIS specifications require up to a maximum of
--     64 equalizer taps (n + m); therefore, this object size
--      can get up 260 bytes (4 + 4x64).
--     The minimum object size (other than zero) for a t-spaced
--     tap with a minimum of 8 symbols will be 36 (4 + 4x8).
--  Refer
--    Data-Over-Cable Service Interface Specifications: Radio
--     Frequency Interface Specification SP-RFIv2.0-I10-051209,
--     Figure 8-23.

docsIfDownstreamChannelTable OBJECT-TYPE
    SYNTAX SEQUENCE OF DocsIfDownstreamChannelEntry
    ACCESS not-accessible
    STATUS mandatory
    DESCRIPTION
        "This table describes the attributes of downstream
         channels (frequency bands)."
    REFERENCE
        "Data-Over-Cable Service Interface Specifications: Radio
         Frequency Interface Specification SP-RFIv2.0-I10-051209,
         Tables 6-16, and 6-17."
    ::= { docsIfBaseObjects 1 }

docsIfDownstreamChannelEntry OBJECT-TYPE
    SYNTAX DocsIfDownstreamChannelEntry
    ACCESS not-accessible
    STATUS mandatory
    DESCRIPTION
        "An entry provides a list of attributes for a single
         downstream channel.
         An entry in this table exists for each ifEntry with an
         ifType of docsCableDownstream(128)."
    INDEX { ifIndex }
    ::= { docsIfDownstreamChannelTable 1 }

DocsIfDownstreamChannelEntry ::= SEQUENCE {
    docsIfDownChannelId INTEGER,
    docsIfDownChannelFrequency INTEGER,
    docsIfDownChannelWidth INTEGER,
    docsIfDownChannelModulation INTEGER,
    docsIfDownChannelInterleave INTEGER,
    docsIfDownChannelPower TenthdBmV,
    docsIfDownChannelAnnex INTEGER,
    docsIfDownChannelStorageType StorageType
    }

docsIfDownChannelId OBJECT-TYPE
    SYNTAX INTEGER(0..255)
    ACCESS read-only
    STATUS mandatory
    DESCRIPTION
        "The Cable Modem Termination System identification of the
         downstream channel within this particular MAC interface.
         if the interface is down, the object returns the most
         current value.  If the downstream channel ID is unknown,
         this object returns a value of 0."
    ::= { docsIfDownstreamChannelEntry 1 }

docsIfDownChannelFrequency OBJECT-TYPE
    SYNTAX INTEGER(0..1000000000)
--  Units
--    hertz
    ACCESS read-write
    STATUS mandatory
    DESCRIPTION
        "The center of the downstream frequency associated with
         this channel.  This object will return the current tuner
         frequency.  If a CMTS provides IF output, this object
         will return 0, unless this CMTS is in control of the
         final downstream frequency.  See the associated
         compliance object for a description of valid frequencies
         that may be written to this object."
    REFERENCE
        "Data-Over-Cable Service Interface Specifications: Radio
         Frequency Interface Specification SP-RFIv2.0-I10-051209,
         Section 6.3.3."
    ::= { docsIfDownstreamChannelEntry 2 }

docsIfDownChannelWidth OBJECT-TYPE
    SYNTAX INTEGER(0..16000000)
--  Units
--    hertz
    ACCESS read-write
    STATUS mandatory
    DESCRIPTION
        "The bandwidth of this downstream channel.  Most
         implementations are expected to support a channel width
         of 6 MHz (North America) and/or 8 MHz (Europe).  See the
         associated compliance object for a description of the
         valid channel widths for this object."
    REFERENCE
        "Data-Over-Cable Service Interface Specifications: Radio
         Frequency Interface Specification SP-RFIv2.0-I10-051209,
         Table 6-17."
    ::= { docsIfDownstreamChannelEntry 3 }

docsIfDownChannelModulation OBJECT-TYPE
    SYNTAX INTEGER {
        unknown(1),
        other(2),
        qam64(3),
        qam256(4)
        }
    ACCESS read-write
    STATUS mandatory
    DESCRIPTION
        "The modulation type associated with this downstream
         channel.  If the interface is down, this object either
         returns the configured value (CMTS), the most current
         value (CM), or the value of unknown(1).  See the
         associated conformance object for write conditions and
         limitations.  See the reference for specifics on the
         modulation profiles implied by qam64 and qam256."
    REFERENCE
        "Data-Over-Cable Service Interface Specifications: Radio
         Frequency Interface Specification SP-RFIv2.0-I10-051209,
         Table 6-17."
    ::= { docsIfDownstreamChannelEntry 4 }

docsIfDownChannelInterleave OBJECT-TYPE
    SYNTAX INTEGER {
        unknown(1),
        other(2),
        taps8Increment16(3),
        taps16Increment8(4),
        taps32Increment4(5),
        taps64Increment2(6),
        taps128Increment1(7),
        taps12increment17(8)
        }
    ACCESS read-write
    STATUS mandatory
    DESCRIPTION
        "The Forward Error Correction (FEC) interleaving used
         for this downstream channel.
         Values are defined as follows:
         taps8Increment16(3):   protection 5.9/4.1 usec,
                                latency .22/.15 msec
         taps16Increment8(4):   protection 12/8.2 usec,
                                latency .48/.33 msec
         taps32Increment4(5):   protection 24/16 usec,
                                latency .98/.68 msec
         taps64Increment2(6):   protection 47/33 usec,
                                latency 2/1.4 msec
         taps128Increment1(7):  protection 95/66 usec,
                                latency 4/2.8 msec
         taps12increment17(8):  protection 18/14 usec,
                                latency 0.43/0.32 msec
        
        The value 'taps12increment17' is supported by EuroDOCSIS
        cable systems only, and the others by DOCSIS cable systems.
        
         If the interface is down, this object either returns
         the configured value (CMTS), the most current value (CM),
         or the value of unknown(1).
         The value of other(2) is returned if the interleave
         is known but not defined in the above list.
         See the associated conformance object for write
         conditions and limitations.  See the reference for the FEC
         configuration described by the setting of this object."
    REFERENCE
        "Data-Over-Cable Service Interface Specifications: Radio
         Frequency Interface Specification SP-RFIv2.0-I10-051209,
         Table 6-15."
    ::= { docsIfDownstreamChannelEntry 5 }

docsIfDownChannelPower OBJECT-TYPE
    SYNTAX TenthdBmV
--    Rsyntax INTEGER
--  Units
--    dBmV
    ACCESS read-write
    STATUS mandatory
    DESCRIPTION
        "At the CMTS, the operational transmit power.  At the CM,
         the received power level.
         If the interface is down, this object either returns
         the configured value (CMTS), the most current value (CM)
         or the value of 0.  See the associated conformance object
         for write conditions and limitations.  See the reference
         for recommended and required power levels."
    REFERENCE
        "Data-Over-Cable Service Interface Specifications: Radio
         Frequency Interface Specification SP-RFIv2.0-I10-051209,
         Tables 6-16, 6-17."
    ::= { docsIfDownstreamChannelEntry 6 }

docsIfDownChannelAnnex OBJECT-TYPE
    SYNTAX INTEGER {
        unknown(1),
        other(2),
        annexA(3),
        annexB(4),
        annexC(5)
        }
    ACCESS read-only
    STATUS mandatory
    DESCRIPTION
        "The value of this object indicates the conformance of
         the implementation to important regional cable standards.
         annexA : Annex A from ITU-T J.83 is used.
                  (equivalent to EN 300 429)
         annexB : Annex B from ITU-T J.83 is used.
         annexC : Annex C from ITU-T J.83 is used."
    REFERENCE
        "Data-Over-Cable Service Interface Specifications: Radio
         Frequency Interface Specification SP-RFIv2.0-I10-051209,
         Sections 6.3.1, and H.3.1."
    ::= { docsIfDownstreamChannelEntry 7 }

docsIfDownChannelStorageType OBJECT-TYPE
    SYNTAX StorageType
--    Rsyntax INTEGER {
--        other(1),
--        volatile(2),
--        nonVolatile(3),
--        permanent(4),
--        readOnly(5)
--        }
    ACCESS read-only
    STATUS mandatory
    DESCRIPTION
        "The storage type for this conceptual row.
         Entries with this object set to permanent(4)
         do not require write operations for read-write
         objects."
    ::= { docsIfDownstreamChannelEntry 8 }

docsIfUpstreamChannelTable OBJECT-TYPE
    SYNTAX SEQUENCE OF DocsIfUpstreamChannelEntry
    ACCESS not-accessible
    STATUS mandatory
    DESCRIPTION
        "This table describes the attributes of attached upstream
         channels."
    ::= { docsIfBaseObjects 2 }

docsIfUpstreamChannelEntry OBJECT-TYPE
    SYNTAX DocsIfUpstreamChannelEntry
    ACCESS not-accessible
    STATUS mandatory
    DESCRIPTION
        "List of attributes for a single upstream channel.  For
         DOCSIS 2.0 CMTSs, an entry in this table exists for
         each ifEntry with an ifType of docsCableUpstreamChannel
         (205).
         For DOCSIS 1.x CM/CMTSs and DOCSIS 2.0 CMs, an entry in
         this table exists for each ifEntry with an ifType of
         docsCableUpstream (129).
        
         For DOCSIS 2.0 CMTSs, two classes of interfaces can be
         defined for this table:
          o Upstream Physical Interfaces: The traditional DOCSIS
            1.x CMTS upstream interface ifType 129 and the DOCSIS
            2.0 ifType 205 that are functional.  In other words,
            interfaces that represent upstream receivers within
            an RF MAC interface.
            Entries of physical interfaces are exposed to the
            management interface with their corresponding
            ifStack hierarchy and are not administratively
            created by this table.
        
          o Upstream Temporary Interfaces: A fictitious
            interface created for the purpose of manipulating
            physical interface parameters offline, then
            validating prior to updating the target physical
            interface.
        
         In case of a reinitialization of the managed system,
         physical interfaces values persist while the temporary
         interfaces are not recreated.
        
         This mechanism helps to minimize service disruptions
         originating in situations where a group of interface
         parameter values need to be consistent with each other
         in SET operations.  A temporary buffer
         (temporary interface) is provided to allow the CMTS
         to validate the parameters offline."
    INDEX { ifIndex }
    ::= { docsIfUpstreamChannelTable 1 }

DocsIfUpstreamChannelEntry ::= SEQUENCE {
    docsIfUpChannelId INTEGER,
    docsIfUpChannelFrequency INTEGER,
    docsIfUpChannelWidth INTEGER,
    docsIfUpChannelModulationProfile Gauge,
    docsIfUpChannelSlotSize Gauge,
    docsIfUpChannelTxTimingOffset Gauge,
    docsIfUpChannelRangingBackoffStart INTEGER,
    docsIfUpChannelRangingBackoffEnd INTEGER,
    docsIfUpChannelTxBackoffStart INTEGER,
    docsIfUpChannelTxBackoffEnd INTEGER,
    docsIfUpChannelScdmaActiveCodes Gauge,
    docsIfUpChannelScdmaCodesPerSlot INTEGER,
    docsIfUpChannelScdmaFrameSize Gauge,
    docsIfUpChannelScdmaHoppingSeed Gauge,
    docsIfUpChannelType DocsisUpstreamType,
    docsIfUpChannelCloneFrom InterfaceIndexOrZero,
    docsIfUpChannelUpdate TruthValue,
    docsIfUpChannelStatus RowStatus,
    docsIfUpChannelPreEqEnable TruthValue
    }

docsIfUpChannelId OBJECT-TYPE
    SYNTAX INTEGER(0..255)
    ACCESS read-only
    STATUS mandatory
    DESCRIPTION
        "The CMTS identification of the upstream channel."
    ::= { docsIfUpstreamChannelEntry 1 }

docsIfUpChannelFrequency OBJECT-TYPE
    SYNTAX INTEGER(0..1000000000)
--  Units
--    hertz
    ACCESS read-write
    STATUS mandatory
    DESCRIPTION
        "The center of the frequency band associated with this
         upstream interface.  This object returns 0 if the frequency
         is undefined or unknown.  Minimum permitted upstream
         frequency is 5,000,000 Hz for current technology.  See
         the associated conformance object for write conditions
         and limitations."
    REFERENCE
        "Data-Over-Cable Service Interface Specifications: Radio
         Frequency Interface Specification SP-RFIv2.0-I10-051209,
         Table 4-2."
    ::= { docsIfUpstreamChannelEntry 2 }

docsIfUpChannelWidth OBJECT-TYPE
    SYNTAX INTEGER(0..64000000)
--  Units
--    hertz
    ACCESS read-write
    STATUS mandatory
    DESCRIPTION
        "The bandwidth of this upstream interface.  This object
         returns 0 if the interface width is undefined or unknown.
         Minimum permitted interface width is currently 200,000 Hz.
         See the associated conformance object for write conditions
         and limitations."
    REFERENCE
        "Data-Over-Cable Service Interface Specifications: Radio
         Frequency Interface Specification SP-RFIv2.0-I10-051209,
         Table 6-5."
    ::= { docsIfUpstreamChannelEntry 3 }

docsIfUpChannelModulationProfile OBJECT-TYPE
    SYNTAX Gauge
    ACCESS read-write
    STATUS mandatory
    DESCRIPTION
        "An entry identical to the docsIfModIndex in the
         docsIfCmtsModulationTable that describes this channel.
         This channel is further instantiated there by a grouping
         of interval usage codes (IUCs) that, together, fully
         describe the channel modulation.  This object returns 0 if
         the docsIfCmtsModulationTable entry does not exist or is
         empty.  See the associated conformance object for write
         conditions and limitations.
         Setting this object returns an 'inconsistentValue'
         error if the following conditions are not satisfied:
         1. All the IUC entries in the selected modulation profile
         MUST have the same value of docsIfCmtsModChannelType.
         2. All of the Modulation parameters in the selected
         modulation profile MUST be consistent with the other
         parameters in this docsIfUpstreamChannelEntry."
    REFERENCE
        "Data-Over-Cable Service Interface Specifications: Radio
         Frequency Interface Specification SP-RFIv2.0-I10-051209,
         Table 8-19."
    ::= { docsIfUpstreamChannelEntry 4 }

docsIfUpChannelSlotSize OBJECT-TYPE
    SYNTAX Gauge
--  Units
--    ticks
    ACCESS read-write
    STATUS mandatory
    DESCRIPTION
        "Applicable to TDMA and ATDMA channel types only.
         The number of 6.25 microsecond ticks in each upstream
         mini-slot.  Returns zero if the value is undefined or
         unknown or in case of an SCDMA channel.
         See the associated conformance object for write
         conditions and limitations."
    REFERENCE
        "Data-Over-Cable Service Interface Specifications: Radio
         Frequency Interface Specification SP-RFIv2.0-I10-051209,
         Section 8.1.2.4."
    ::= { docsIfUpstreamChannelEntry 5 }

docsIfUpChannelTxTimingOffset OBJECT-TYPE
    SYNTAX Gauge
    ACCESS read-only
    STATUS mandatory
    DESCRIPTION
        "At the CM, a measure of the current round trip time
         obtained from the ranging offset (initial ranging offset +
         ranging offset adjustments).
         At the CMTS, the maximum of timing offset, among all the
         CMs that are/were present on the channel, taking into
         account all ( initial + periodic ) timing offset
         corrections that were sent for each of the CMs.  Generally,
         these measurements are positive, but if the measurements
         are negative, the value of this object is zero.  Used for
         timing of CM upstream transmissions to ensure synchronized
         arrivals at the CMTS.
         Units are one 64th fraction of 6.25 microseconds."
    REFERENCE
        "Data-Over-Cable Service Interface Specifications: Radio
         Frequency Interface Specification SP-RFIv2.0-I10-051209,
         Section 6.2.19."
    ::= { docsIfUpstreamChannelEntry 6 }

docsIfUpChannelRangingBackoffStart OBJECT-TYPE
    SYNTAX INTEGER(0..16)
    ACCESS read-write
    STATUS mandatory
    DESCRIPTION
        "The initial random backoff window to use when retrying
         Ranging Requests.  Expressed as a power of 2.  A value of
         16 at the CMTS indicates that a proprietary adaptive retry
         mechanism is to be used.  See the associated conformance
         object for write conditions and limitations."
    REFERENCE
        "Data-Over-Cable Service Interface Specifications: Radio
         Frequency Interface Specification SP-RFIv2.0-I10-051209,
         Sections 8.3.4, and 9.4."
    ::= { docsIfUpstreamChannelEntry 7 }

docsIfUpChannelRangingBackoffEnd OBJECT-TYPE
    SYNTAX INTEGER(0..16)
    ACCESS read-write
    STATUS mandatory
    DESCRIPTION
        "The final random backoff window to use when retrying
         Ranging Requests.  Expressed as a power of 2.  A value of
         16 at the CMTS indicates that a proprietary adaptive retry
         mechanism is to be used.  See the associated conformance
         object for write conditions and limitations."
    REFERENCE
        "Data-Over-Cable Service Interface Specifications: Radio
         Frequency Interface Specification SP-RFIv2.0-I10-051209,
         Section 8.3.4, and 9.4."
    ::= { docsIfUpstreamChannelEntry 8 }

docsIfUpChannelTxBackoffStart OBJECT-TYPE
    SYNTAX INTEGER(0..16)
    ACCESS read-write
    STATUS mandatory
    DESCRIPTION
        "The initial random backoff window to use when retrying
         transmissions.  Expressed as a power of 2.  A value of 16
         at the CMTS indicates that a proprietary adaptive retry
         mechanism is to be used.  See the associated conformance
         object for write conditions and limitations."
    REFERENCE
        "Data-Over-Cable Service Interface Specifications: Radio
         Frequency Interface Specification SP-RFIv2.0-I10-051209,
         Section 8.3.4, and 9.4."
    ::= { docsIfUpstreamChannelEntry 9 }

docsIfUpChannelTxBackoffEnd OBJECT-TYPE
    SYNTAX INTEGER(0..16)
    ACCESS read-write
    STATUS mandatory
    DESCRIPTION
        "The final random backoff window to use when retrying
         transmissions.  Expressed as a power of 2.  A value of 16
         at the CMTS indicates that a proprietary adaptive retry
         mechanism is to be used.  See the associated conformance
         object for write conditions and limitations."
    REFERENCE
        "Data-Over-Cable Service Interface Specifications: Radio
         Frequency Interface Specification SP-RFIv2.0-I10-051209,
         Section 8.3.4, and 9.4."
    ::= { docsIfUpstreamChannelEntry 10 }

docsIfUpChannelScdmaActiveCodes OBJECT-TYPE
    SYNTAX Gauge(0|64..66|68..70|72|74..78|80..82|84..88|90..96|98..100|102|104..106|108|110..112|114..126|128)
    ACCESS read-write
    STATUS mandatory
    DESCRIPTION
        "Applicable for SCDMA channel types only.
         Number of active codes.  Returns zero for
         Non-SCDMA channel types.  Note that legal
         values from 64..128 MUST be non-prime."
    REFERENCE
        "Data-Over-Cable Service Interface Specifications: Radio
         Frequency Interface Specification SP-RFIv2.0-I10-051209,
         Section 6.2.11.2.1."
    ::= { docsIfUpstreamChannelEntry 11 }

docsIfUpChannelScdmaCodesPerSlot OBJECT-TYPE
    SYNTAX INTEGER(0|2..32)
--  Units
--    codesperMinislots
    ACCESS read-write
    STATUS mandatory
    DESCRIPTION
        "Applicable for SCDMA channel types only.
         The number of SCDMA codes per mini-slot.
         Returns zero if the value is undefined or unknown or in
         case of a TDMA or ATDMA channel."
    REFERENCE
        "Data-Over-Cable Service Interface Specifications: Radio
         Frequency Interface Specification SP-RFIv2.0-I10-051209,
         Section 6.2.11.2.1."
    ::= { docsIfUpstreamChannelEntry 12 }

docsIfUpChannelScdmaFrameSize OBJECT-TYPE
    SYNTAX Gauge(0..32)
--  Units
--    spreadIntervals
    ACCESS read-write
    STATUS mandatory
    DESCRIPTION
        "Applicable for SCDMA channel types only.
         SCDMA Frame size in units of spreading intervals.
         This value returns zero for non-SCDMA Profiles."
    REFERENCE
        "Data-Over-Cable Service Interface Specifications: Radio
         Frequency Interface Specification SP-RFIv2.0-I10-051209,
         Section 6.2.12."
    ::= { docsIfUpstreamChannelEntry 13 }

docsIfUpChannelScdmaHoppingSeed OBJECT-TYPE
    SYNTAX Gauge(0..32767)
    ACCESS read-write
    STATUS mandatory
    DESCRIPTION
        "Applicable for SCDMA channel types only.
         15-bit seed used for code hopping sequence initialization.
         Returns zero for non-SCDMA channel types.
         Setting this value to a value different than zero for
         non-SCDMA channel types returns the error 'wrongValue'."
    REFERENCE
        "Data-Over-Cable Service Interface Specifications: Radio
         Frequency Interface Specification SP-RFIv2.0-I10-051209,
         Section 6.2.14.1."
    ::= { docsIfUpstreamChannelEntry 14 }

docsIfUpChannelType OBJECT-TYPE
    SYNTAX DocsisUpstreamType
--    Rsyntax INTEGER {
--        ?? enum value of zero may cause problems
--        unknown(0),
--        tdma(1),
--        atdma(2),
--        scdma(3),
--        tdmaAndAtdma(4)
--        }
    ACCESS read-only
    STATUS mandatory
    DESCRIPTION
        "Reflects the Upstream channel type.
         This object returns the value of docsIfCmtsModChannelType
         for the modulation profile selected in
         docsIfUpChannelModulationProfile for this row."
    REFERENCE
        "Data-Over-Cable Service Interface Specifications: Radio
         Frequency Interface Specification SP-RFIv2.0-I10-051209,
         Section 6.2.1."
    ::= { docsIfUpstreamChannelEntry 15 }

docsIfUpChannelCloneFrom OBJECT-TYPE
    SYNTAX InterfaceIndexOrZero
--    Rsyntax INTEGER(0..2147483647)
    ACCESS read-write
    STATUS mandatory
    DESCRIPTION
        "This object contains the ifIndex value of the physical
         interface row entry whose parameters are to be adjusted.
        
         Upon setting this object to the ifIndex value of a
         physical interface, the following interface objects values
         are copied to this entry:
         docsIfUpChannelFrequency,
         docsIfUpChannelWidth,
         docsIfUpChannelModulationProfile,
         docsIfUpChannelSlotSize,
         docsIfUpChannelRangingBackoffStart,
         docsIfUpChannelRangingBackoffEnd,
         docsIfUpChannelTxBackoffStart,
         docsIfUpChannelTxBackoffEnd,
         docsIfUpChannelScdmaActiveCodes,
         docsIfUpChannelScdmaCodesPerSlot,
         docsIfUpChannelScdmaFrameSize,
         docsIfUpChannelScdmaHoppingSeed,
         docsIfUpChannelType, and
         docsIfUpChannelPreEqEnable
         Setting this object to the value of a non-existent or
         a temporary upstream interface returns the error
         'wrongValue'.
         This object MUST contain a value of zero for physical
         interfaces entries.
         Setting this object in row entries that correspond to
         physical interfaces returns the error 'wrongValue'."
    ::= { docsIfUpstreamChannelEntry 16 }

docsIfUpChannelUpdate OBJECT-TYPE
    SYNTAX TruthValue
--    Rsyntax INTEGER {
--        true(1),
--        false(2)
--        }
    ACCESS read-write
    STATUS mandatory
    DESCRIPTION
        "Used to perform the copy of adjusted parameters from the
         temporary interface entry to the physical interface
         indicated by the docsIfUpChannelCloneFrom object.  The
         transfer is initiated through an SNMP SET to 'true' of
         this object.
         A SET to 'true' fails and returns error 'commitFailed'
         if docsIfUpChannelStatus value is 'notInService', which
         means that the interface parameters values are not
         compatible with each other or have not been validated yet.
         Reading this object always returns 'false'."
    ::= { docsIfUpstreamChannelEntry 17 }

docsIfUpChannelStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is only used for the creation of a temporary
         upstream row with the purpose of updating the parameters
         of a physical upstream channel entry.
        
         The following restrictions apply to this object:
         1. This object is not writable for physical interfaces.
         2. Temporary interface entries are only created by a SET
            of this object to createandWait(5).
         3. ifAdminStatus from the Interface MIB RFC 2863 is used
            to take a physical upstream channel offline, to be
            consistent with DOCSIS 1.x operation, as indicated in
            RFC 2670.
            In addition,
             o ifAdminStatus 'down' is reflected in this object
               as 'notInService'.
             o ifOperStatus 'down' while ifAdminStatus 'up' is
               reflected in this object as 'notInservice'.
         4. Temporary created rows MUST be set to 'active' with
            the purpose of validating upstream parameter
            consistency prior to transferring the parameters to the
            physical interface.
        
         Below is a mandatory procedure for adjusting the values
         of a physical interface:
         1. Create a temporary interface entry through an SNMP SET
            using 'createAndWait'.  At this point, the RowStatus
            reports 'notReady'.
            The Manager entity uses an ifIndex value outside the
            operational range of the physical interfaces for the
            creation of a temporary interface.
         2. Set the docsIfUpChannelCloneFrom object to the ifIndex
            value of the physical row to update.  Now
            docsIfUpChannelStatus reports 'notInService'.
         3. Change the upstream parameters to the desired values
            in the temporary row.
         4. Validate that all parameters are consistent by setting
            docsIfUpChannelStatus to 'active'.  A failure to set the
            RowStatus to 'active' returns the error 'commitFailed',
            which means the parameters are not compatible with the
            target physical interface.
         5. With docsIfUpChannelStatus 'active', transfer the
            parameters to the target physical interface by setting
            the object docsIfUpChannelUpdate to 'true'.
         6. Delete the temporary row by setting
            docsIfUpChannelStatus to 'destroy'."
    ::= { docsIfUpstreamChannelEntry 18 }

docsIfUpChannelPreEqEnable OBJECT-TYPE
    SYNTAX TruthValue
--    Rsyntax INTEGER {
--        true(1),
--        false(2)
--        }
    ACCESS read-write
    STATUS mandatory
    DESCRIPTION
        "At the CMTS, this object is used to enable or disable
         pre-equalization on the upstream channel represented by
         this table instance.  At the CM, this object is read-only
         and reflects the status of pre-equalization as represented
         in the RNG-RSP.  Pre-equalization is considered enabled at
         the CM if a RNG-RSP with pre-equalization data has been
         received at least once since the last mac
         reinitialization."
    DEFVAL { false }
    ::= { docsIfUpstreamChannelEntry 19 }

docsIfQosProfileTable OBJECT-TYPE
    SYNTAX SEQUENCE OF DocsIfQosProfileEntry
    ACCESS not-accessible
    STATUS mandatory
    DESCRIPTION
        "Describes the attributes for each class of service."
    ::= { docsIfBaseObjects 3 }

docsIfQosProfileEntry OBJECT-TYPE
    SYNTAX DocsIfQosProfileEntry
    ACCESS not-accessible
    STATUS mandatory
    DESCRIPTION
        "Describes the attributes for a single class of service.
         If implemented as read-create in the Cable Modem
         Termination System, creation of entries in this table is
         controlled by the value of
         docsIfCmtsQosProfilePermissions.
        
         If implemented as read-only, entries are created based
         on information in REG-REQ MAC messages received from
         cable modems (for Cable Modem Termination System), or
         based on information extracted from the TFTP option file
         (for Cable Modem).
         In the Cable Modem Termination System, read-only entries
         are removed if no longer referenced by
         docsIfCmtsServiceTable.
        
         An entry in this table MUST not be removed while it is
         referenced by an entry in docsIfCmServiceTable (Cable
         Modem) or docsIfCmtsServiceTable (Cable Modem Termination
         System).
        
         An entry in this table SHOULD NOT be changeable while
         it is referenced by an entry in docsIfCmtsServiceTable.
        
         If this table is created automatically, there SHOULD only
         be a single entry for each Class of Service.  Multiple
         entries with the same Class of Service parameters are NOT
         RECOMMENDED."
    INDEX { docsIfQosProfIndex }
    ::= { docsIfQosProfileTable 1 }

DocsIfQosProfileEntry ::= SEQUENCE {
    docsIfQosProfIndex INTEGER,
    docsIfQosProfPriority INTEGER,
    docsIfQosProfMaxUpBandwidth INTEGER,
    docsIfQosProfGuarUpBandwidth INTEGER,
    docsIfQosProfMaxDownBandwidth INTEGER,
    docsIfQosProfMaxTxBurst INTEGER,
    docsIfQosProfBaselinePrivacy TruthValue,
    docsIfQosProfStatus RowStatus,
    docsIfQosProfMaxTransmitBurst INTEGER,
    docsIfQosProfStorageType StorageType
    }

docsIfQosProfIndex OBJECT-TYPE
    SYNTAX INTEGER(1..16383)
    ACCESS not-accessible
    STATUS mandatory
    DESCRIPTION
        "The index value that uniquely identifies an entry
         in the docsIfQosProfileTable."
    ::= { docsIfQosProfileEntry 1 }

docsIfQosProfPriority OBJECT-TYPE
    SYNTAX INTEGER(0..7)
    ACCESS read-write
    STATUS mandatory
    DESCRIPTION
        "A relative priority assigned to this service when
         allocating bandwidth.  Zero indicates lowest priority
         and seven indicates highest priority.
         Interpretation of priority is device-specific.
         MUST NOT be changed while this row is active."
    REFERENCE
        "Data-Over-Cable Service Interface Specifications: Radio
         Frequency Interface Specification SP-RFIv2.0-I10-051209,
         Annex C.1.1.4."
    DEFVAL { 0 }
    ::= { docsIfQosProfileEntry 2 }

docsIfQosProfMaxUpBandwidth OBJECT-TYPE
    SYNTAX INTEGER(0..100000000)
--  Units
--    bits per second
    ACCESS read-write
    STATUS mandatory
    DESCRIPTION
        "The maximum upstream bandwidth, in bits per second,
         allowed for a service with this service class.
         Zero if there is no restriction of upstream bandwidth.
         MUST NOT be changed while this row is active."
    REFERENCE
        "Data-Over-Cable Service Interface Specifications: Radio
         Frequency Interface Specification SP-RFIv2.0-I10-051209,
         Annex C.1.1.4."
    DEFVAL { 0 }
    ::= { docsIfQosProfileEntry 3 }

docsIfQosProfGuarUpBandwidth OBJECT-TYPE
    SYNTAX INTEGER(0..100000000)
--  Units
--    bits per second
    ACCESS read-write
    STATUS mandatory
    DESCRIPTION
        "Minimum guaranteed upstream bandwidth, in bits per second,
         allowed for a service with this service class.
         MUST NOT be changed while this row is active."
    REFERENCE
        "Data-Over-Cable Service Interface Specifications: Radio
         Frequency Interface Specification SP-RFIv2.0-I10-051209,
         Annex C.1.1.4."
    DEFVAL { 0 }
    ::= { docsIfQosProfileEntry 4 }

docsIfQosProfMaxDownBandwidth OBJECT-TYPE
    SYNTAX INTEGER(0..100000000)
--  Units
--    bits per second
    ACCESS read-write
    STATUS mandatory
    DESCRIPTION
        "The maximum downstream bandwidth, in bits per second,
         allowed for a service with this service class.
         Zero if there is no restriction of downstream bandwidth.
         MUST NOT be changed while this row is active."
    REFERENCE
        "Data-Over-Cable Service Interface Specifications: Radio
         Frequency Interface Specification SP-RFIv2.0-I10-051209,
         Annex C.1.1.4."
    DEFVAL { 0 }
    ::= { docsIfQosProfileEntry 5 }

docsIfQosProfMaxTxBurst OBJECT-TYPE
    SYNTAX INTEGER(0..255)
--  Units
--    mini-slots
    ACCESS read-write
    STATUS deprecated
    DESCRIPTION
        "The maximum number of mini-slots that may be requested
         for a single upstream transmission.
         A value of zero means there is no limit.
         MUST NOT be changed while this row is active.
         This object has been deprecated and replaced by
         docsIfQosProfMaxTransmitBurst, to fix a mismatch
         of the units and value range with respect to the DOCSIS
         Maximum Upstream Channel Transmit Burst Configuration
         Setting."
    REFERENCE
        "Data-Over-Cable Service Interface Specifications: Radio
         Frequency Interface Specification SP-RFIv2.0-I10-051209,
         C.1.1.4."
    DEFVAL { 0 }
    ::= { docsIfQosProfileEntry 6 }

docsIfQosProfBaselinePrivacy OBJECT-TYPE
    SYNTAX TruthValue
--    Rsyntax INTEGER {
--        true(1),
--        false(2)
--        }
    ACCESS read-write
    STATUS mandatory
    DESCRIPTION
        "Indicates whether Baseline Privacy is enabled for this
         service class.
         MUST NOT be changed while this row is active."
    DEFVAL { false }
    ::= { docsIfQosProfileEntry 7 }

docsIfQosProfStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This is object is used to create or delete rows in
         this table.  This object MUST NOT be changed from active
         while the row is referenced by any entry in either
         docsIfCmServiceTable (on the CM) or
         docsIfCmtsServiceTable (on the CMTS)."
    ::= { docsIfQosProfileEntry 8 }

docsIfQosProfMaxTransmitBurst OBJECT-TYPE
    SYNTAX INTEGER(0..65535)
--  Units
--    bytes
    ACCESS read-write
    STATUS mandatory
    DESCRIPTION
        "The maximum number of bytes that may be requested for a
         single upstream transmission.  A value of zero means there
         is no limit.  Note: This value does not include any
         physical layer overhead.
         MUST NOT be changed while this row is active."
    REFERENCE
        "Data-Over-Cable Service Interface Specifications: Radio
         Frequency Interface Specification SP-RFIv2.0-I10-051209,
         Annex C.1.1.4."
    DEFVAL { 0 }
    ::= { docsIfQosProfileEntry 9 }

docsIfQosProfStorageType OBJECT-TYPE
    SYNTAX StorageType
--    Rsyntax INTEGER {
--        other(1),
--        volatile(2),
--        nonVolatile(3),
--        permanent(4),
--        readOnly(5)
--        }
    ACCESS read-only
    STATUS mandatory
    DESCRIPTION
        "The storage type for this conceptual row.
         Entries with this object set to permanent(4)
         do not require write operations for writable
         objects."
    ::= { docsIfQosProfileEntry 10 }

docsIfSignalQualityTable OBJECT-TYPE
    SYNTAX SEQUENCE OF DocsIfSignalQualityEntry
    ACCESS not-accessible
    STATUS mandatory
    DESCRIPTION
        "At the CM, describes the PHY signal quality of downstream
         channels.  At the CMTS, this object describes the PHY
         signal quality of upstream channels.  At the CMTS, this
         table MAY exclude contention intervals."
    ::= { docsIfBaseObjects 4 }

docsIfSignalQualityEntry OBJECT-TYPE
    SYNTAX DocsIfSignalQualityEntry
    ACCESS not-accessible
    STATUS mandatory
    DESCRIPTION
        "At the CM, this object describes the PHY characteristics of
         a downstream channel.  At the CMTS, it describes the PHY
         signal quality of an upstream channel.
         An entry in this table exists for each ifEntry with an
         ifType of docsCableDownstream(128) for Cable Modems.
         For DOCSIS 1.1 Cable Modem Termination Systems, an entry
         exists for each ifEntry with an ifType of
         docsCableUpstream (129).
         For DOCSIS 2.0 Cable Modem Termination Systems, an entry
         exists for each ifEntry with an ifType of
         docsCableUpstreamChannel (205)."
    INDEX { ifIndex }
    ::= { docsIfSignalQualityTable 1 }

DocsIfSignalQualityEntry ::= SEQUENCE {
    docsIfSigQIncludesContention TruthValue,
    docsIfSigQUnerroreds Counter,
    docsIfSigQCorrecteds Counter,
    docsIfSigQUncorrectables Counter,
    docsIfSigQSignalNoise TenthdB,
    docsIfSigQMicroreflections INTEGER,
    docsIfSigQEqualizationData DocsEqualizerData,
    docsIfSigQExtUnerroreds Counter,
    docsIfSigQExtCorrecteds Counter,
    docsIfSigQExtUncorrectables Counter
    }

docsIfSigQIncludesContention OBJECT-TYPE
    SYNTAX TruthValue
--    Rsyntax INTEGER {
--        true(1),
--        false(2)
--        }
    ACCESS read-only
    STATUS mandatory
    DESCRIPTION
        "true(1) if this CMTS includes contention intervals in
         the counters in this table.  Always false(2) for CMs."
    REFERENCE
        "Data-Over-Cable Service Interface Specifications: Radio
         Frequency Interface Specification SP-RFIv2.0-I10-051209,
         Section 9.4.1"
    ::= { docsIfSignalQualityEntry 1 }

docsIfSigQUnerroreds OBJECT-TYPE
    SYNTAX Counter
--  Units
--    codewords
    ACCESS read-only
    STATUS mandatory
    DESCRIPTION
        "Codewords received on this channel without error.
         This includes all codewords, whether or not they
         were part of frames destined for this device.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Sections 6.2.4, and 6.3.6."
    ::= { docsIfSignalQualityEntry 2 }

docsIfSigQCorrecteds OBJECT-TYPE
    SYNTAX Counter
--  Units
--    codewords
    ACCESS read-only
    STATUS mandatory
    DESCRIPTION
        "Codewords received on this channel with correctable
         errors.  This includes all codewords, whether or not
         they were part of frames destined for this device.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Sections 6.2.4, and 6.3.6."
    ::= { docsIfSignalQualityEntry 3 }

docsIfSigQUncorrectables OBJECT-TYPE
    SYNTAX Counter
--  Units
--    codewords
    ACCESS read-only
    STATUS mandatory
    DESCRIPTION
        "Codewords received on this channel with uncorrectable
         errors.  This includes all codewords, whether or not
         they were part of frames destined for this device.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Sections 6.2.4, and 6.3.6."
    ::= { docsIfSignalQualityEntry 4 }

docsIfSigQSignalNoise OBJECT-TYPE
    SYNTAX TenthdB
--    Rsyntax INTEGER
--  Units
--    TenthdB
    ACCESS read-only
    STATUS mandatory
    DESCRIPTION
        "Signal/Noise ratio as perceived for this channel.
         At the CM, this object  describes the Signal/Noise of the
         downstream channel.  At the CMTS, it describes the
         average Signal/Noise of the upstream channel."
    REFERENCE
        "Data-Over-Cable Service Interface Specifications: Radio
         Frequency Interface Specification SP-RFIv2.0-I10-051209,
         Tables 4-1 and 4-2"
    ::= { docsIfSignalQualityEntry 5 }

docsIfSigQMicroreflections OBJECT-TYPE
    SYNTAX INTEGER(0..255)
--  Units
--    -dBc
    ACCESS read-only
    STATUS mandatory
    DESCRIPTION
        "Microreflections, including in-channel response
         as perceived on this interface, measured in dBc below
         the signal level.
         This object is not assumed to return an absolutely
         accurate value, but it gives a rough indication
         of microreflections received on this interface.
         It is up to the implementer to provide information
         as accurately as possible."
    REFERENCE
        "Data-Over-Cable Service Interface Specifications: Radio
         Frequency Interface Specification SP-RFIv2.0-I10-051209,
         Tables 4-1 and 4-2"
    ::= { docsIfSignalQualityEntry 6 }

docsIfSigQEqualizationData OBJECT-TYPE
    SYNTAX DocsEqualizerData
--    Rsyntax OCTET STRING(SIZE(0|36..260))
    ACCESS read-only
    STATUS mandatory
    DESCRIPTION
        "At the CM, this object returns the equalization data for
         the downstream channel.
        
         At the CMTS, this object is not applicable and is not
         instantiated.  Note that previous CMTS implementations
         may instantiate this object in two ways:
         - An equalization value indicating an equalization
           average for the upstream channel.  Those values have
           vendor-dependent interpretations.
         - Return a zero-length OCTET STRING to indicate that
           the value is unknown or if there is no equalization
           data available or defined."
    REFERENCE
        "DOCSIS Radio Frequency Interface Specification,
         Figure 6-23."
    ::= { docsIfSignalQualityEntry 7 }

docsIfSigQExtUnerroreds OBJECT-TYPE
    SYNTAX --?? syntax is not convertable to SMIv1
           Counter
--  Units
--    codewords
    ACCESS read-only
    STATUS mandatory
    DESCRIPTION
        "Codewords received on this channel without error.
         This includes all codewords, whether or not they
         were part of frames destined for this device.
         This is the 64-bit version of docsIfSigQUnerroreds.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Sections 6.2.4, and 6.3.6."
    ::= { docsIfSignalQualityEntry 8 }

docsIfSigQExtCorrecteds OBJECT-TYPE
    SYNTAX --?? syntax is not convertable to SMIv1
           Counter
--  Units
--    codewords
    ACCESS read-only
    STATUS mandatory
    DESCRIPTION
        "Codewords received on this channel with correctable
         errors.  This includes all codewords, whether or not
         they were part of frames destined for this device.
         This is the 64-bit version of docsIfSigQCorrecteds.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Sections 6.2.4, and 6.3.6."
    ::= { docsIfSignalQualityEntry 9 }

docsIfSigQExtUncorrectables OBJECT-TYPE
    SYNTAX --?? syntax is not convertable to SMIv1
           Counter
--  Units
--    codewords
    ACCESS read-only
    STATUS mandatory
    DESCRIPTION
        "Codewords received on this channel with uncorrectable
         errors.  This includes all codewords, whether or not
         they were part of frames destined for this device.
         This is the 64-bit version of docsIfSigQUncorrectables.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Sections 6.2.4, 6.3.6."
    ::= { docsIfSignalQualityEntry 10 }

docsIfDocsisBaseCapability OBJECT-TYPE
    SYNTAX DocsisVersion
--    Rsyntax INTEGER {
--        docsis10(1),
--        docsis11(2),
--        docsis20(3)
--        }
    ACCESS read-only
    STATUS mandatory
    DESCRIPTION
        "Indication of the DOCSIS capability of the device."
    REFERENCE
        "Data-Over-Cable Service Interface Specifications: Radio
         Frequency Interface Specification SP-RFIv2.0-I10-051209,
         Annex G."
    ::= { docsIfBaseObjects 5 }

docsIfCmMacTable OBJECT-TYPE
    SYNTAX SEQUENCE OF DocsIfCmMacEntry
    ACCESS not-accessible
    STATUS mandatory
    DESCRIPTION
        "Describes the attributes of each CM MAC interface,
         extending the information available from ifEntry."
    ::= { docsIfCmObjects 1 }

docsIfCmMacEntry OBJECT-TYPE
    SYNTAX DocsIfCmMacEntry
    ACCESS not-accessible
    STATUS mandatory
    DESCRIPTION
        "An entry containing objects describing attributes of
         each MAC entry, extending the information in ifEntry.
         An entry in this table exists for each ifEntry with an
         ifType of docsCableMaclayer(127)."
    INDEX { ifIndex }
    ::= { docsIfCmMacTable 1 }

DocsIfCmMacEntry ::= SEQUENCE {
    docsIfCmCmtsAddress MacAddress,
    docsIfCmCapabilities OCTET STRING,
    docsIfCmRangingRespTimeout TimeTicks,
    docsIfCmRangingTimeout TimeInterval
    }

docsIfCmCmtsAddress OBJECT-TYPE
    SYNTAX MacAddress
--    Rsyntax OCTET STRING(SIZE(6))
    ACCESS read-only
    STATUS mandatory
    DESCRIPTION
        "Identifies the CMTS that is believed to control this MAC
         domain.  At the CM, this will be the source address from
         SYNC, MAP, and other MAC-layer messages.  If the CMTS is
         unknown, returns 00-00-00-00-00-00."
    REFERENCE
        "Data-Over-Cable Service Interface Specifications: Radio
         Frequency Interface Specification SP-RFIv2.0-I10-051209,
         Section 8.2.2."
    ::= { docsIfCmMacEntry 1 }

docsIfCmCapabilities OBJECT-TYPE
    SYNTAX OCTET STRING(SIZE(1..2))
        -- BITS are:
        --   atmCells(0)
        --   concatenation(1)
    ACCESS read-only
    STATUS mandatory
    DESCRIPTION
        "Identifies the capabilities of the MAC implementation
         at this interface.  Note that packet transmission is
         always supported.  Therefore, there is no specific bit
         required to explicitly indicate this capability.
         Note that BITS objects are encoded most significant bit
         first.  For example, if bit 1 is set, the value of this
         object is the octet string '40'H."
    ::= { docsIfCmMacEntry 2 }

docsIfCmRangingRespTimeout OBJECT-TYPE
    SYNTAX TimeTicks
    ACCESS read-write
    STATUS obsolete
    DESCRIPTION
        "Waiting time for a Ranging Response packet.
         This object has been obsoleted and replaced by
         docsIfCmRangingTimeout to correct the typing to
         TimeInterval."
    REFERENCE
        "Data-Over-Cable Service Interface Specifications: Radio
         Frequency Interface Specification SP-RFIv2.0-I10-051209,
         Section 9.1.6."
    DEFVAL { 20 }
    ::= { docsIfCmMacEntry 3 }

docsIfCmRangingTimeout OBJECT-TYPE
    SYNTAX TimeInterval
--    Rsyntax INTEGER(0..2147483647)
--  Units
--    HundredOfSeconds
    ACCESS read-write
    STATUS mandatory
    DESCRIPTION
        "Waiting time for a Ranging Response packet.
         This object MUST NOT persist at reinitialization
         of the managed system."
    REFERENCE
        "Data-Over-Cable Service Interface Specifications: Radio
         Frequency Interface Specification SP-RFIv2.0-I10-051209,
         Section 9.1.6, timer T3."
    DEFVAL { 20 }
    ::= { docsIfCmMacEntry 4 }

docsIfCmStatusTable OBJECT-TYPE
    SYNTAX SEQUENCE OF DocsIfCmStatusEntry
    ACCESS not-accessible
    STATUS mandatory
    DESCRIPTION
        "This table maintains a number of status objects
         and counters for Cable Modems."
    ::= { docsIfCmObjects 2 }

docsIfCmStatusEntry OBJECT-TYPE
    SYNTAX DocsIfCmStatusEntry
    ACCESS not-accessible
    STATUS mandatory
    DESCRIPTION
        "A set of status objects and counters for a single MAC
         layer instance in Cable Modem.
         An entry in this table exists for each ifEntry with an
         ifType of docsCableMaclayer(127)."
    INDEX { ifIndex }
    ::= { docsIfCmStatusTable 1 }

DocsIfCmStatusEntry ::= SEQUENCE {
    docsIfCmStatusValue INTEGER,
    docsIfCmStatusCode OCTET STRING,
    docsIfCmStatusTxPower TenthdBmV,
    docsIfCmStatusResets Counter,
    docsIfCmStatusLostSyncs Counter,
    docsIfCmStatusInvalidMaps Counter,
    docsIfCmStatusInvalidUcds Counter,
    docsIfCmStatusInvalidRangingResponses Counter,
    docsIfCmStatusInvalidRegistrationResponses Counter,
    docsIfCmStatusT1Timeouts Counter,
    docsIfCmStatusT2Timeouts Counter,
    docsIfCmStatusT3Timeouts Counter,
    docsIfCmStatusT4Timeouts Counter,
    docsIfCmStatusRangingAborteds Counter,
    docsIfCmStatusDocsisOperMode DocsisQosVersion,
    docsIfCmStatusModulationType DocsisUpstreamType,
    docsIfCmStatusEqualizationData DocsEqualizerData,
    docsIfCmStatusUCCs Counter,
    docsIfCmStatusUCCFails Counter
    }

docsIfCmStatusValue OBJECT-TYPE
    SYNTAX INTEGER {
        other(1),
        notReady(2),
        notSynchronized(3),
        phySynchronized(4),
        usParametersAcquired(5),
        rangingComplete(6),
        ipComplete(7),
        todEstablished(8),
        securityEstablished(9),
        paramTransferComplete(10),
        registrationComplete(11),
        operational(12),
        accessDenied(13)
        }
    ACCESS read-only
    STATUS mandatory
    DESCRIPTION
        "Current Cable Modem connectivity state, as specified
         in the RF Interface Specification.  Interpretations for
         state values 1-12 are clearly outlined in the SP-RFI
         reference given below.
         The state value accessDenied(13) indicates the CMTS has
         sent a Registration Aborted message to the CM.  The same
         state is reported as accessDenied(7) by the CMTS object
         docsIfCmtsCmStatusValue."
    REFERENCE
        "Data-Over-Cable Service Interface Specifications: Radio
         Frequency Interface Specification SP-RFIv2.0-I10-051209,
         Section 11.2.
         Data-Over-Cable Service Interface Specifications:
         Operations Support System Interface Specification
         SP-OSSIv2.0-I09-050812, Section 6.3.4.2."
    ::= { docsIfCmStatusEntry 1 }

docsIfCmStatusCode OBJECT-TYPE
    SYNTAX OCTET STRING(SIZE(0|5|6))
    ACCESS read-only
    STATUS mandatory
    DESCRIPTION
        "Status code for a Cable Modem as defined in the
         OSSI Specification.  The status code consists
         of a single character indicating error groups, followed
         by a two- or three-digit number indicating the status
         condition, followed by a decimal.
         An example of a returned value could be 'T101.0'.
         The zero-length OCTET STRING indicates no status code yet
         registered."
    REFERENCE
        "Data-Over-Cable Service Interface Specifications:
         Operations Support System Interface Specification
         SP-OSSIv2.0-I09-050812, Annex D."
    ::= { docsIfCmStatusEntry 2 }

docsIfCmStatusTxPower OBJECT-TYPE
    SYNTAX TenthdBmV
--    Rsyntax INTEGER
--  Units
--    TenthdBmV
    ACCESS read-only
    STATUS mandatory
    DESCRIPTION
        "The operational transmit power for the attached upstream
         channel."
    REFERENCE
        "Data-Over-Cable Service Interface Specifications: Radio
         Frequency Interface Specification SP-RFIv2.0-I10-051209,
         Section 6.2.18."
    ::= { docsIfCmStatusEntry 3 }

docsIfCmStatusResets OBJECT-TYPE
    SYNTAX Counter
--  Units
--    resets
    ACCESS read-only
    STATUS mandatory
    DESCRIPTION
        "Number of times the CM reset or initialized this
         interface.
         Discontinuities in the value of this counter can occur
         at reinitialization of the managed system, and at other
         times as indicated by the value of
         ifCounterDiscontinuityTime for the associated ifIndex."
    ::= { docsIfCmStatusEntry 4 }

docsIfCmStatusLostSyncs OBJECT-TYPE
    SYNTAX Counter
    ACCESS read-only
    STATUS mandatory
    DESCRIPTION
        "Number of times the CM lost synchronization with
         the downstream channel.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Section 8.3.2."
    ::= { docsIfCmStatusEntry 5 }

docsIfCmStatusInvalidMaps OBJECT-TYPE
    SYNTAX Counter
--  Units
--    maps
    ACCESS read-only
    STATUS mandatory
    DESCRIPTION
        "Number of times the CM received invalid MAP messages.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Section 8.3.4."
    ::= { docsIfCmStatusEntry 6 }

docsIfCmStatusInvalidUcds OBJECT-TYPE
    SYNTAX Counter
--  Units
--    messages
    ACCESS read-only
    STATUS mandatory
    DESCRIPTION
        "Number of times the CM received invalid UCD messages.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Section 8.3.3."
    ::= { docsIfCmStatusEntry 7 }

docsIfCmStatusInvalidRangingResponses OBJECT-TYPE
    SYNTAX Counter
--  Units
--    messages
    ACCESS read-only
    STATUS mandatory
    DESCRIPTION
        "Number of times the CM received invalid ranging response
         messages.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Section 8.3.6."
    ::= { docsIfCmStatusEntry 8 }

docsIfCmStatusInvalidRegistrationResponses OBJECT-TYPE
    SYNTAX Counter
--  Units
--    messages
    ACCESS read-only
    STATUS mandatory
    DESCRIPTION
        "Number of times the CM received invalid registration
         response messages.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Section 8.3.8."
    ::= { docsIfCmStatusEntry 9 }

docsIfCmStatusT1Timeouts OBJECT-TYPE
    SYNTAX Counter
--  Units
--    timeouts
    ACCESS read-only
    STATUS mandatory
    DESCRIPTION
        "Number of times counter T1 expired in the CM.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Figure 9-2."
    ::= { docsIfCmStatusEntry 10 }

docsIfCmStatusT2Timeouts OBJECT-TYPE
    SYNTAX Counter
--  Units
--    timeouts
    ACCESS read-only
    STATUS mandatory
    DESCRIPTION
        "Number of times counter T2 expired in the CM.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Figure 9-2."
    ::= { docsIfCmStatusEntry 11 }

docsIfCmStatusT3Timeouts OBJECT-TYPE
    SYNTAX Counter
--  Units
--    timeouts
    ACCESS read-only
    STATUS mandatory
    DESCRIPTION
        "Number of times counter T3 expired in the CM.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Figure 9-2."
    ::= { docsIfCmStatusEntry 12 }

docsIfCmStatusT4Timeouts OBJECT-TYPE
    SYNTAX Counter
--  Units
--    timeouts
    ACCESS read-only
    STATUS mandatory
    DESCRIPTION
        "Number of times counter T4 expired in the CM.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Figure 9-2."
    ::= { docsIfCmStatusEntry 13 }

docsIfCmStatusRangingAborteds OBJECT-TYPE
    SYNTAX Counter
--  Units
--    attempts
    ACCESS read-only
    STATUS mandatory
    DESCRIPTION
        "Number of times the ranging process was aborted
         by the CMTS.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Section 9.3.3."
    ::= { docsIfCmStatusEntry 14 }

docsIfCmStatusDocsisOperMode OBJECT-TYPE
    SYNTAX DocsisQosVersion
--    Rsyntax INTEGER {
--        docsis10(1),
--        docsis11(2)
--        }
    ACCESS read-only
    STATUS mandatory
    DESCRIPTION
        "Indication of whether the device has registered using 1.0
         Class of Service or 1.1 Quality of Service.
         An unregistered CM SHOULD indicate 'docsis11' for a
         docsIfDocsisBaseCapability value of DOCSIS 1.1/2.0.  An
         unregistered CM SHOULD indicate 'docsis10'  for a
         docsIfDocsisBaseCapability value of DOCSIS 1.0."
    REFERENCE
        "Data-Over-Cable Service Interface Specifications: Radio
         Frequency Interface Specification SP-RFIv2.0-I10-051209,
         Annex G."
    ::= { docsIfCmStatusEntry 15 }

docsIfCmStatusModulationType OBJECT-TYPE
    SYNTAX DocsisUpstreamType
--    Rsyntax INTEGER {
--        ?? enum value of zero may cause problems
--        unknown(0),
--        tdma(1),
--        atdma(2),
--        scdma(3),
--        tdmaAndAtdma(4)
--        }
    ACCESS read-only
    STATUS mandatory
    DESCRIPTION
        "Indicates modulation type status currently used by the
         CM.  Since this object specifically identifies PHY mode,
         the shared upstream channel type is not permitted."
    REFERENCE
        "Data-Over-Cable Service Interface Specifications: Radio
         Frequency Interface Specification SP-RFIv2.0-I10-051209,
         Section 6.2.1."
    ::= { docsIfCmStatusEntry 16 }

docsIfCmStatusEqualizationData OBJECT-TYPE
    SYNTAX DocsEqualizerData
--    Rsyntax OCTET STRING(SIZE(0|36..260))
    ACCESS read-only
    STATUS mandatory
    DESCRIPTION
        "Pre-equalization data for this CM after convolution with
         data indicated in the RNG-RSP.  This data is valid when
         docsIfUpChannelPreEqEnable is set to true."
    REFERENCE
        "Data-Over-Cable Service Interface Specifications: Radio
         Frequency Interface Specification SP-RFIv2.0-I10-051209,
         Figure 8-23."
    ::= { docsIfCmStatusEntry 17 }

docsIfCmStatusUCCs OBJECT-TYPE
    SYNTAX Counter
--  Units
--    attempts
    ACCESS read-only
    STATUS mandatory
    DESCRIPTION
        "The number of successful Upstream Channel Change
         transactions.
         Discontinuities in the value of this counter can occur
         at reinitialization of the managed system, and at other
         times as indicated by the value of
         ifCounterDiscontinuityTime for the associated ifIndex."
    ::= { docsIfCmStatusEntry 18 }

docsIfCmStatusUCCFails OBJECT-TYPE
    SYNTAX Counter
--  Units
--    attempts
    ACCESS read-only
    STATUS mandatory
    DESCRIPTION
        "The number of failed Upstream Channel Change
         transactions.
         Discontinuities in the value of this counter can occur
         at reinitialization of the managed system, and at other
         times as indicated by the value of
         ifCounterDiscontinuityTime for the associated ifIndex."
    ::= { docsIfCmStatusEntry 19 }

docsIfCmServiceTable OBJECT-TYPE
    SYNTAX SEQUENCE OF DocsIfCmServiceEntry
    ACCESS not-accessible
    STATUS mandatory
    DESCRIPTION
        "Describes the attributes of each upstream service queue
         on a CM."
    ::= { docsIfCmObjects 3 }

docsIfCmServiceEntry OBJECT-TYPE
    SYNTAX DocsIfCmServiceEntry
    ACCESS not-accessible
    STATUS mandatory
    DESCRIPTION
        "Describes the attributes of an upstream bandwidth service
         queue.
         An entry in this table exists for each Service ID.
         The primary index is an ifIndex with an ifType of
         docsCableMaclayer(127)."
    INDEX { ifIndex, docsIfCmServiceId }
    ::= { docsIfCmServiceTable 1 }

DocsIfCmServiceEntry ::= SEQUENCE {
    docsIfCmServiceId INTEGER,
    docsIfCmServiceQosProfile INTEGER,
    docsIfCmServiceTxSlotsImmed Counter,
    docsIfCmServiceTxSlotsDed Counter,
    docsIfCmServiceTxRetries Counter,
    docsIfCmServiceTxExceededs Counter,
    docsIfCmServiceRqRetries Counter,
    docsIfCmServiceRqExceededs Counter,
    docsIfCmServiceExtTxSlotsImmed Counter,
    docsIfCmServiceExtTxSlotsDed Counter
    }

docsIfCmServiceId OBJECT-TYPE
    SYNTAX INTEGER(1..16383)
    ACCESS not-accessible
    STATUS mandatory
    DESCRIPTION
        "Identifies a service queue for upstream bandwidth.  The
         attributes of this service queue are shared between the
         CM and the CMTS.  The CMTS allocates upstream bandwidth
         to this service queue based on requests from the CM and
         on the class of service associated with this queue."
    ::= { docsIfCmServiceEntry 1 }

docsIfCmServiceQosProfile OBJECT-TYPE
    SYNTAX INTEGER(0..16383)
    ACCESS read-only
    STATUS mandatory
    DESCRIPTION
        "The index in docsIfQosProfileTable describing the quality
         of service attributes associated with this particular
         service.  If no associated entry in docsIfQosProfileTable
         exists, this object returns a value of zero."
    ::= { docsIfCmServiceEntry 2 }

docsIfCmServiceTxSlotsImmed OBJECT-TYPE
    SYNTAX Counter
--  Units
--    mini-slots
    ACCESS read-only
    STATUS mandatory
    DESCRIPTION
        "The number of upstream mini-slots that have been used to
         transmit data PDUs in immediate (contention) mode.  This
         includes only those PDUs that are presumed to have
         arrived at the head-end (i.e., those that were explicitly
         acknowledged).  It does not include retransmission attempts
         or mini-slots used by requests.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Section 9.4."
    ::= { docsIfCmServiceEntry 3 }

docsIfCmServiceTxSlotsDed OBJECT-TYPE
    SYNTAX Counter
--  Units
--    mini-slots
    ACCESS read-only
    STATUS mandatory
    DESCRIPTION
        "The number of upstream mini-slots that have been used to
         transmit data PDUs in dedicated mode (i.e., as a result
         of a unicast Data Grant).
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Section 9.4."
    ::= { docsIfCmServiceEntry 4 }

docsIfCmServiceTxRetries OBJECT-TYPE
    SYNTAX Counter
--  Units
--    attempts
    ACCESS read-only
    STATUS mandatory
    DESCRIPTION
        "The number of attempts to transmit data PDUs containing
         requests for acknowledgment that did not result in
         acknowledgment.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Section 9.4."
    ::= { docsIfCmServiceEntry 5 }

docsIfCmServiceTxExceededs OBJECT-TYPE
    SYNTAX Counter
--  Units
--    attempts
    ACCESS read-only
    STATUS mandatory
    DESCRIPTION
        "The number of data PDU transmission failures due to
         excessive retries without acknowledgment.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Section 9.4."
    ::= { docsIfCmServiceEntry 6 }

docsIfCmServiceRqRetries OBJECT-TYPE
    SYNTAX Counter
--  Units
--    attempts
    ACCESS read-only
    STATUS mandatory
    DESCRIPTION
        "The number of attempts to transmit bandwidth requests
         that did not result in acknowledgment.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Section 9.4."
    ::= { docsIfCmServiceEntry 7 }

docsIfCmServiceRqExceededs OBJECT-TYPE
    SYNTAX Counter
--  Units
--    attempts
    ACCESS read-only
    STATUS mandatory
    DESCRIPTION
        "The number of requests for bandwidth that failed due to
         excessive retries without acknowledgment.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Section 9.4."
    ::= { docsIfCmServiceEntry 8 }

docsIfCmServiceExtTxSlotsImmed OBJECT-TYPE
    SYNTAX --?? syntax is not convertable to SMIv1
           Counter
--  Units
--    mini-slots
    ACCESS read-only
    STATUS mandatory
    DESCRIPTION
        "The number of upstream mini-slots that have been used to
         transmit data PDUs in immediate (contention) mode.  This
         includes only those PDUs that are presumed to have
         arrived at the head-end (i.e., those that were explicitly
         acknowledged).  It does not include retransmission attempts
         or mini-slots used by requests.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Section 9.4."
    ::= { docsIfCmServiceEntry 9 }

docsIfCmServiceExtTxSlotsDed OBJECT-TYPE
    SYNTAX --?? syntax is not convertable to SMIv1
           Counter
--  Units
--    mini-slots
    ACCESS read-only
    STATUS mandatory
    DESCRIPTION
        "The number of upstream mini-slots that have been used to
         transmit data PDUs in dedicated mode (i.e., as a result
         of a unicast Data Grant).
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Section 9.4."
    ::= { docsIfCmServiceEntry 10 }

docsIfCmtsMacTable OBJECT-TYPE
    SYNTAX SEQUENCE OF DocsIfCmtsMacEntry
    ACCESS not-accessible
    STATUS mandatory
    DESCRIPTION
        "Describes the attributes of each CMTS MAC interface,
         extending the information available from ifEntry.
         Mandatory for all CMTS devices."
    ::= { docsIfCmtsObjects 1 }

docsIfCmtsMacEntry OBJECT-TYPE
    SYNTAX DocsIfCmtsMacEntry
    ACCESS not-accessible
    STATUS mandatory
    DESCRIPTION
        "An entry containing objects describing attributes of each
         MAC entry, extending the information in ifEntry.
         An entry in this table exists for each ifEntry with an
         ifType of docsCableMaclayer(127)."
    INDEX { ifIndex }
    ::= { docsIfCmtsMacTable 1 }

DocsIfCmtsMacEntry ::= SEQUENCE {
    docsIfCmtsCapabilities OCTET STRING,
    docsIfCmtsSyncInterval INTEGER,
    docsIfCmtsUcdInterval INTEGER,
    docsIfCmtsMaxServiceIds INTEGER,
    docsIfCmtsInsertionInterval TimeTicks,
    docsIfCmtsInvitedRangingAttempts INTEGER,
    docsIfCmtsInsertInterval TimeInterval,
    docsIfCmtsMacStorageType StorageType
    }

docsIfCmtsCapabilities OBJECT-TYPE
    SYNTAX OCTET STRING(SIZE(1..2))
        -- BITS are:
        --   atmCells(0)
        --   concatenation(1)
    ACCESS read-only
    STATUS mandatory
    DESCRIPTION
        "Identifies the capabilities of the CMTS MAC
         implementation at this interface.  Note that packet
         transmission is always supported.  Therefore, there
         is no specific bit required to explicitly indicate
         this capability.
         Note that BITS objects are encoded most significant bit
         first.  For example, if bit 1 is set, the value of this
         object is the octet string '40'H."
    ::= { docsIfCmtsMacEntry 1 }

docsIfCmtsSyncInterval OBJECT-TYPE
    SYNTAX INTEGER(1..200)
--  Units
--    Milliseconds
    ACCESS read-write
    STATUS mandatory
    DESCRIPTION
        "The interval between CMTS transmission of successive SYNC
         messages at this interface."
    REFERENCE
        "Data-Over-Cable Service Interface Specifications: Radio
         Frequency Interface Specification SP-RFIv2.0-I10-051209,
         Section 9.3."
    ::= { docsIfCmtsMacEntry 2 }

docsIfCmtsUcdInterval OBJECT-TYPE
    SYNTAX INTEGER(1..2000)
--  Units
--    Milliseconds
    ACCESS read-write
    STATUS mandatory
    DESCRIPTION
        "The interval between CMTS transmission of successive
         Upstream Channel Descriptor messages for each upstream
         channel at this interface."
    REFERENCE
        "Data-Over-Cable Service Interface Specifications: Radio
         Frequency Interface Specification SP-RFIv2.0-I10-051209,
         Section 9.3"
    ::= { docsIfCmtsMacEntry 3 }

docsIfCmtsMaxServiceIds OBJECT-TYPE
    SYNTAX INTEGER(1..16383)
--  Units
--    SIDs
    ACCESS read-only
    STATUS mandatory
    DESCRIPTION
        "The maximum number of service IDs that may be
         simultaneously active."
    ::= { docsIfCmtsMacEntry 4 }

docsIfCmtsInsertionInterval OBJECT-TYPE
    SYNTAX TimeTicks
    ACCESS read-write
    STATUS obsolete
    DESCRIPTION
        "The amount of time to elapse between each broadcast
         initial maintenance grant.  Broadcast initial maintenance
         grants are used to allow new cable modems to join the
         network.  Zero indicates that a vendor-specific algorithm
         is used instead of a fixed time.  The maximum amount of
         time permitted by the specification is 2 seconds.
         This object has been obsoleted and replaced by
         docsIfCmtsInsertInterval to fix a SYNTAX typing problem."
    REFERENCE
        "Data-Over-Cable Service Interface Specifications: Radio
         Frequency Interface Specification SP-RFIv2.0-I10-051209,
         Annex B."
    ::= { docsIfCmtsMacEntry 5 }

docsIfCmtsInvitedRangingAttempts OBJECT-TYPE
    SYNTAX INTEGER(0..1024)
--  Units
--    attempts
    ACCESS read-write
    STATUS mandatory
    DESCRIPTION
        "The maximum number of attempts to make on invitations
         for ranging requests.  A value of zero means the system
         SHOULD attempt to range forever."
    REFERENCE
        "Data-Over-Cable Service Interface Specifications: Radio
         Frequency Interface Specification SP-RFIv2.0-I10-051209,
         Section 9.3.3 and Annex B."
    ::= { docsIfCmtsMacEntry 6 }

docsIfCmtsInsertInterval OBJECT-TYPE
    SYNTAX TimeInterval
--    Rsyntax INTEGER(0..2147483647)
--  Units
--    HundredOfSeconds
    ACCESS read-write
    STATUS mandatory
    DESCRIPTION
        "The amount of time to elapse between each broadcast
         initial maintenance grant.  Broadcast initial maintenance
         grants are used to allow new cable modems to join the
         network.  Zero indicates that a vendor-specific algorithm
         is used instead of a fixed time.  The maximum amount of
         time permitted by the specification is 2 seconds."
    REFERENCE
        "Data-Over-Cable Service Interface Specifications: Radio
         Frequency Interface Specification SP-RFIv2.0-I10-051209,
         Annex B."
    ::= { docsIfCmtsMacEntry 7 }

docsIfCmtsMacStorageType OBJECT-TYPE
    SYNTAX StorageType
--    Rsyntax INTEGER {
--        other(1),
--        volatile(2),
--        nonVolatile(3),
--        permanent(4),
--        readOnly(5)
--        }
    ACCESS read-only
    STATUS mandatory
    DESCRIPTION
        "The storage type for this conceptual row.
         Entries with this object set to permanent(4)
         do not require write operations for read-write
         objects."
    ::= { docsIfCmtsMacEntry 8 }

docsIfCmtsStatusTable OBJECT-TYPE
    SYNTAX SEQUENCE OF DocsIfCmtsStatusEntry
    ACCESS not-accessible
    STATUS mandatory
    DESCRIPTION
        "For the MAC layer, this group maintains a number of
         status objects and counters."
    ::= { docsIfCmtsObjects 2 }

docsIfCmtsStatusEntry OBJECT-TYPE
    SYNTAX DocsIfCmtsStatusEntry
    ACCESS not-accessible
    STATUS mandatory
    DESCRIPTION
        "Status entry for a single MAC layer.
          An entry in this table exists for each ifEntry with an
          ifType of docsCableMaclayer(127)."
    INDEX { ifIndex }
    ::= { docsIfCmtsStatusTable 1 }

DocsIfCmtsStatusEntry ::= SEQUENCE {
    docsIfCmtsStatusInvalidRangeReqs Counter,
    docsIfCmtsStatusRangingAborteds Counter,
    docsIfCmtsStatusInvalidRegReqs Counter,
    docsIfCmtsStatusFailedRegReqs Counter,
    docsIfCmtsStatusInvalidDataReqs Counter,
    docsIfCmtsStatusT5Timeouts Counter
    }

docsIfCmtsStatusInvalidRangeReqs OBJECT-TYPE
    SYNTAX Counter
--  Units
--    messages
    ACCESS read-only
    STATUS mandatory
    DESCRIPTION
        "This object counts invalid RNG-REQ messages received on
         this interface.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Section 8.3.5."
    ::= { docsIfCmtsStatusEntry 1 }

docsIfCmtsStatusRangingAborteds OBJECT-TYPE
    SYNTAX Counter
--  Units
--    attempts
    ACCESS read-only
    STATUS mandatory
    DESCRIPTION
        "This object counts ranging attempts that were explicitly
         aborted by the CMTS.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Section 8.3.6."
    ::= { docsIfCmtsStatusEntry 2 }

docsIfCmtsStatusInvalidRegReqs OBJECT-TYPE
    SYNTAX Counter
--  Units
--    messages
    ACCESS read-only
    STATUS mandatory
    DESCRIPTION
        "This object counts invalid REG-REQ messages received on
         this interface; that is, syntax, out of range parameters,
         or erroneous requests.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Section 8.3.7."
    ::= { docsIfCmtsStatusEntry 3 }

docsIfCmtsStatusFailedRegReqs OBJECT-TYPE
    SYNTAX Counter
--  Units
--    attempts
    ACCESS read-only
    STATUS mandatory
    DESCRIPTION
        "This object counts failed registration attempts.  Included
         are docsIfCmtsStatusInvalidRegReqs, authentication, and
         class of service failures.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Section 8.3.7."
    ::= { docsIfCmtsStatusEntry 4 }

docsIfCmtsStatusInvalidDataReqs OBJECT-TYPE
    SYNTAX Counter
--  Units
--    messages
    ACCESS read-only
    STATUS mandatory
    DESCRIPTION
        "This object counts invalid data request messages
         received on this interface.
         Discontinuities in the value of this counter can occur
         at reinitialization of the managed system, and at other
         times as indicated by the value of
         ifCounterDiscontinuityTime for the associated ifIndex."
    ::= { docsIfCmtsStatusEntry 5 }

docsIfCmtsStatusT5Timeouts OBJECT-TYPE
    SYNTAX Counter
--  Units
--    timeouts
    ACCESS read-only
    STATUS mandatory
    DESCRIPTION
        "This object counts the number of times counter T5
         expired on this interface.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Figure 9-2."
    ::= { docsIfCmtsStatusEntry 6 }

docsIfCmtsCmStatusTable OBJECT-TYPE
    SYNTAX SEQUENCE OF DocsIfCmtsCmStatusEntry
    ACCESS not-accessible
    STATUS mandatory
    DESCRIPTION
        "A set of objects in the CMTS, maintained for each
         cable modem connected to this CMTS."
    ::= { docsIfCmtsObjects 3 }

docsIfCmtsCmStatusEntry OBJECT-TYPE
    SYNTAX DocsIfCmtsCmStatusEntry
    ACCESS not-accessible
    STATUS mandatory
    DESCRIPTION
        "Status information for a single cable modem.
         An entry in this table exists for each cable modem
         that is connected to the CMTS implementing this table."
    INDEX { docsIfCmtsCmStatusIndex }
    ::= { docsIfCmtsCmStatusTable 1 }

DocsIfCmtsCmStatusEntry ::= SEQUENCE {
    docsIfCmtsCmStatusIndex INTEGER,
    docsIfCmtsCmStatusMacAddress MacAddress,
    docsIfCmtsCmStatusIpAddress IpAddress,
    docsIfCmtsCmStatusDownChannelIfIndex InterfaceIndexOrZero,
    docsIfCmtsCmStatusUpChannelIfIndex InterfaceIndexOrZero,
    docsIfCmtsCmStatusRxPower TenthdBmV,
    docsIfCmtsCmStatusTimingOffset Gauge,
    docsIfCmtsCmStatusEqualizationData DocsEqualizerData,
    docsIfCmtsCmStatusValue INTEGER,
    docsIfCmtsCmStatusUnerroreds Counter,
    docsIfCmtsCmStatusCorrecteds Counter,
    docsIfCmtsCmStatusUncorrectables Counter,
    docsIfCmtsCmStatusSignalNoise TenthdB,
    docsIfCmtsCmStatusMicroreflections INTEGER,
    docsIfCmtsCmStatusExtUnerroreds Counter,
    docsIfCmtsCmStatusExtCorrecteds Counter,
    docsIfCmtsCmStatusExtUncorrectables Counter,
    docsIfCmtsCmStatusDocsisRegMode DocsisQosVersion,
    docsIfCmtsCmStatusModulationType DocsisUpstreamType,
    docsIfCmtsCmStatusInetAddressType InetAddressType,
    docsIfCmtsCmStatusInetAddress InetAddress,
    docsIfCmtsCmStatusValueLastUpdate TimeStamp,
    docsIfCmtsCmStatusHighResolutionTimingOffset Gauge
    }

docsIfCmtsCmStatusIndex OBJECT-TYPE
    SYNTAX INTEGER(1..2147483647)
    ACCESS not-accessible
    STATUS mandatory
    DESCRIPTION
        "Index value to uniquely identify an entry in this table.
         For an individual cable modem, this index value SHOULD
         NOT change during CMTS uptime."
    ::= { docsIfCmtsCmStatusEntry 1 }

docsIfCmtsCmStatusMacAddress OBJECT-TYPE
    SYNTAX MacAddress
--    Rsyntax OCTET STRING(SIZE(6))
    ACCESS read-only
    STATUS mandatory
    DESCRIPTION
        "MAC address of the cable modem.  If the cable modem has
         multiple MAC addresses, this is the MAC address associated
         with the Cable interface."
    REFERENCE
        "Data-Over-Cable Service Interface Specifications: Radio
         Frequency Interface Specification SP-RFIv2.0-I10-051209,
         Section 8.2.2."
    ::= { docsIfCmtsCmStatusEntry 2 }

docsIfCmtsCmStatusIpAddress OBJECT-TYPE
    SYNTAX IpAddress
    ACCESS read-only
    STATUS deprecated
    DESCRIPTION
        "IP address of this cable modem.  If the cable modem has no
         IP address assigned, or the IP address is unknown, this
         object returns a value of 0.0.0.0.  If the cable modem has
         multiple IP addresses, this object returns the IP address
         associated with the Cable interface.
         This object has been deprecated and replaced by
         docsIfCmtsCmStatusInetAddressType and
         docsIfCmtsCmStatusInetAddress, to enable IPv6 addressing
         in the future."
    ::= { docsIfCmtsCmStatusEntry 3 }

docsIfCmtsCmStatusDownChannelIfIndex OBJECT-TYPE
    SYNTAX InterfaceIndexOrZero
--    Rsyntax INTEGER(0..2147483647)
    ACCESS read-only
    STATUS mandatory
    DESCRIPTION
        "IfIndex of the downstream channel that this CM is
         connected to.  If the downstream channel is unknown, this
         object returns a value of zero."
    ::= { docsIfCmtsCmStatusEntry 4 }

docsIfCmtsCmStatusUpChannelIfIndex OBJECT-TYPE
    SYNTAX InterfaceIndexOrZero
--    Rsyntax INTEGER(0..2147483647)
    ACCESS read-only
    STATUS mandatory
    DESCRIPTION
        "For DOCSIS 2.0, indicates the ifIndex of the logical
         upstream channel (ifType 205) this CM is connected to.
         For DOCSIS 1.x, indicates the ifIndex of the upstream
          channel (ifType 129) this CM is connected to.
          If the upstream channel is unknown, this object
          returns a value of zero."
    ::= { docsIfCmtsCmStatusEntry 5 }

docsIfCmtsCmStatusRxPower OBJECT-TYPE
    SYNTAX TenthdBmV
--    Rsyntax INTEGER
--  Units
--    ThenthdBmV
    ACCESS read-only
    STATUS mandatory
    DESCRIPTION
        "The receive power as perceived for upstream data from
         this cable modem.
         If the receive power is unknown, this object returns
         a value of zero."
    REFERENCE
        "Data-Over-Cable Service Interface Specifications: Radio
         Frequency Interface Specification SP-RFIv2.0-I10-051209,
         Section 6.2.18."
    ::= { docsIfCmtsCmStatusEntry 6 }

docsIfCmtsCmStatusTimingOffset OBJECT-TYPE
    SYNTAX Gauge(0..4294967295)
    ACCESS read-only
    STATUS mandatory
    DESCRIPTION
        "A measure of the current round trip time for this CM.
         Used for timing of CM upstream transmissions to ensure
         synchronized arrivals at the CMTS.  Units are in terms
         of (6.25 microseconds/64).  Returns zero if the value
         is unknown.
         For channels requiring finer resolution, please refer to
         object docsIfCmtsCmStatusHighResolutionTimingOffset."
    REFERENCE
        "Data-Over-Cable Service Interface Specifications: Radio
         Frequency Interface Specification SP-RFIv2.0-I10-051209,
         Section 6.2.17."
    ::= { docsIfCmtsCmStatusEntry 7 }

docsIfCmtsCmStatusEqualizationData OBJECT-TYPE
    SYNTAX DocsEqualizerData
--    Rsyntax OCTET STRING(SIZE(0|36..260))
    ACCESS read-only
    STATUS mandatory
    DESCRIPTION
        "Equalization data for this CM, as measured by the CMTS.
         Returns the zero-length OCTET STRING if the value is
         unknown or if there is no equalization data available
         or defined."
    REFERENCE
        "Data-Over-Cable Service Interface Specifications: Radio
         Frequency Interface Specification SP-RFIv2.0-I10-051209,
         Figure 8-23."
    ::= { docsIfCmtsCmStatusEntry 8 }

docsIfCmtsCmStatusValue OBJECT-TYPE
    SYNTAX INTEGER {
        other(1),
        ranging(2),
        rangingAborted(3),
        rangingComplete(4),
        ipComplete(5),
        registrationComplete(6),
        accessDenied(7),
        operational(8),
        registeredBPIInitializing(9)
        }
    ACCESS read-only
    STATUS mandatory
    DESCRIPTION
        "Current cable modem connectivity state, as specified
         in the RF Interface Specification.  Returned status
         information is the CM status, as assumed by the CMTS,
         and indicates the following events:
         other(1)
            Any state other than below.
         ranging(2)
            The CMTS has received an Initial Ranging Request
            message from the CM, and the ranging process is not
            yet complete.
         rangingAborted(3)
            The CMTS has sent a Ranging Abort message to the CM.
         rangingComplete(4)
            The CMTS has sent a Ranging Complete message to the CM.
         ipComplete(5)
            The CMTS has received a DHCP reply message and
            forwarded it to the CM.
         registrationComplete(6)
            The CMTS has sent a Registration Response message to
            the CM.
         accessDenied(7)
            The CMTS has sent a Registration Aborted message
            to the CM.
         operational(8)
            Value 8 is considered reserved and should not be defined
            in future revisions of this MIB module to avoid conflict
            with documented implementations that support value 8 to
            indicate operational state after completing the BPI
            initialization process.
         registeredBPIInitializing(9)
            Baseline Privacy (BPI) is enabled and the CMTS is in the
            process of completing BPI initialization.  This state
            MAY last for a significant length of time if failures
            occur during the initialization process.  After
            completion of BPI initialization, the CMTS will report
            registrationComplete(6).
         The CMTS only needs to report states it is able to
         detect."
    REFERENCE
        "Data-Over-Cable Service Interface Specifications: Radio
         Frequency Interface Specification SP-RFIv2.0-I10-051209,
         Section 11.2."
    ::= { docsIfCmtsCmStatusEntry 9 }

docsIfCmtsCmStatusUnerroreds OBJECT-TYPE
    SYNTAX Counter
--  Units
--    codewords
    ACCESS read-only
    STATUS mandatory
    DESCRIPTION
        "Codewords received without error from this cable modem.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Section 6.2.4."
    ::= { docsIfCmtsCmStatusEntry 10 }

docsIfCmtsCmStatusCorrecteds OBJECT-TYPE
    SYNTAX Counter
--  Units
--    codewords
    ACCESS read-only
    STATUS mandatory
    DESCRIPTION
        "Codewords received with correctable errors from this
         cable modem.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Section 6.2.4."
    ::= { docsIfCmtsCmStatusEntry 11 }

docsIfCmtsCmStatusUncorrectables OBJECT-TYPE
    SYNTAX Counter
--  Units
--    codewords
    ACCESS read-only
    STATUS mandatory
    DESCRIPTION
        "Codewords received with uncorrectable errors from this
         cable modem.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Section 6.2.4."
    ::= { docsIfCmtsCmStatusEntry 12 }

docsIfCmtsCmStatusSignalNoise OBJECT-TYPE
    SYNTAX TenthdB
--    Rsyntax INTEGER
--  Units
--    TenthdB
    ACCESS read-only
    STATUS mandatory
    DESCRIPTION
        "Signal/Noise ratio as perceived for upstream data from
         this cable modem.
         If the Signal/Noise is unknown, this object returns
         a value of zero."
    REFERENCE
        "Data-Over-Cable Service Interface Specifications: Radio
         Frequency Interface Specification SP-RFIv2.0-I10-051209,
         Tables 4-1 and 4-2."
    ::= { docsIfCmtsCmStatusEntry 13 }

docsIfCmtsCmStatusMicroreflections OBJECT-TYPE
    SYNTAX INTEGER(0..255)
--  Units
--    -dBc
    ACCESS read-only
    STATUS mandatory
    DESCRIPTION
        "Total microreflections, including in-channel response
         as perceived on this interface, measured in dBc below
         the signal level.
         This object is not assumed to return an absolutely
         accurate value, but it gives a rough indication
         of microreflections received on this interface.
         It is up to the implementer to provide information
         as accurately as possible.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Tables 4-1 and 4-2"
    ::= { docsIfCmtsCmStatusEntry 14 }

docsIfCmtsCmStatusExtUnerroreds OBJECT-TYPE
    SYNTAX --?? syntax is not convertable to SMIv1
           Counter
--  Units
--    codewords
    ACCESS read-only
    STATUS mandatory
    DESCRIPTION
        "Codewords received without error from this cable modem.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Section 6.2.5."
    ::= { docsIfCmtsCmStatusEntry 15 }

docsIfCmtsCmStatusExtCorrecteds OBJECT-TYPE
    SYNTAX --?? syntax is not convertable to SMIv1
           Counter
--  Units
--    codewords
    ACCESS read-only
    STATUS mandatory
    DESCRIPTION
        "Codewords received with correctable errors from this
         cable modem.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Section 6.2.5."
    ::= { docsIfCmtsCmStatusEntry 16 }

docsIfCmtsCmStatusExtUncorrectables OBJECT-TYPE
    SYNTAX --?? syntax is not convertable to SMIv1
           Counter
--  Units
--    codewords
    ACCESS read-only
    STATUS mandatory
    DESCRIPTION
        "Codewords received with uncorrectable errors from this
         cable modem.
         Discontinuities in the value of this counter can occur
         at reinitialization of the managed system, and at other
         times as indicated by the value of
         ifCounterDiscontinuityTime for the associated ifIndex."
    REFERENCE
        "Data-Over-Cable Service Interface Specifications: Radio
         Frequency Interface Specification SP-RFIv2.0-I10-051209,
         Section 6.2.5."
    ::= { docsIfCmtsCmStatusEntry 17 }

docsIfCmtsCmStatusDocsisRegMode OBJECT-TYPE
    SYNTAX DocsisQosVersion
--    Rsyntax INTEGER {
--        docsis10(1),
--        docsis11(2)
--        }
    ACCESS read-only
    STATUS mandatory
    DESCRIPTION
        "Indication of whether the CM has registered using 1.0
         Class of Service or 1.1 Quality of Service."
    REFERENCE
        "Data-Over-Cable Service Interface Specifications: Radio
         Frequency Interface Specification SP-RFIv2.0-I10-051209,
         Annex G."
    ::= { docsIfCmtsCmStatusEntry 18 }

docsIfCmtsCmStatusModulationType OBJECT-TYPE
    SYNTAX DocsisUpstreamType
--    Rsyntax INTEGER {
--        ?? enum value of zero may cause problems
--        unknown(0),
--        tdma(1),
--        atdma(2),
--        scdma(3),
--        tdmaAndAtdma(4)
--        }
    ACCESS read-only
    STATUS mandatory
    DESCRIPTION
        "Indicates modulation type currently used by the CM.  Since
         this object specifically identifies PHY mode, the shared
         type is not permitted.  If the upstream channel is
         unknown, this object returns a value of zero."
    REFERENCE
        "Data-Over-Cable Service Interface Specifications: Radio
         Frequency Interface Specification SP-RFIv2.0-I10-051209,
         Table 8-19."
    ::= { docsIfCmtsCmStatusEntry 19 }

docsIfCmtsCmStatusInetAddressType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-only
    STATUS mandatory
    DESCRIPTION
        "The type of internet address of
         docsIfCmtsCmStatusInetAddress.  If the cable modem
         internet address is unassigned or unknown, then the
         value of this object is unknown(0)."
    ::= { docsIfCmtsCmStatusEntry 20 }

docsIfCmtsCmStatusInetAddress OBJECT-TYPE
    SYNTAX InetAddress
--    Rsyntax OCTET STRING(SIZE(0..255))
    ACCESS read-only
    STATUS mandatory
    DESCRIPTION
        "Internet address of this cable modem.  If the Cable
         Modem has no Internet address assigned, or the Internet
         address is unknown, the value of this object is the
         zero-length OCTET STRING.  If the cable modem has
         multiple Internet addresses, this object returns the
         Internet address associated with the Cable
         (i.e., RF MAC) interface."
    ::= { docsIfCmtsCmStatusEntry 21 }

docsIfCmtsCmStatusValueLastUpdate OBJECT-TYPE
    SYNTAX TimeStamp
--    Rsyntax TimeTicks
    ACCESS read-only
    STATUS mandatory
    DESCRIPTION
        "The value of sysUpTime when docsIfCmtsCmStatusValue
         was last updated."
    ::= { docsIfCmtsCmStatusEntry 22 }

docsIfCmtsCmStatusHighResolutionTimingOffset OBJECT-TYPE
    SYNTAX Gauge(0..4294967295)
    ACCESS read-only
    STATUS mandatory
    DESCRIPTION
        "A measure of the current round trip time for this CM.
         Used for timing of CM upstream transmissions to ensure
         synchronized arrivals at the CMTS.  Units are in terms
         of (6.25 microseconds/(64*256)).  Returns zero if the value
         is unknown.
         This is the high resolution version of object
         docsIfCmtsCmStatusTimingOffset, for channels requiring
         finer resolution."
    REFERENCE
        "Data-Over-Cable Service Interface Specifications: Radio
         Frequency Interface Specification SP-RFIv2.0-I10-051209,
         Section 6.2.17."
    ::= { docsIfCmtsCmStatusEntry 23 }

docsIfCmtsServiceTable OBJECT-TYPE
    SYNTAX SEQUENCE OF DocsIfCmtsServiceEntry
    ACCESS not-accessible
    STATUS mandatory
    DESCRIPTION
        "Describes the attributes of upstream service queues
         in a Cable Modem Termination System."
    ::= { docsIfCmtsObjects 4 }

docsIfCmtsServiceEntry OBJECT-TYPE
    SYNTAX DocsIfCmtsServiceEntry
    ACCESS not-accessible
    STATUS mandatory
    DESCRIPTION
        "Describes the attributes of a single upstream bandwidth
         service queue.
         Entries in this table exist for each ifEntry with an
         ifType of docsCableMaclayer(127), and for each service
         queue (Service ID) within this MAC layer.
         Entries in this table are created with the creation of
         individual Service IDs by the MAC layer and removed
         when a Service ID is removed."
    INDEX { ifIndex, docsIfCmtsServiceId }
    ::= { docsIfCmtsServiceTable 1 }

DocsIfCmtsServiceEntry ::= SEQUENCE {
    docsIfCmtsServiceId INTEGER,
    docsIfCmtsServiceCmStatusIndex INTEGER,
    docsIfCmtsServiceAdminStatus INTEGER,
    docsIfCmtsServiceQosProfile INTEGER,
    docsIfCmtsServiceCreateTime TimeStamp,
    docsIfCmtsServiceInOctets Counter,
    docsIfCmtsServiceInPackets Counter,
    docsIfCmtsServiceNewCmStatusIndex INTEGER
    }

docsIfCmtsServiceId OBJECT-TYPE
    SYNTAX INTEGER(1..16383)
    ACCESS not-accessible
    STATUS mandatory
    DESCRIPTION
        "Identifies a service queue for upstream bandwidth.  The
         attributes of this service queue are shared between the
         Cable Modem and the Cable Modem Termination System.
         The CMTS allocates upstream bandwidth to this service
         queue based on requests from the CM and on the class of
         service associated with this queue."
    ::= { docsIfCmtsServiceEntry 1 }

docsIfCmtsServiceCmStatusIndex OBJECT-TYPE
    SYNTAX INTEGER(0..65535)
    ACCESS read-only
    STATUS deprecated
    DESCRIPTION
        "Pointer to an entry in docsIfCmtsCmStatusTable identifying
         the cable modem using this Service Queue.  If multiple
         cable modems are using this Service Queue, the value of
         this object is zero.
         This object has been deprecated and replaced by
         docsIfCmtsServiceNewCmStatusIndex, to fix a mismatch
         of the value range with respect to docsIfCmtsCmStatusIndex
         (1..2147483647)."
    ::= { docsIfCmtsServiceEntry 2 }

docsIfCmtsServiceAdminStatus OBJECT-TYPE
    SYNTAX INTEGER {
        enabled(1),
        disabled(2),
        destroyed(3)
        }
    ACCESS read-write
    STATUS mandatory
    DESCRIPTION
        "Allows a service class for a particular modem to be
         suppressed, (re-)enabled, or deleted altogether."
    ::= { docsIfCmtsServiceEntry 3 }

docsIfCmtsServiceQosProfile OBJECT-TYPE
    SYNTAX INTEGER(0..16383)
    ACCESS read-only
    STATUS mandatory
    DESCRIPTION
        "The index in docsIfQosProfileTable describing the quality
         of service attributes associated with this particular
         service.  If no associated docsIfQosProfileTable entry
         exists, this object returns a value of zero."
    ::= { docsIfCmtsServiceEntry 4 }

docsIfCmtsServiceCreateTime OBJECT-TYPE
    SYNTAX TimeStamp
--    Rsyntax TimeTicks
    ACCESS read-only
    STATUS mandatory
    DESCRIPTION
        "The value of sysUpTime when this entry was created."
    ::= { docsIfCmtsServiceEntry 5 }

docsIfCmtsServiceInOctets OBJECT-TYPE
    SYNTAX Counter
--  Units
--    Bytes
    ACCESS read-only
    STATUS mandatory
    DESCRIPTION
        "The cumulative number of Packet Data octets received
         on this Service ID.  The count does not include the
         size of the Cable MAC header.
         Discontinuities in the value of this counter can occur
         at reinitialization of the managed system, and at other
         times as indicated by the value of
         ifCounterDiscontinuityTime for the associated ifIndex."
    ::= { docsIfCmtsServiceEntry 6 }

docsIfCmtsServiceInPackets OBJECT-TYPE
    SYNTAX Counter
--  Units
--    packets
    ACCESS read-only
    STATUS mandatory
    DESCRIPTION
        "The cumulative number of Packet Data packets received
         on this Service ID.
         Discontinuities in the value of this counter can occur
         at reinitialization of the managed system, and at other
         times as indicated by the value of
         ifCounterDiscontinuityTime for the associated ifIndex."
    ::= { docsIfCmtsServiceEntry 7 }

docsIfCmtsServiceNewCmStatusIndex OBJECT-TYPE
    SYNTAX INTEGER(0..2147483647)
    ACCESS read-only
    STATUS mandatory
    DESCRIPTION
        "Pointer (via docsIfCmtsCmStatusIndex) to an entry in
         docsIfCmtsCmStatusTable identifying the cable modem
         using this Service Queue.  If multiple cable modems are
         using this Service Queue, the value of this object is
         zero."
    ::= { docsIfCmtsServiceEntry 8 }

docsIfCmtsModulationTable OBJECT-TYPE
    SYNTAX SEQUENCE OF DocsIfCmtsModulationEntry
    ACCESS not-accessible
    STATUS mandatory
    DESCRIPTION
        "Describes a modulation profile associated with one or more
         upstream channels."
    ::= { docsIfCmtsObjects 5 }

docsIfCmtsModulationEntry OBJECT-TYPE
    SYNTAX DocsIfCmtsModulationEntry
    ACCESS not-accessible
    STATUS mandatory
    DESCRIPTION
        "Describes a modulation profile for an Interval Usage Code
         for one or more upstream channels.
         Entries in this table are created by the operator.
        
         Initial default entries MAY be created at system
         initialization time, which could report a value of
         'permanent' or 'readOnly' for docsIfCmtsModStorageType.
         A CMTS MAY reject the creation of additional Interval
         Usage Codes for a modulation profile being defined at
         Initialization time.
         No individual objects have to be specified in order
         to create an entry in this table.
         Note that some objects do not have DEFVAL clauses
         but do have calculated defaults and need not be specified
         during row creation."
    INDEX { docsIfCmtsModIndex, docsIfCmtsModIntervalUsageCode }
    ::= { docsIfCmtsModulationTable 1 }

DocsIfCmtsModulationEntry ::= SEQUENCE {
    docsIfCmtsModIndex INTEGER,
    docsIfCmtsModIntervalUsageCode INTEGER,
    docsIfCmtsModControl RowStatus,
    docsIfCmtsModType INTEGER,
    docsIfCmtsModPreambleLen INTEGER,
    docsIfCmtsModDifferentialEncoding TruthValue,
    docsIfCmtsModFECErrorCorrection INTEGER,
    docsIfCmtsModFECCodewordLength INTEGER,
    docsIfCmtsModScramblerSeed INTEGER,
    docsIfCmtsModMaxBurstSize INTEGER,
    docsIfCmtsModGuardTimeSize Gauge,
    docsIfCmtsModLastCodewordShortened TruthValue,
    docsIfCmtsModScrambler TruthValue,
    docsIfCmtsModByteInterleaverDepth Gauge,
    docsIfCmtsModByteInterleaverBlockSize Gauge,
    docsIfCmtsModPreambleType INTEGER,
    docsIfCmtsModTcmErrorCorrectionOn TruthValue,
    docsIfCmtsModScdmaInterleaverStepSize Gauge,
    docsIfCmtsModScdmaSpreaderEnable TruthValue,
    docsIfCmtsModScdmaSubframeCodes Gauge,
    docsIfCmtsModChannelType DocsisUpstreamType,
    docsIfCmtsModStorageType StorageType
    }

docsIfCmtsModIndex OBJECT-TYPE
    SYNTAX INTEGER(1..2147483647)
    ACCESS not-accessible
    STATUS mandatory
    DESCRIPTION
        "An index into the Channel Modulation table representing
         a group of Interval Usage Codes, all associated with the
         same channel."
    ::= { docsIfCmtsModulationEntry 1 }

docsIfCmtsModIntervalUsageCode OBJECT-TYPE
    SYNTAX INTEGER {
        request(1),
        requestData(2),
        initialRanging(3),
        periodicRanging(4),
        shortData(5),
        longData(6),
        advPhyShortData(9),
        advPhyLongData(10),
        ugs(11)
        }
    ACCESS not-accessible
    STATUS mandatory
    DESCRIPTION
        "An index into the Channel Modulation table that, when
         grouped with other Interval Usage Codes, fully
         instantiates all modulation sets for a given upstream
         channel."
    REFERENCE
        "Data-Over-Cable Service Interface Specifications: Radio
         Frequency Interface Specification SP-RFIv2.0-I10-051209,
         Table 8-20."
    ::= { docsIfCmtsModulationEntry 2 }

docsIfCmtsModControl OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "Controls and reflects the status of rows in this table.
         There is no restriction on the changing of values in this
         table while their associated rows are active, with the
         exception of:
        
         1. If a modulation profile is being referenced by one
            or more upstream channels, an attempt to set the value
            of docsIfCmtsModChannelType returns an
            'inconsistentValue' error.
        
         2. If a modulation profile is being referenced by one
            or more upstream channels, an attempt to set
            docsIfCmtsModControl to destroy(6) or notInService(2)
            returns an 'inconsistentValue' error."
    ::= { docsIfCmtsModulationEntry 3 }

docsIfCmtsModType OBJECT-TYPE
    SYNTAX INTEGER {
        other(1),
        qpsk(2),
        qam16(3),
        qam8(4),
        qam32(5),
        qam64(6),
        qam128(7)
        }
    ACCESS read-write
    STATUS mandatory
    DESCRIPTION
        "The modulation type used on this channel.  Returns
         other(1) if the modulation type is not
         qpsk, qam16, qam8, qam32, qam64, or qam128.
         Type qam128 is used for SCDMA channels only.
         See the reference for the modulation profiles
         implied by different modulation types."
    REFERENCE
        "Data-Over-Cable Service Interface Specifications: Radio
         Frequency Interface Specification SP-RFIv2.0-I10-051209,
         Tables 6-7, and 8-19."
    DEFVAL { qpsk }
    ::= { docsIfCmtsModulationEntry 4 }

docsIfCmtsModPreambleLen OBJECT-TYPE
    SYNTAX INTEGER(0..1536)
--  Units
--    bits
    ACCESS read-write
    STATUS mandatory
    DESCRIPTION
        "The preamble length for this modulation profile in bits.
         Default value is the minimum needed by the implementation
         at the CMTS for the given modulation profile."
    REFERENCE
        "Data-Over-Cable Service Interface Specifications: Radio
         Frequency Interface Specification SP-RFIv2.0-I10-051209,
         Tables 6-7, and 8-19."
    ::= { docsIfCmtsModulationEntry 5 }

docsIfCmtsModDifferentialEncoding OBJECT-TYPE
    SYNTAX TruthValue
--    Rsyntax INTEGER {
--        true(1),
--        false(2)
--        }
    ACCESS read-write
    STATUS mandatory
    DESCRIPTION
        "Specifies whether or not differential encoding is used
         on this channel."
    REFERENCE
        "Data-Over-Cable Service Interface Specifications: Radio
         Frequency Interface Specification SP-RFIv2.0-I10-051209,
         Tables 6-7, and 8-19."
    DEFVAL { false }
    ::= { docsIfCmtsModulationEntry 6 }

docsIfCmtsModFECErrorCorrection OBJECT-TYPE
    SYNTAX INTEGER(0..16)
--  Units
--    Bytes
    ACCESS read-write
    STATUS mandatory
    DESCRIPTION
        "The number of correctable errored bytes (t) used in
         forward error correction code.  The value of 0 indicates
         that no correction is employed.  The number of check bytes
         appended will be twice this value."
    REFERENCE
        "Data-Over-Cable Service Interface Specifications: Radio
         Frequency Interface Specification SP-RFIv2.0-I10-051209,
         Tables 6-7, and 8-19."
    DEFVAL { 0 }
    ::= { docsIfCmtsModulationEntry 7 }

docsIfCmtsModFECCodewordLength OBJECT-TYPE
    SYNTAX INTEGER(1..255)
--  Units
--    Bytes
    ACCESS read-write
    STATUS mandatory
    DESCRIPTION
        "The number of data bytes (k) in the forward error
         correction codeword.
         This object is not used if docsIfCmtsModFECErrorCorrection
         is zero."
    REFERENCE
        "Data-Over-Cable Service Interface Specifications: Radio
         Frequency Interface Specification SP-RFIv2.0-I10-051209,
         Tables 6-7, and 8-19."
    DEFVAL { 32 }
    ::= { docsIfCmtsModulationEntry 8 }

docsIfCmtsModScramblerSeed OBJECT-TYPE
    SYNTAX INTEGER(0..32767)
    ACCESS read-write
    STATUS mandatory
    DESCRIPTION
        "The 15-bit seed value for the scrambler polynomial."
    REFERENCE
        "Data-Over-Cable Service Interface Specifications: Radio
         Frequency Interface Specification SP-RFIv2.0-I10-051209,
         Table 8-19."
    DEFVAL { 0 }
    ::= { docsIfCmtsModulationEntry 9 }

docsIfCmtsModMaxBurstSize OBJECT-TYPE
    SYNTAX INTEGER(0..255)
--  Units
--    mini-slots
    ACCESS read-write
    STATUS mandatory
    DESCRIPTION
        "The maximum number of mini-slots that can be transmitted
         during this channel's burst time.  Returns zero if the
         burst length is bounded by the allocation MAP rather than
         by this profile.
         Default value is 0, except for shortData, where it is 8."
    REFERENCE
        "Data-Over-Cable Service Interface Specifications: Radio
         Frequency Interface Specification SP-RFIv2.0-I10-051209,
         Table 8-19."
    ::= { docsIfCmtsModulationEntry 10 }

docsIfCmtsModGuardTimeSize OBJECT-TYPE
    SYNTAX Gauge
--  Units
--    Symbol-times
    ACCESS read-only
    STATUS mandatory
    DESCRIPTION
        "The number of symbol-times that MUST follow the end of
         this channel's burst.  Default value is the minimum time
         needed by the implementation for this modulation profile."
    REFERENCE
        "Data-Over-Cable Service Interface Specifications: Radio
         Frequency Interface Specification SP-RFIv2.0-I10-051209,
         Tables 6-7, and 8-19."
    ::= { docsIfCmtsModulationEntry 11 }

docsIfCmtsModLastCodewordShortened OBJECT-TYPE
    SYNTAX TruthValue
--    Rsyntax INTEGER {
--        true(1),
--        false(2)
--        }
    ACCESS read-write
    STATUS mandatory
    DESCRIPTION
        "Indicates whether the last FEC codeword is truncated."
    REFERENCE
        "Data-Over-Cable Service Interface Specifications: Radio
         Frequency Interface Specification SP-RFIv2.0-I10-051209,
         Tables 6-7, and 8-19."
    DEFVAL { true }
    ::= { docsIfCmtsModulationEntry 12 }

docsIfCmtsModScrambler OBJECT-TYPE
    SYNTAX TruthValue
--    Rsyntax INTEGER {
--        true(1),
--        false(2)
--        }
    ACCESS read-write
    STATUS mandatory
    DESCRIPTION
        "Indicates whether the scrambler is employed."
    REFERENCE
        "Data-Over-Cable Service Interface Specifications: Radio
         Frequency Interface Specification SP-RFIv2.0-I10-051209,
         Tables 6-7, and 8-19."
    DEFVAL { false }
    ::= { docsIfCmtsModulationEntry 13 }

docsIfCmtsModByteInterleaverDepth OBJECT-TYPE
    SYNTAX Gauge
    ACCESS read-write
    STATUS mandatory
    DESCRIPTION
        "ATDMA Byte Interleaver Depth (Ir).  This object returns 1
         for non-ATDMA profiles."
    REFERENCE
        "Data-Over-Cable Service Interface Specifications: Radio
         Frequency Interface Specification SP-RFIv2.0-I10-051209,
         Tables 6-7, and 8-19."
    DEFVAL { 1 }
    ::= { docsIfCmtsModulationEntry 14 }

docsIfCmtsModByteInterleaverBlockSize OBJECT-TYPE
    SYNTAX Gauge
    ACCESS read-write
    STATUS mandatory
    DESCRIPTION
        "ATDMA Byte Interleaver Block size (Br).  This object
         returns zero for non-ATDMA profiles "
    REFERENCE
        "Data-Over-Cable Service Interface Specifications: Radio
         Frequency Interface Specification SP-RFIv2.0-I10-051209,
         Tables 6-7, and 8-19."
    DEFVAL { 18 }
    ::= { docsIfCmtsModulationEntry 15 }

docsIfCmtsModPreambleType OBJECT-TYPE
    SYNTAX INTEGER {
        --?? enum value of zero may cause problems
        unknown(0),
        qpsk0(1),
        qpsk1(2)
        }
    ACCESS read-write
    STATUS mandatory
    DESCRIPTION
        "Preamble type for DOCSIS 2.0 bursts.  The value
         'unknown(0)' represents a row entry consisting only of
         DOCSIS 1.x bursts"
    REFERENCE
        "Data-Over-Cable Service Interface Specifications: Radio
         Frequency Interface Specification SP-RFIv2.0-I10-051209,
         Tables 6-7, and 8-19."
    DEFVAL { qpsk0 }
    ::= { docsIfCmtsModulationEntry 16 }

docsIfCmtsModTcmErrorCorrectionOn OBJECT-TYPE
    SYNTAX TruthValue
--    Rsyntax INTEGER {
--        true(1),
--        false(2)
--        }
    ACCESS read-write
    STATUS mandatory
    DESCRIPTION
        "Trellis Code Modulation (TCM) On/Off.  This value returns
         false for non-S-CDMA profiles."
    REFERENCE
        "Data-Over-Cable Service Interface Specifications: Radio
         Frequency Interface Specification SP-RFIv2.0-I10-051209,
         Tables 6-7, and 8-19."
    DEFVAL { false }
    ::= { docsIfCmtsModulationEntry 17 }

docsIfCmtsModScdmaInterleaverStepSize OBJECT-TYPE
    SYNTAX Gauge(0|1..32)
    ACCESS read-write
    STATUS mandatory
    DESCRIPTION
        " S-CDMA Interleaver step size.  This value returns zero
          for non-S-CDMA profiles."
    REFERENCE
        "Data-Over-Cable Service Interface Specifications: Radio
         Frequency Interface Specification SP-RFIv2.0-I10-051209,
         Tables 6-7, and 8-19."
    DEFVAL { 1 }
    ::= { docsIfCmtsModulationEntry 18 }

docsIfCmtsModScdmaSpreaderEnable OBJECT-TYPE
    SYNTAX TruthValue
--    Rsyntax INTEGER {
--        true(1),
--        false(2)
--        }
    ACCESS read-write
    STATUS mandatory
    DESCRIPTION
        " S-CDMA spreader.  This value returns false for non-S-CDMA
          profiles.  Default value for IUC 3 and 4 is OFF; for
          all other IUCs it is ON."
    REFERENCE
        "Data-Over-Cable Service Interface Specifications: Radio
         Frequency Interface Specification SP-RFIv2.0-I10-051209,
         Tables 6-7, and 8-19."
    ::= { docsIfCmtsModulationEntry 19 }

docsIfCmtsModScdmaSubframeCodes OBJECT-TYPE
    SYNTAX Gauge(0|1..128)
    ACCESS read-write
    STATUS mandatory
    DESCRIPTION
        " S-CDMA sub-frame size.  This value returns zero
          for non-S-CDMA profiles."
    REFERENCE
        "Data-Over-Cable Service Interface Specifications: Radio
         Frequency Interface Specification SP-RFIv2.0-I10-051209,
         Table 6-7, and 8-19."
    DEFVAL { 1 }
    ::= { docsIfCmtsModulationEntry 20 }

docsIfCmtsModChannelType OBJECT-TYPE
    SYNTAX DocsisUpstreamType
--    Rsyntax INTEGER {
--        ?? enum value of zero may cause problems
--        unknown(0),
--        tdma(1),
--        atdma(2),
--        scdma(3),
--        tdmaAndAtdma(4)
--        }
    ACCESS read-write
    STATUS mandatory
    DESCRIPTION
        "Describes the modulation channel type for this modulation
         entry.
         All the active entries in a modulation profile (that is all
         active entries that share a common docsIfCmtsModIndex)
         MUST have the same value of docsIfCmtsModChannelType."
    REFERENCE
        "Data-Over-Cable Service Interface Specifications: Radio
         Frequency Interface Specification SP-RFIv2.0-I10-051209,
         Table 8-19."
    DEFVAL { tdma }
    ::= { docsIfCmtsModulationEntry 21 }

docsIfCmtsModStorageType OBJECT-TYPE
    SYNTAX StorageType
--    Rsyntax INTEGER {
--        other(1),
--        volatile(2),
--        nonVolatile(3),
--        permanent(4),
--        readOnly(5)
--        }
    ACCESS read-only
    STATUS mandatory
    DESCRIPTION
        "The storage type for this conceptual row.
         Entries with this object set to permanent(4)
         do not require write operations for read-write
         objects."
    DEFVAL { nonVolatile }
    ::= { docsIfCmtsModulationEntry 22 }

docsIfCmtsQosProfilePermissions OBJECT-TYPE
    SYNTAX OCTET STRING(SIZE(1..2))
        -- BITS are:
        --   createByManagement(0)
        --   updateByManagement(1)
        --   createByModems(2)
    ACCESS read-write
    STATUS mandatory
    DESCRIPTION
        "This object specifies permitted methods of creating
         entries in docsIfQosProfileTable.
         createByManagement(0) is set if entries can be created
         using SNMP.  updateByManagement(1) is set if updating
         entries using SNMP is permitted.  createByModems(2)
         is set if entries can be created based on information
         in REG-REQ MAC messages received from cable modems.
         Information in this object is only applicable if
         docsIfQosProfileTable is implemented as read-create.
         Otherwise, this object is implemented as read-only
         and returns createByModems(2).
         Either createByManagement(0) or updateByManagement(1)
         MUST be set when writing to this object.
         Note that BITS objects are encoded most significant bit
         first.  For example, if bit 2 is set, the value of this
         object is the octet string '20'H."
    ::= { docsIfCmtsObjects 6 }

docsIfCmtsMacToCmTable OBJECT-TYPE
    SYNTAX SEQUENCE OF DocsIfCmtsMacToCmEntry
    ACCESS not-accessible
    STATUS mandatory
    DESCRIPTION
        "This is a table to provide a quick access index into the
         docsIfCmtsCmStatusTable.  There is exactly one row in this
         table for each row in the docsIfCmtsCmStatusTable.  In
         general, the management station SHOULD use this table only
         to get a pointer into the docsIfCmtsCmStatusTable (which
         corresponds to the CM's RF interface MAC address) and
         SHOULD not iterate (e.g., GetNext through) this table."
    ::= { docsIfCmtsObjects 7 }

docsIfCmtsMacToCmEntry OBJECT-TYPE
    SYNTAX DocsIfCmtsMacToCmEntry
    ACCESS not-accessible
    STATUS mandatory
    DESCRIPTION
        "A row in the docsIfCmtsMacToCmTable.
         An entry in this table exists for each cable modem
         that is connected to the CMTS implementing this table."
    INDEX { docsIfCmtsCmMac }
    ::= { docsIfCmtsMacToCmTable 1 }

DocsIfCmtsMacToCmEntry ::= SEQUENCE {
    docsIfCmtsCmMac MacAddress,
    docsIfCmtsCmPtr INTEGER
    }

docsIfCmtsCmMac OBJECT-TYPE
    SYNTAX MacAddress
--    Rsyntax OCTET STRING(SIZE(6))
    ACCESS not-accessible
    STATUS mandatory
    DESCRIPTION
        "The RF side MAC address for the referenced CM (e.g., the
         interface on the CM that has docsCableMacLayer(127) as
         its ifType)."
    ::= { docsIfCmtsMacToCmEntry 1 }

docsIfCmtsCmPtr OBJECT-TYPE
    SYNTAX INTEGER(1..2147483647)
    ACCESS read-only
    STATUS mandatory
    DESCRIPTION
        "An row index into docsIfCmtsCmStatusTable.  When queried
         with the correct instance value (e.g., a CM's MAC address),
         returns the index in docsIfCmtsCmStatusTable that
         represents that CM."
    ::= { docsIfCmtsMacToCmEntry 2 }

docsIfCmtsChannelUtilizationInterval OBJECT-TYPE
    SYNTAX INTEGER(0..86400)
--  Units
--    seconds
    ACCESS read-write
    STATUS mandatory
    DESCRIPTION
        "The time interval in seconds over which the channel
         utilization index is calculated.  All upstream/downstream
         channels use the same
         docsIfCmtsChannelUtilizationInterval.
         Setting a value of zero disables utilization reporting.
         A channel utilization index is calculated over a fixed
         window applying to the most recent
         docsIfCmtsChannelUtilizationInterval.  It would therefore
         be prudent to use a relatively short
         docsIfCmtsChannelUtilizationInterval.
         It is a vendor decision whether to reset the timer when
         docsIfCmtsChannelUtilizationInterval is changed during a
         utilization sampling period."
    ::= { docsIfCmtsObjects 8 }

docsIfCmtsChannelUtilizationTable OBJECT-TYPE
    SYNTAX SEQUENCE OF DocsIfCmtsChannelUtilizationEntry
    ACCESS not-accessible
    STATUS mandatory
    DESCRIPTION
        "Reports utilization statistics for attached upstream and
         downstream physical channels."
    ::= { docsIfCmtsObjects 9 }

docsIfCmtsChannelUtilizationEntry OBJECT-TYPE
    SYNTAX DocsIfCmtsChannelUtilizationEntry
    ACCESS not-accessible
    STATUS mandatory
    DESCRIPTION
        "Utilization statistics for a single upstream or downstream
         physical channel.  An entry exists in this table for each
         ifEntry with an ifType equal to
         docsCableDownstream (128)
         or docsCableUpstream (129)."
    INDEX { ifIndex, docsIfCmtsChannelUtIfType, docsIfCmtsChannelUtId }
    ::= { docsIfCmtsChannelUtilizationTable 1 }

DocsIfCmtsChannelUtilizationEntry ::= SEQUENCE {
    docsIfCmtsChannelUtIfType IANAifType,
    docsIfCmtsChannelUtId INTEGER,
    docsIfCmtsChannelUtUtilization INTEGER
    }

docsIfCmtsChannelUtIfType OBJECT-TYPE
    SYNTAX IANAifType
--    Rsyntax INTEGER {
--        other(1),
--        regular1822(2),
--        hdh1822(3),
--        ddnX25(4),
--        rfc877x25(5),
--        ethernetCsmacd(6),
--        iso88023Csmacd(7),
--        iso88024TokenBus(8),
--        iso88025TokenRing(9),
--        iso88026Man(10),
--        starLan(11),
--        proteon10Mbit(12),
--        proteon80Mbit(13),
--        hyperchannel(14),
--        fddi(15),
--        lapb(16),
--        sdlc(17),
--        ds1(18),
--        e1(19),
--        basicISDN(20),
--        primaryISDN(21),
--        propPointToPointSerial(22),
--        ppp(23),
--        softwareLoopback(24),
--        eon(25),
--        ethernet3Mbit(26),
--        nsip(27),
--        slip(28),
--        ultra(29),
--        ds3(30),
--        sip(31),
--        frameRelay(32),
--        rs232(33),
--        para(34),
--        arcnet(35),
--        arcnetPlus(36),
--        atm(37),
--        miox25(38),
--        sonet(39),
--        x25ple(40),
--        iso88022llc(41),
--        localTalk(42),
--        smdsDxi(43),
--        frameRelayService(44),
--        v35(45),
--        hssi(46),
--        hippi(47),
--        modem(48),
--        aal5(49),
--        sonetPath(50),
--        sonetVT(51),
--        smdsIcip(52),
--        propVirtual(53),
--        propMultiplexor(54),
--        ieee80212(55),
--        fibreChannel(56),
--        hippiInterface(57),
--        frameRelayInterconnect(58),
--        aflane8023(59),
--        aflane8025(60),
--        cctEmul(61),
--        fastEther(62),
--        isdn(63),
--        v11(64),
--        v36(65),
--        g703at64k(66),
--        g703at2mb(67),
--        qllc(68),
--        fastEtherFX(69),
--        channel(70),
--        ieee80211(71),
--        ibm370parChan(72),
--        escon(73),
--        dlsw(74),
--        isdns(75),
--        isdnu(76),
--        lapd(77),
--        ipSwitch(78),
--        rsrb(79),
--        atmLogical(80),
--        ds0(81),
--        ds0Bundle(82),
--        bsc(83),
--        async(84),
--        cnr(85),
--        iso88025Dtr(86),
--        eplrs(87),
--        arap(88),
--        propCnls(89),
--        hostPad(90),
--        termPad(91),
--        frameRelayMPI(92),
--        x213(93),
--        adsl(94),
--        radsl(95),
--        sdsl(96),
--        vdsl(97),
--        iso88025CRFPInt(98),
--        myrinet(99),
--        voiceEM(100),
--        voiceFXO(101),
--        voiceFXS(102),
--        voiceEncap(103),
--        voiceOverIp(104),
--        atmDxi(105),
--        atmFuni(106),
--        atmIma(107),
--        pppMultilinkBundle(108),
--        ipOverCdlc(109),
--        ipOverClaw(110),
--        stackToStack(111),
--        virtualIpAddress(112),
--        mpc(113),
--        ipOverAtm(114),
--        iso88025Fiber(115),
--        tdlc(116),
--        gigabitEthernet(117)
--        }
    ACCESS not-accessible
    STATUS mandatory
    DESCRIPTION
        "The secondary index into this table.  Indicates the IANA
         interface type associated with this physical channel.
         Only docsCableDownstream (128) and
         docsCableUpstream (129) are valid."
    ::= { docsIfCmtsChannelUtilizationEntry 1 }

docsIfCmtsChannelUtId OBJECT-TYPE
    SYNTAX INTEGER(0..255)
    ACCESS not-accessible
    STATUS mandatory
    DESCRIPTION
        "The tertiary index into this table.  Indicates the CMTS
         identifier for this physical channel."
    ::= { docsIfCmtsChannelUtilizationEntry 2 }

docsIfCmtsChannelUtUtilization OBJECT-TYPE
    SYNTAX INTEGER(0..100)
--  Units
--    percent
    ACCESS read-only
    STATUS mandatory
    DESCRIPTION
        "The calculated and truncated utilization index for this
         physical upstream or downstream channel, accurate as of
         the most recent docsIfCmtsChannelUtilizationInterval.
        
         Upstream Channel Utilization Index:
        
         The upstream channel utilization index is expressed as a
         percentage of mini-slots utilized on the physical channel,
         regardless of burst type.  For an Initial Maintenance
         region, the mini-slots for the complete region are
         considered utilized if the CMTS received an upstream
         burst within the region from any CM on the physical
         channel.  For contention REQ and REQ/DATA regions, the
         mini-slots for a transmission opportunity within the
         region are considered utilized if the CMTS received an
         upstream burst within the opportunity from any CM on the
         physical channel.  For all other regions, utilized
         mini-slots are those in which the CMTS granted
         bandwidth to any unicast SID on the physical channel.
        
         For an upstream interface that has multiple logical
         upstream channels enabled, the utilization index is a
         weighted sum of utilization indices for the logical
         channels.  The weight for each utilization index is the
         percentage of upstream mini-slots allocated for the
         corresponding logical channel.
         Example:
         If 75% of bandwidth is allocated to the first logical
         channel and 25% to the second, and the utilization
         indices for each are 60 and 40, respectively, the
         utilization index for the upstream physical channel is
         (60 * 0.75) + (40 * 0.25) = 55.  This figure
         applies to the most recent utilization interval.
        
         Downstream Channel Utilization Index:
        
         The downstream channel utilization index is a percentage
         expressing the ratio between bytes used to transmit data
         versus the total number of bytes transmitted in the raw
         bandwidth of the MPEG channel.  As with the upstream
         utilization index, the calculated value represents
         the most recent utilization interval.
         Formula:
         Downstream utilization index =
         (100 * (data bytes / raw bytes))
        
         Definitions:
         Data bytes:    Number of bytes transmitted as data in the
                        docsIfCmtsChannelUtilizationInterval.
                        Identical to docsIfCmtsDownChannelCtrUsed
                        Bytes measured over the utilization
                        interval.
         Raw bandwidth: Total number of bytes available for
                        transmitting data, not including bytes
                        used for headers and other overhead.
         Raw bytes:     (raw bandwidth *
                        docsIfCmtsChannelUtilizationInterval).
                        Identical to docsIfCmtsDownChannelCtrTotal
                        Bytes measured over the utilization
                        interval."
    ::= { docsIfCmtsChannelUtilizationEntry 3 }

docsIfCmtsDownChannelCounterTable OBJECT-TYPE
    SYNTAX SEQUENCE OF DocsIfCmtsDownChannelCounterEntry
    ACCESS not-accessible
    STATUS mandatory
    DESCRIPTION
        "This table is implemented at the CMTS to collect
         downstream channel statistics for utilization
         calculations."
    ::= { docsIfCmtsObjects 10 }

docsIfCmtsDownChannelCounterEntry OBJECT-TYPE
    SYNTAX DocsIfCmtsDownChannelCounterEntry
    ACCESS not-accessible
    STATUS mandatory
    DESCRIPTION
        "An entry provides a list of traffic counters for a single
         downstream channel.
         An entry in this table exists for each ifEntry with an
         ifType of docsCableDownstream(128)."
    INDEX { ifIndex }
    ::= { docsIfCmtsDownChannelCounterTable 1 }

DocsIfCmtsDownChannelCounterEntry ::= SEQUENCE {
    docsIfCmtsDownChnlCtrId INTEGER,
    docsIfCmtsDownChnlCtrTotalBytes Counter,
    docsIfCmtsDownChnlCtrUsedBytes Counter,
    docsIfCmtsDownChnlCtrExtTotalBytes Counter,
    docsIfCmtsDownChnlCtrExtUsedBytes Counter
    }

docsIfCmtsDownChnlCtrId OBJECT-TYPE
    SYNTAX INTEGER(0..255)
    ACCESS read-only
    STATUS mandatory
    DESCRIPTION
        "The Cable Modem Termination System identification
         of the downstream channel within this particular MAC
         interface.  If the interface is down, the object returns
         the most current value.  If the downstream channel ID is
         unknown, this object returns a value of 0."
    ::= { docsIfCmtsDownChannelCounterEntry 1 }

docsIfCmtsDownChnlCtrTotalBytes OBJECT-TYPE
    SYNTAX Counter
--  Units
--    Bytes
    ACCESS read-only
    STATUS mandatory
    DESCRIPTION
        "At the CMTS, the total number of bytes in the Payload
         portion of MPEG Packets (i.e., not including MPEG header
         or pointer_field) transported by this downstream channel.
         This is the 32-bit version of
         docsIfCmtsDownChnlCtrExtTotalBytes, included to provide
         back compatibility with SNMPv1 managers.
         Discontinuities in the value of this counter can occur
         at reinitialization of the managed system, and at other
         times as indicated by the value of
         ifCounterDiscontinuityTime for the associated ifIndex."
    ::= { docsIfCmtsDownChannelCounterEntry 2 }

docsIfCmtsDownChnlCtrUsedBytes OBJECT-TYPE
    SYNTAX Counter
--  Units
--    Bytes
    ACCESS read-only
    STATUS mandatory
    DESCRIPTION
        "At the CMTS, the total number of DOCSIS data bytes
         transported by this downstream channel.
         The number of data bytes is defined as the total number
         of bytes transported in DOCSIS payloads minus the number
         of stuff bytes transported in DOCSIS payloads.
         This is the 32-bit version of
         docsIfCmtsDownChnlCtrExtUsedBytes, included to provide
         back compatibility with SNMPv1 managers.
         Discontinuities in the value of this counter can occur
         at reinitialization of the managed system, and at other
         times as indicated by the value of
         ifCounterDiscontinuityTime for the associated ifIndex."
    ::= { docsIfCmtsDownChannelCounterEntry 3 }

docsIfCmtsDownChnlCtrExtTotalBytes OBJECT-TYPE
    SYNTAX --?? syntax is not convertable to SMIv1
           Counter
--  Units
--    Bytes
    ACCESS read-only
    STATUS mandatory
    DESCRIPTION
        "At the CMTS, the total number of bytes in the Payload
         portion of MPEG Packets (i.e., not including MPEG header
         or pointer_field) transported by this downstream
         channel.
         This is the 64-bit version of
         docsIfCmtsDownChnlCtrTotalBytes and will not be
         accessible to SNMPv1 managers.
         Discontinuities in the value of this counter can occur
         at reinitialization of the managed system, and at other
         times as indicated by the value of
         ifCounterDiscontinuityTime for the associated ifIndex."
    ::= { docsIfCmtsDownChannelCounterEntry 4 }

docsIfCmtsDownChnlCtrExtUsedBytes OBJECT-TYPE
    SYNTAX --?? syntax is not convertable to SMIv1
           Counter
--  Units
--    Bytes
    ACCESS read-only
    STATUS mandatory
    DESCRIPTION
        "At the CMTS, the total number of DOCSIS data bytes
         transported by this downstream channel.  The number
         of data bytes is defined as the total number of bytes
         transported in DOCSIS payloads minus the number of
         stuff bytes transported in DOCSIS payloads.
         This is the 64-bit version of
         docsIfCmtsDownChnlCtrUsedBytes and will not be accessible
         to SNMPv1 managers.
         Discontinuities in the value of this counter can occur
         at reinitialization of the managed system, and at other
         times as indicated by the value of
         ifCounterDiscontinuityTime for the associated ifIndex."
    ::= { docsIfCmtsDownChannelCounterEntry 5 }

docsIfCmtsUpChannelCounterTable OBJECT-TYPE
    SYNTAX SEQUENCE OF DocsIfCmtsUpChannelCounterEntry
    ACCESS not-accessible
    STATUS mandatory
    DESCRIPTION
        "This table is implemented at the CMTS to provide upstream
         channel statistics appropriate for channel utilization
         calculations."
    ::= { docsIfCmtsObjects 11 }

docsIfCmtsUpChannelCounterEntry OBJECT-TYPE
    SYNTAX DocsIfCmtsUpChannelCounterEntry
    ACCESS not-accessible
    STATUS mandatory
    DESCRIPTION
        "List of traffic statistics for a single upstream channel.
         For DOCSIS 2.0 CMTSs, an entry in this table
         exists for each ifEntry with an ifType of
         docsCableUpstreamChannel (205).
         For DOCSIS 1.x CMTSs, an entry in this table
         exists for each ifEntry with an ifType of
         docsCableUpstream (129)."
    INDEX { ifIndex }
    ::= { docsIfCmtsUpChannelCounterTable 1 }

DocsIfCmtsUpChannelCounterEntry ::= SEQUENCE {
    docsIfCmtsUpChnlCtrId INTEGER,
    docsIfCmtsUpChnlCtrTotalMslots Counter,
    docsIfCmtsUpChnlCtrUcastGrantedMslots Counter,
    docsIfCmtsUpChnlCtrTotalCntnMslots Counter,
    docsIfCmtsUpChnlCtrUsedCntnMslots Counter,
    docsIfCmtsUpChnlCtrExtTotalMslots Counter,
    docsIfCmtsUpChnlCtrExtUcastGrantedMslots Counter,
    docsIfCmtsUpChnlCtrExtTotalCntnMslots Counter,
    docsIfCmtsUpChnlCtrExtUsedCntnMslots Counter,
    docsIfCmtsUpChnlCtrCollCntnMslots Counter,
    docsIfCmtsUpChnlCtrTotalCntnReqMslots Counter,
    docsIfCmtsUpChnlCtrUsedCntnReqMslots Counter,
    docsIfCmtsUpChnlCtrCollCntnReqMslots Counter,
    docsIfCmtsUpChnlCtrTotalCntnReqDataMslots Counter,
    docsIfCmtsUpChnlCtrUsedCntnReqDataMslots Counter,
    docsIfCmtsUpChnlCtrCollCntnReqDataMslots Counter,
    docsIfCmtsUpChnlCtrTotalCntnInitMaintMslots Counter,
    docsIfCmtsUpChnlCtrUsedCntnInitMaintMslots Counter,
    docsIfCmtsUpChnlCtrCollCntnInitMaintMslots Counter,
    docsIfCmtsUpChnlCtrExtCollCntnMslots Counter,
    docsIfCmtsUpChnlCtrExtTotalCntnReqMslots Counter,
    docsIfCmtsUpChnlCtrExtUsedCntnReqMslots Counter,
    docsIfCmtsUpChnlCtrExtCollCntnReqMslots Counter,
    docsIfCmtsUpChnlCtrExtTotalCntnReqDataMslots Counter,
    docsIfCmtsUpChnlCtrExtUsedCntnReqDataMslots Counter,
    docsIfCmtsUpChnlCtrExtCollCntnReqDataMslots Counter,
    docsIfCmtsUpChnlCtrExtTotalCntnInitMaintMslots Counter,
    docsIfCmtsUpChnlCtrExtUsedCntnInitMaintMslots Counter,
    docsIfCmtsUpChnlCtrExtCollCntnInitMaintMslots Counter
    }

docsIfCmtsUpChnlCtrId OBJECT-TYPE
    SYNTAX INTEGER(0..255)
    ACCESS read-only
    STATUS mandatory
    DESCRIPTION
        "The CMTS identification of the upstream channel."
    ::= { docsIfCmtsUpChannelCounterEntry 1 }

docsIfCmtsUpChnlCtrTotalMslots OBJECT-TYPE
    SYNTAX Counter
--  Units
--    mini-slots
    ACCESS read-only
    STATUS mandatory
    DESCRIPTION
        "Current count, from CMTS initialization, of all mini-slots
         defined for this upstream logical channel.  This count
         includes all IUCs and SIDs, even those allocated to the
         NULL SID for a 2.0 logical channel that is inactive.  This
         is the 32-bit version of docsIfCmtsUpChnlCtrExtTotalMslots
         and is included for back compatibility with SNMPv1
         managers.  Support for this object is mandatory.
         Discontinuities in the value of this counter can occur
         at reinitialization of the managed system, and at other
         times as indicated by the value of
         ifCounterDiscontinuityTime for the associated ifIndex."
    ::= { docsIfCmtsUpChannelCounterEntry 2 }

docsIfCmtsUpChnlCtrUcastGrantedMslots OBJECT-TYPE
    SYNTAX Counter
--  Units
--    mini-slots
    ACCESS read-only
    STATUS mandatory
    DESCRIPTION
        "Current count, from CMTS initialization, of unicast
         granted mini-slots on the upstream logical channel,
         regardless of burst type.  Unicast granted mini-slots are
         those in which the CMTS assigned bandwidth to any unicast
         SID on the logical channel.  However, this object does not
         include minis-lots for reserved IUCs, or grants to SIDs
         designated as meaning 'no CM'.  This is the 32-bit version
         of docsIfCmtsUpChnlCtrExtUcastGrantedMslots, and is
         included for back compatibility with SNMPv1 managers.
         Support for this object is mandatory.
         Discontinuities in the value of this counter can occur
         at reinitialization of the managed system, and at other
         times as indicated by the value of
         ifCounterDiscontinuityTime for the associated ifIndex."
    ::= { docsIfCmtsUpChannelCounterEntry 3 }

docsIfCmtsUpChnlCtrTotalCntnMslots OBJECT-TYPE
    SYNTAX Counter
--  Units
--    mini-slots
    ACCESS read-only
    STATUS mandatory
    DESCRIPTION
        "Current count, from CMTS initialization, of contention
         mini-slots defined for this upstream logical channel.  This
         count includes all mini-slots assigned to a broadcast or
         multicast SID on the logical channel.  This is the 32-bit
         version of docsIfCmtsUpChnlCtrExtTotalCntnMslots, and is
         included for back compatibility with SNMPv1 managers.
         Support for this object is mandatory.
         Discontinuities in the value of this counter can occur
         at reinitialization of the managed system, and at other
         times as indicated by the value of
         ifCounterDiscontinuityTime for the associated ifIndex."
    ::= { docsIfCmtsUpChannelCounterEntry 4 }

docsIfCmtsUpChnlCtrUsedCntnMslots OBJECT-TYPE
    SYNTAX Counter
--  Units
--    mini-slots
    ACCESS read-only
    STATUS mandatory
    DESCRIPTION
        "Current count, from CMTS initialization, of contention
         mini-slots utilized on the upstream logical channel.  For
         contention regions, utilized mini-slots are those in which
         the CMTS correctly received an upstream burst from any CM
         on the upstream logical channel.  This is the 32-bit
         version of docsIfCmtsUpChnlCtrExtUsedCntnMslots and is
         included for back compatibility with SNMPv1 managers.
         Support for this object is mandatory.
         Discontinuities in the value of this counter can occur
         at reinitialization of the managed system, and at other
         times as indicated by the value of
         ifCounterDiscontinuityTime for the associated ifIndex."
    ::= { docsIfCmtsUpChannelCounterEntry 5 }

docsIfCmtsUpChnlCtrExtTotalMslots OBJECT-TYPE
    SYNTAX --?? syntax is not convertable to SMIv1
           Counter
--  Units
--    mini-slots
    ACCESS read-only
    STATUS mandatory
    DESCRIPTION
        "Current count, from CMTS initialization, of all mini-slots
         defined for this upstream logical channel.  This count
         includes all IUCs and SIDs, even those allocated to the
         NULL SID for a 2.0 logical channel that is inactive.  This
         is the 64-bit version of docsIfCmtsUpChnlCtrTotalMslots
         and will not be accessible to SNMPv1 managers.
         Support for this object is mandatory.
         Discontinuities in the value of this counter can occur
         at reinitialization of the managed system, and at other
         times as indicated by the value of
         ifCounterDiscontinuityTime for the associated ifIndex."
    ::= { docsIfCmtsUpChannelCounterEntry 6 }

docsIfCmtsUpChnlCtrExtUcastGrantedMslots OBJECT-TYPE
    SYNTAX --?? syntax is not convertable to SMIv1
           Counter
--  Units
--    mini-slots
    ACCESS read-only
    STATUS mandatory
    DESCRIPTION
        "Current count, from CMTS initialization, of unicast
         granted mini-slots on the upstream logical channel,
         regardless of burst type.  Unicast granted mini-slots are
         those in which the CMTS assigned bandwidth to any unicast
         SID on the logical channel.  However, this object does not
         include mini-slots for reserved IUCs, or grants to SIDs
         designated as meaning 'no CM'.  This is the 64-bit version
         of docsIfCmtsUpChnlCtrUcastGrantedMslots and will not be
         accessible to SNMPv1 managers.
         Support for this object is mandatory.
         Discontinuities in the value of this counter can occur
         at reinitialization of the managed system, and at other
         times as indicated by the value of
         ifCounterDiscontinuityTime for the associated ifIndex."
    ::= { docsIfCmtsUpChannelCounterEntry 7 }

docsIfCmtsUpChnlCtrExtTotalCntnMslots OBJECT-TYPE
    SYNTAX --?? syntax is not convertable to SMIv1
           Counter
--  Units
--    mini-slots
    ACCESS read-only
    STATUS mandatory
    DESCRIPTION
        "Current count, from CMTS initialization, of contention
         mini-slots defined for this upstream logical channel.  This
         count includes all mini-slots assigned to a broadcast or
         multicast SID on the logical channel.  This is the 64-bit
         version of docsIfCmtsUpChnlCtrTotalCntnMslots and will
         not be accessible to SNMPv1 managers.
         Support for this object is mandatory.
         Discontinuities in the value of this counter can occur
         at reinitialization of the managed system, and at other
         times as indicated by the value of
         ifCounterDiscontinuityTime for the associated ifIndex."
    ::= { docsIfCmtsUpChannelCounterEntry 8 }

docsIfCmtsUpChnlCtrExtUsedCntnMslots OBJECT-TYPE
    SYNTAX --?? syntax is not convertable to SMIv1
           Counter
--  Units
--    mini-slots
    ACCESS read-only
    STATUS mandatory
    DESCRIPTION
        "Current count, from CMTS initialization, of contention
         mini-slots utilized on the upstream logical channel.  For
         contention regions, utilized mini-slots are those in which
         the CMTS correctly received an upstream burst from any CM
         on the upstream logical channel.  This is the 64-bit
         version of docsIfCmtsUpChnlCtrUsedCntnMslots and will not
         be accessible to SNMPv1 managers.
         Support for this object is mandatory.
         Discontinuities in the value of this counter can occur
         at reinitialization of the managed system, and at other
         times as indicated by the value of
         ifCounterDiscontinuityTime for the associated ifIndex."
    ::= { docsIfCmtsUpChannelCounterEntry 9 }

docsIfCmtsUpChnlCtrCollCntnMslots OBJECT-TYPE
    SYNTAX Counter
--  Units
--    mini-slots
    ACCESS read-only
    STATUS mandatory
    DESCRIPTION
        "Current count, from CMTS initialization, of contention
         mini-slots subjected to collisions on the upstream logical
         channel.  For contention regions, these are the mini-slots
         applicable to bursts that the CMTS detected but could not
         correctly receive.  This is the 32-bit version of
         docsIfCmtsUpChnlCtrExtCollCntnMslots and is included for
         back compatibility with SNMPv1 managers.
         Discontinuities in the value of this counter can occur
         at reinitialization of the managed system, and at other
         times as indicated by the value of
         ifCounterDiscontinuityTime for the associated ifIndex."
    ::= { docsIfCmtsUpChannelCounterEntry 10 }

docsIfCmtsUpChnlCtrTotalCntnReqMslots OBJECT-TYPE
    SYNTAX Counter
--  Units
--    mini-slots
    ACCESS read-only
    STATUS mandatory
    DESCRIPTION
        "Current count, from CMTS initialization, of contention
         request mini-slots defined for this upstream logical
         channel.  This count includes all mini-slots for IUC1
         assigned to a broadcast or multicast SID on the logical
         channel.  This is the 32-bit version of
         docsIfCmtsUpChnlCtrExtTotalCntnReqMslots and is included
         for back compatibility with SNMPv1 managers.
         Discontinuities in the value of this counter can occur
         at reinitialization of the managed system, and at other
         times as indicated by the value of
         ifCounterDiscontinuityTime for the associated ifIndex."
    ::= { docsIfCmtsUpChannelCounterEntry 11 }

docsIfCmtsUpChnlCtrUsedCntnReqMslots OBJECT-TYPE
    SYNTAX Counter
--  Units
--    mini-slots
    ACCESS read-only
    STATUS mandatory
    DESCRIPTION
        "Current count, from CMTS initialization, of contention
         request mini-slots utilized on this upstream logical
         channel.  This count includes all contention mini-slots for
         IUC1 applicable to bursts that the CMTS correctly
         received.  This is the 32-bit version of
         docsIfCmtsUpChnlCtrExtUsedCntnReqMslots and is included
         for back compatibility with SNMPv1 managers.
         Discontinuities in the value of this counter can occur
         at reinitialization of the managed system, and at other
         times as indicated by the value of
         ifCounterDiscontinuityTime for the associated ifIndex."
    ::= { docsIfCmtsUpChannelCounterEntry 12 }

docsIfCmtsUpChnlCtrCollCntnReqMslots OBJECT-TYPE
    SYNTAX Counter
--  Units
--    mini-slots
    ACCESS read-only
    STATUS mandatory
    DESCRIPTION
        "Current count, from CMTS initialization, of contention
         request mini-slots subjected to collisions on this upstream
         logical channel.  This includes all contention mini-slots
         for IUC1 applicable to bursts that the CMTS detected but
         could not correctly receive.  This is the 32-bit version of
         docsIfCmtsUpChnlCtrExtCollCntnReqMslots and is included
         for back compatibility with SNMPv1 managers.
         Discontinuities in the value of this counter can occur
         at reinitialization of the managed system, and at other
         times as indicated by the value of
         ifCounterDiscontinuityTime for the associated ifIndex."
    ::= { docsIfCmtsUpChannelCounterEntry 13 }

docsIfCmtsUpChnlCtrTotalCntnReqDataMslots OBJECT-TYPE
    SYNTAX Counter
--  Units
--    mini-slots
    ACCESS read-only
    STATUS mandatory
    DESCRIPTION
        "Current count, from CMTS initialization, of contention
         request data mini-slots defined for this upstream logical
         channel.  This count includes all mini-slots for IUC2
         assigned to a broadcast or multicast SID on the logical
         channel.  This is the 32-bit version of
         docsIfCmtsUpChnlCtrExtTotalCntnReqDataMslots and is
         included for back compatibility with SNMPv1 managers.
         Discontinuities in the value of this counter can occur
         at reinitialization of the managed system, and at other
         times as indicated by the value of
         ifCounterDiscontinuityTime for the associated ifIndex."
    ::= { docsIfCmtsUpChannelCounterEntry 14 }

docsIfCmtsUpChnlCtrUsedCntnReqDataMslots OBJECT-TYPE
    SYNTAX Counter
--  Units
--    mini-slots
    ACCESS read-only
    STATUS mandatory
    DESCRIPTION
        "Current count, from CMTS initialization, of contention
         request data mini-slots utilized on this upstream logical
         channel.  This includes all contention mini-slots for IUC2
         applicable to bursts that the CMTS correctly received.
         This is the 32-bit version of
         docsIfCmtsUpChnlCtrExtUsedCntnReqDataMslots and is
         included for back compatibility with SNMPv1 managers.
         Discontinuities in the value of this counter can occur
         at reinitialization of the managed system, and at other
         times as indicated by the value of
         ifCounterDiscontinuityTime for the associated ifIndex."
    ::= { docsIfCmtsUpChannelCounterEntry 15 }

docsIfCmtsUpChnlCtrCollCntnReqDataMslots OBJECT-TYPE
    SYNTAX Counter
--  Units
--    mini-slots
    ACCESS read-only
    STATUS mandatory
    DESCRIPTION
        "Current count, from CMTS initialization, of contention
         request data mini-slots subjected to collisions on this
         upstream logical channel.  This includes all contention
         mini-slots for IUC2 applicable to bursts that the CMTS
         detected, but could not correctly receive.  This is the
         32-bit version of
         docsIfCmtsUpChnlCtrExtCollCntnReqDataMslots and is
         included for back compatibility with SNMPv1 managers.
         Discontinuities in the value of this counter can occur
         at reinitialization of the managed system, and at other
         times as indicated by the value of
         ifCounterDiscontinuityTime for the associated ifIndex."
    ::= { docsIfCmtsUpChannelCounterEntry 16 }

docsIfCmtsUpChnlCtrTotalCntnInitMaintMslots OBJECT-TYPE
    SYNTAX Counter
--  Units
--    mini-slots
    ACCESS read-only
    STATUS mandatory
    DESCRIPTION
        "Current count, from CMTS initialization, of contention
         initial maintenance mini-slots defined for this upstream
         logical channel.  This includes all mini-slots for IUC3
         assigned to a broadcast or multicast SID on the logical
         channel.  This is the 32-bit version of
         docsIfCmtsUpChnlCtrExtTotalCntnInitMaintMslots
         and is included for back compatibility with SNMPv1
         managers.
         Discontinuities in the value of this counter can occur
         at reinitialization of the managed system, and at other
         times as indicated by the value of
         ifCounterDiscontinuityTime for the associated ifIndex."
    ::= { docsIfCmtsUpChannelCounterEntry 17 }

docsIfCmtsUpChnlCtrUsedCntnInitMaintMslots OBJECT-TYPE
    SYNTAX Counter
    ACCESS read-only
    STATUS mandatory
    DESCRIPTION
        "Current count, from CMTS initialization, of contention
         initial maintenance mini-slots utilized on this upstream
         logical channel.  This includes all contention mini-slots
         for IUC3 applicable to bursts that the CMTS correctly
         received.  This is the 32-bit version of
         docsIfCmtsUpChnlCtrExtUsedCntnInitMaintMslots
         and is included for back compatibility with SNMPv1
         managers.
         Discontinuities in the value of this counter can occur
         at reinitialization of the managed system, and at other
         times as indicated by the value of
         ifCounterDiscontinuityTime for the associated ifIndex."
    ::= { docsIfCmtsUpChannelCounterEntry 18 }

docsIfCmtsUpChnlCtrCollCntnInitMaintMslots OBJECT-TYPE
    SYNTAX Counter
--  Units
--    mini-slots
    ACCESS read-only
    STATUS mandatory
    DESCRIPTION
        "Current count, from CMTS initialization, of contention
         initial maintenance mini-slots subjected to collisions on
         this upstream logical channel.  This includes all
         contention mini-slots for IUC3 applicable to bursts that
         the CMTS detected, but could not correctly receive.
         This is the 32-bit version of
         docsIfCmtsUpChnlCtrExtCollCntnInitMaintMslots
         and is included for back compatibility with SNMPv1
         managers.
         Discontinuities in the value of this counter can occur
         at reinitialization of the managed system, and at other
         times as indicated by the value of
         ifCounterDiscontinuityTime for the associated ifIndex."
    ::= { docsIfCmtsUpChannelCounterEntry 19 }

docsIfCmtsUpChnlCtrExtCollCntnMslots OBJECT-TYPE
    SYNTAX --?? syntax is not convertable to SMIv1
           Counter
--  Units
--    mini-slots
    ACCESS read-only
    STATUS mandatory
    DESCRIPTION
        "Current count, from CMTS initialization, of collision
         contention mini-slots on the upstream logical channel.
         For contention regions, these are the mini-slots applicable
         to bursts that the CMTS detected, but could not correctly
         receive.  This is the 64-bit version of
         docsIfCmtsUpChnlCtrCollCntnMslots and will not be
         accessible to SNMPv1 managers.
         Discontinuities in the value of this counter can occur
         at reinitialization of the managed system, and at other
         times as indicated by the value of
         ifCounterDiscontinuityTime for the associated ifIndex."
    ::= { docsIfCmtsUpChannelCounterEntry 20 }

docsIfCmtsUpChnlCtrExtTotalCntnReqMslots OBJECT-TYPE
    SYNTAX --?? syntax is not convertable to SMIv1
           Counter
--  Units
--    mini-slots
    ACCESS read-only
    STATUS mandatory
    DESCRIPTION
        "Current count, from CMTS initialization, of contention
         request mini-slots defined for this upstream logical
         channel.  This count includes all mini-slots for IUC1
         assigned to a broadcast or multicast SID on the logical
         channel.  This is the 64-bit version of
         docsIfCmtsUpChnlCtrTotalCntnReqMslots and will not be
         accessible to SNMPv1 managers.
         Discontinuities in the value of this counter can occur
         at reinitialization of the managed system, and at other
         times as indicated by the value of
         ifCounterDiscontinuityTime for the associated ifIndex."
    ::= { docsIfCmtsUpChannelCounterEntry 21 }

docsIfCmtsUpChnlCtrExtUsedCntnReqMslots OBJECT-TYPE
    SYNTAX --?? syntax is not convertable to SMIv1
           Counter
--  Units
--    mini-slots
    ACCESS read-only
    STATUS mandatory
    DESCRIPTION
        "Current count, from CMTS initialization, of contention
         request mini-slots utilized on this upstream logical
         channel.  This count includes all contention mini-slots for
         IUC1 applicable to bursts that the CMTS correctly
         received.  This is the 64-bit version of
         docsIfCmtsUpChnlCtrUsedCntnReqMslots and will not be
         accessible to SNMPv1 managers.
         Discontinuities in the value of this counter can occur
         at reinitialization of the managed system, and at other
         times as indicated by the value of
         ifCounterDiscontinuityTime for the associated ifIndex."
    ::= { docsIfCmtsUpChannelCounterEntry 22 }

docsIfCmtsUpChnlCtrExtCollCntnReqMslots OBJECT-TYPE
    SYNTAX --?? syntax is not convertable to SMIv1
           Counter
--  Units
--    mini-slots
    ACCESS read-only
    STATUS mandatory
    DESCRIPTION
        "Current count, from CMTS initialization, of contention
         request mini-slots subjected to collisions on this upstream
         logical channel.  This includes all contention mini-slots
         for IUC1 applicable to bursts that the CMTS detected,
         but could not correctly receive.  This is the 64-bit
         version of docsIfCmtsUpChnlCtrCollCntnReqMslots and will
         not be accessible to SNMPv1 managers.
         Discontinuities in the value of this counter can occur
         at reinitialization of the managed system, and at other
         times as indicated by the value of
         ifCounterDiscontinuityTime for the associated ifIndex."
    ::= { docsIfCmtsUpChannelCounterEntry 23 }

docsIfCmtsUpChnlCtrExtTotalCntnReqDataMslots OBJECT-TYPE
    SYNTAX --?? syntax is not convertable to SMIv1
           Counter
--  Units
--    mini-slots
    ACCESS read-only
    STATUS mandatory
    DESCRIPTION
        "Current count, from CMTS initialization, of contention
         request data mini-slots defined for this upstream logical
         channel.  This count includes all mini-slots for IUC2
         assigned to a broadcast or multicast SID on the logical
         channel.  This is the 64-bit version of
         docsIfCmtsUpChnlCtrTotalCntnReqDataMslots and will not be
         accessible to SNMPv1 managers.
         Discontinuities in the value of this counter can occur
         at reinitialization of the managed system, and at other
         times as indicated by the value of
         ifCounterDiscontinuityTime for the associated ifIndex."
    ::= { docsIfCmtsUpChannelCounterEntry 24 }

docsIfCmtsUpChnlCtrExtUsedCntnReqDataMslots OBJECT-TYPE
    SYNTAX --?? syntax is not convertable to SMIv1
           Counter
--  Units
--    mini-slots
    ACCESS read-only
    STATUS mandatory
    DESCRIPTION
        "Current count, from CMTS initialization, of contention
         request data mini-slots utilized on this upstream logical
         channel.  This includes all contention mini-slots for IUC2
         applicable to bursts that the CMTS correctly received.
         This is the 64-bit version of
         docsIfCmtsUpChnlCtrUsedCntnReqDataMslots and will not be
         accessible to SNMPv1 managers.
         Discontinuities in the value of this counter can occur
         at reinitialization of the managed system, and at other
         times as indicated by the value of
         ifCounterDiscontinuityTime for the associated ifIndex."
    ::= { docsIfCmtsUpChannelCounterEntry 25 }

docsIfCmtsUpChnlCtrExtCollCntnReqDataMslots OBJECT-TYPE
    SYNTAX --?? syntax is not convertable to SMIv1
           Counter
--  Units
--    mini-slots
    ACCESS read-only
    STATUS mandatory
    DESCRIPTION
        "Current count, from CMTS initialization, of contention
         request data mini-slots subjected to collisions on this
         upstream logical channel.  This includes all contention
         mini-slots for IUC2 applicable to bursts that the CMTS
         detected, but could not correctly receive.  This is the
         64-bit version of
         docsIfCmtsUpChnlCtrCollCntnReqDataMslots
         and will not be accessible to SNMPv1 managers.
         Discontinuities in the value of this counter can occur
         at reinitialization of the managed system, and at other
         times as indicated by the value of
         ifCounterDiscontinuityTime for the associated ifIndex."
    ::= { docsIfCmtsUpChannelCounterEntry 26 }

docsIfCmtsUpChnlCtrExtTotalCntnInitMaintMslots OBJECT-TYPE
    SYNTAX --?? syntax is not convertable to SMIv1
           Counter
--  Units
--    mini-slots
    ACCESS read-only
    STATUS mandatory
    DESCRIPTION
        "Current count, from CMTS initialization, of initial
         maintenance mini-slots defined for this upstream logical
         channel.  This count includes all mini-slots for IUC3
         assigned to a broadcast or multicast SID on the logical
         channel.  This is the 64-bit version of
         docsIfCmtsUpChnlCtrTotalCntnInitMaintMslots
         and will not be accessible to SNMPv1 managers.
         Discontinuities in the value of this counter can occur
         at reinitialization of the managed system, and at other
         times as indicated by the value of
         ifCounterDiscontinuityTime for the associated ifIndex."
    ::= { docsIfCmtsUpChannelCounterEntry 27 }

docsIfCmtsUpChnlCtrExtUsedCntnInitMaintMslots OBJECT-TYPE
    SYNTAX --?? syntax is not convertable to SMIv1
           Counter
--  Units
--    mini-slots
    ACCESS read-only
    STATUS mandatory
    DESCRIPTION
        "Current count, from CMTS initialization, of initial
         maintenance mini-slots utilized on this upstream logical
         channel.  This includes all contention mini-slots for IUC3
         applicable to bursts that the CMTS correctly received.
         This is the 64-bit version of
         docsIfCmtsUpChnlCtrUsedCntnInitMaintMslots
         and will not be accessible to SNMPv1 managers.
         Discontinuities in the value of this counter can occur
         at reinitialization of the managed system, and at other
         times as indicated by the value of
         ifCounterDiscontinuityTime for the associated ifIndex."
    ::= { docsIfCmtsUpChannelCounterEntry 28 }

docsIfCmtsUpChnlCtrExtCollCntnInitMaintMslots OBJECT-TYPE
    SYNTAX --?? syntax is not convertable to SMIv1
           Counter
--  Units
--    mini-slots
    ACCESS read-only
    STATUS mandatory
    DESCRIPTION
        "Current count, from CMTS initialization, of contention
         initial maintenance mini-slots subjected to collisions on
         this upstream logical channel.  This includes all
         contention mini-slots for IUC3 applicable to bursts that
         the CMTS detected, but could not correctly receive.
         This is the 64-bit version of
         docsIfCmtsUpChnlCtrCollCntnInitMaintMslots and will not
         be accessible to SNMPv1 managers.
         Discontinuities in the value of this counter can occur
         at reinitialization of the managed system, and at other
         times as indicated by the value of
         ifCounterDiscontinuityTime for the associated ifIndex."
    ::= { docsIfCmtsUpChannelCounterEntry 29 }

docsIfBasicGroup OBJECT IDENTIFIER ::= { docsIfGroups 1 }
-- OBJECT-GROUP
--  Status
--    deprecated
--  Descr
--    Group of objects implemented in both cable modems and
--     cable modem termination systems.
--  objects
--    docsIfDownChannelId, docsIfDownChannelFrequency, 
--    docsIfDownChannelWidth, docsIfDownChannelModulation, 
--    docsIfDownChannelInterleave, docsIfDownChannelPower, 
--    docsIfUpChannelId, docsIfUpChannelFrequency, 
--    docsIfUpChannelWidth, docsIfUpChannelModulationProfile, 
--    docsIfUpChannelSlotSize, docsIfUpChannelTxTimingOffset, 
--    docsIfUpChannelRangingBackoffStart, 
--    docsIfUpChannelRangingBackoffEnd, 
--    docsIfUpChannelTxBackoffStart, docsIfUpChannelTxBackoffEnd, 
--    docsIfQosProfPriority, docsIfQosProfMaxUpBandwidth, 
--    docsIfQosProfGuarUpBandwidth, docsIfQosProfMaxDownBandwidth, 
--    docsIfQosProfMaxTxBurst, docsIfQosProfBaselinePrivacy, 
--    docsIfQosProfStatus, docsIfSigQIncludesContention, 
--    docsIfSigQUnerroreds, docsIfSigQCorrecteds, 
--    docsIfSigQUncorrectables, docsIfSigQSignalNoise, 
--    docsIfSigQMicroreflections, docsIfSigQEqualizationData

docsIfCmGroup OBJECT IDENTIFIER ::= { docsIfGroups 2 }
-- OBJECT-GROUP
--  Status
--    deprecated
--  Descr
--    Group of objects implemented in cable modems.
--  objects
--    docsIfCmCmtsAddress, docsIfCmCapabilities, 
--    docsIfCmRangingTimeout, docsIfCmStatusValue, 
--    docsIfCmStatusCode, docsIfCmStatusTxPower, 
--    docsIfCmStatusResets, docsIfCmStatusLostSyncs, 
--    docsIfCmStatusInvalidMaps, docsIfCmStatusInvalidUcds, 
--    docsIfCmStatusInvalidRangingResponses, 
--    docsIfCmStatusInvalidRegistrationResponses, 
--    docsIfCmStatusT1Timeouts, docsIfCmStatusT2Timeouts, 
--    docsIfCmStatusT3Timeouts, docsIfCmStatusT4Timeouts, 
--    docsIfCmStatusRangingAborteds, docsIfCmServiceQosProfile, 
--    docsIfCmServiceTxSlotsImmed, docsIfCmServiceTxSlotsDed, 
--    docsIfCmServiceTxRetries, docsIfCmServiceTxExceededs, 
--    docsIfCmServiceRqRetries, docsIfCmServiceRqExceededs

docsIfCmtsGroup OBJECT IDENTIFIER ::= { docsIfGroups 3 }
-- OBJECT-GROUP
--  Status
--    deprecated
--  Descr
--    Group of objects implemented in Cable Modem Termination
--     Systems.
--  objects
--    docsIfCmtsCapabilities, docsIfCmtsSyncInterval, 
--    docsIfCmtsUcdInterval, docsIfCmtsMaxServiceIds, 
--    docsIfCmtsInvitedRangingAttempts, docsIfCmtsInsertInterval, 
--    docsIfCmtsStatusInvalidRangeReqs, 
--    docsIfCmtsStatusRangingAborteds, 
--    docsIfCmtsStatusInvalidRegReqs, docsIfCmtsStatusFailedRegReqs, 
--    docsIfCmtsStatusInvalidDataReqs, docsIfCmtsStatusT5Timeouts, 
--    docsIfCmtsCmStatusMacAddress, docsIfCmtsCmStatusIpAddress, 
--    docsIfCmtsCmStatusDownChannelIfIndex, 
--    docsIfCmtsCmStatusUpChannelIfIndex, docsIfCmtsCmStatusRxPower, 
--    docsIfCmtsCmStatusTimingOffset, 
--    docsIfCmtsCmStatusEqualizationData, docsIfCmtsCmStatusValue, 
--    docsIfCmtsCmStatusUnerroreds, docsIfCmtsCmStatusCorrecteds, 
--    docsIfCmtsCmStatusUncorrectables, 
--    docsIfCmtsCmStatusSignalNoise, 
--    docsIfCmtsCmStatusMicroreflections, 
--    docsIfCmtsServiceCmStatusIndex, docsIfCmtsServiceAdminStatus, 
--    docsIfCmtsServiceQosProfile, docsIfCmtsServiceCreateTime, 
--    docsIfCmtsServiceInOctets, docsIfCmtsServiceInPackets, 
--    docsIfCmtsModType, docsIfCmtsModControl, 
--    docsIfCmtsModPreambleLen, docsIfCmtsModDifferentialEncoding, 
--    docsIfCmtsModFECErrorCorrection, 
--    docsIfCmtsModFECCodewordLength, docsIfCmtsModScramblerSeed, 
--    docsIfCmtsModMaxBurstSize, docsIfCmtsModGuardTimeSize, 
--    docsIfCmtsModLastCodewordShortened, docsIfCmtsModScrambler, 
--    docsIfCmtsQosProfilePermissions, docsIfCmtsCmPtr

docsIfObsoleteGroup OBJECT IDENTIFIER ::= { docsIfGroups 4 }
-- OBJECT-GROUP
--  Status
--    obsolete
--  Descr
--    Group of objects obsoleted.
--  objects
--    docsIfCmRangingRespTimeout, docsIfCmtsInsertionInterval

docsIfBasicGroupV2 OBJECT IDENTIFIER ::= { docsIfGroups 5 }
-- OBJECT-GROUP
--  Status
--    mandatory
--  Descr
--    Group of objects implemented in both cable modems and
--     cable modem termination systems.
--  objects
--    docsIfDownChannelId, docsIfDownChannelFrequency, 
--    docsIfDownChannelWidth, docsIfDownChannelModulation, 
--    docsIfDownChannelInterleave, docsIfDownChannelPower, 
--    docsIfDownChannelAnnex, docsIfUpChannelId, 
--    docsIfUpChannelFrequency, docsIfUpChannelWidth, 
--    docsIfUpChannelModulationProfile, docsIfUpChannelSlotSize, 
--    docsIfUpChannelTxTimingOffset, 
--    docsIfUpChannelRangingBackoffStart, 
--    docsIfUpChannelRangingBackoffEnd, 
--    docsIfUpChannelTxBackoffStart, docsIfUpChannelTxBackoffEnd, 
--    docsIfUpChannelScdmaActiveCodes, 
--    docsIfUpChannelScdmaCodesPerSlot, 
--    docsIfUpChannelScdmaFrameSize, 
--    docsIfUpChannelScdmaHoppingSeed, docsIfUpChannelType, 
--    docsIfUpChannelCloneFrom, docsIfUpChannelUpdate, 
--    docsIfUpChannelStatus, docsIfUpChannelPreEqEnable, 
--    docsIfQosProfPriority, docsIfQosProfMaxUpBandwidth, 
--    docsIfQosProfGuarUpBandwidth, docsIfQosProfMaxDownBandwidth, 
--    docsIfQosProfBaselinePrivacy, docsIfQosProfStatus, 
--    docsIfQosProfMaxTransmitBurst, docsIfSigQIncludesContention, 
--    docsIfSigQUnerroreds, docsIfSigQCorrecteds, 
--    docsIfSigQUncorrectables, docsIfSigQSignalNoise, 
--    docsIfSigQMicroreflections, docsIfSigQExtUnerroreds, 
--    docsIfSigQExtCorrecteds, docsIfSigQExtUncorrectables, 
--    docsIfDocsisBaseCapability

docsIfCmGroupV2 OBJECT IDENTIFIER ::= { docsIfGroups 6 }
-- OBJECT-GROUP
--  Status
--    mandatory
--  Descr
--    Group of objects implemented in cable modems.
--  objects
--    docsIfCmCmtsAddress, docsIfCmCapabilities, 
--    docsIfCmRangingTimeout, docsIfCmStatusValue, 
--    docsIfCmStatusCode, docsIfCmStatusTxPower, 
--    docsIfCmStatusResets, docsIfCmStatusLostSyncs, 
--    docsIfCmStatusInvalidMaps, docsIfCmStatusInvalidUcds, 
--    docsIfCmStatusInvalidRangingResponses, 
--    docsIfCmStatusInvalidRegistrationResponses, 
--    docsIfCmStatusT1Timeouts, docsIfCmStatusT2Timeouts, 
--    docsIfCmStatusT3Timeouts, docsIfCmStatusT4Timeouts, 
--    docsIfCmStatusRangingAborteds, docsIfCmStatusDocsisOperMode, 
--    docsIfCmStatusModulationType, docsIfCmStatusEqualizationData, 
--    docsIfCmStatusUCCs, docsIfCmStatusUCCFails, 
--    docsIfCmServiceQosProfile, docsIfCmServiceTxSlotsImmed, 
--    docsIfCmServiceTxSlotsDed, docsIfCmServiceTxRetries, 
--    docsIfCmServiceTxExceededs, docsIfCmServiceRqRetries, 
--    docsIfCmServiceRqExceededs, docsIfCmServiceExtTxSlotsImmed, 
--    docsIfCmServiceExtTxSlotsDed, docsIfSigQEqualizationData

docsIfCmtsGroupV2 OBJECT IDENTIFIER ::= { docsIfGroups 7 }
-- OBJECT-GROUP
--  Status
--    mandatory
--  Descr
--    Group of objects implemented in Cable Modem Termination
--     Systems.
--  objects
--    docsIfCmtsCapabilities, docsIfCmtsSyncInterval, 
--    docsIfCmtsUcdInterval, docsIfCmtsMaxServiceIds, 
--    docsIfCmtsInvitedRangingAttempts, docsIfCmtsInsertInterval, 
--    docsIfCmtsMacStorageType, docsIfCmtsStatusInvalidRangeReqs, 
--    docsIfCmtsStatusRangingAborteds, 
--    docsIfCmtsStatusInvalidRegReqs, docsIfCmtsStatusFailedRegReqs, 
--    docsIfCmtsStatusInvalidDataReqs, docsIfCmtsStatusT5Timeouts, 
--    docsIfCmtsCmStatusMacAddress, 
--    docsIfCmtsCmStatusDownChannelIfIndex, 
--    docsIfCmtsCmStatusUpChannelIfIndex, docsIfCmtsCmStatusRxPower, 
--    docsIfCmtsCmStatusTimingOffset, 
--    docsIfCmtsCmStatusEqualizationData, docsIfCmtsCmStatusValue, 
--    docsIfCmtsCmStatusUnerroreds, docsIfCmtsCmStatusCorrecteds, 
--    docsIfCmtsCmStatusUncorrectables, 
--    docsIfCmtsCmStatusSignalNoise, 
--    docsIfCmtsCmStatusMicroreflections, 
--    docsIfCmtsCmStatusExtUnerroreds, 
--    docsIfCmtsCmStatusExtCorrecteds, 
--    docsIfCmtsCmStatusExtUncorrectables, 
--    docsIfCmtsCmStatusDocsisRegMode, 
--    docsIfCmtsCmStatusModulationType, 
--    docsIfCmtsCmStatusInetAddressType, 
--    docsIfCmtsCmStatusInetAddress, 
--    docsIfCmtsCmStatusValueLastUpdate, 
--    docsIfCmtsCmStatusHighResolutionTimingOffset, 
--    docsIfCmtsServiceAdminStatus, docsIfCmtsServiceQosProfile, 
--    docsIfCmtsServiceCreateTime, docsIfCmtsServiceInOctets, 
--    docsIfCmtsServiceInPackets, docsIfCmtsServiceNewCmStatusIndex, 
--    docsIfCmtsModType, docsIfCmtsModControl, 
--    docsIfCmtsModPreambleLen, docsIfCmtsModDifferentialEncoding, 
--    docsIfCmtsModFECErrorCorrection, 
--    docsIfCmtsModFECCodewordLength, docsIfCmtsModScramblerSeed, 
--    docsIfCmtsModMaxBurstSize, docsIfCmtsModGuardTimeSize, 
--    docsIfCmtsModLastCodewordShortened, docsIfCmtsModScrambler, 
--    docsIfCmtsModByteInterleaverDepth, 
--    docsIfCmtsModByteInterleaverBlockSize, 
--    docsIfCmtsModPreambleType, docsIfCmtsModTcmErrorCorrectionOn, 
--    docsIfCmtsModScdmaInterleaverStepSize, 
--    docsIfCmtsModScdmaSpreaderEnable, 
--    docsIfCmtsModScdmaSubframeCodes, docsIfCmtsModChannelType, 
--    docsIfCmtsModStorageType, docsIfCmtsQosProfilePermissions, 
--    docsIfCmtsCmPtr, docsIfCmtsChannelUtilizationInterval, 
--    docsIfCmtsChannelUtUtilization, docsIfCmtsDownChnlCtrId, 
--    docsIfCmtsDownChnlCtrTotalBytes, 
--    docsIfCmtsDownChnlCtrUsedBytes, 
--    docsIfCmtsDownChnlCtrExtTotalBytes, 
--    docsIfCmtsDownChnlCtrExtUsedBytes, docsIfCmtsUpChnlCtrId, 
--    docsIfCmtsUpChnlCtrTotalMslots, 
--    docsIfCmtsUpChnlCtrUcastGrantedMslots, 
--    docsIfCmtsUpChnlCtrTotalCntnMslots, 
--    docsIfCmtsUpChnlCtrUsedCntnMslots, 
--    docsIfCmtsUpChnlCtrExtTotalMslots, 
--    docsIfCmtsUpChnlCtrExtUcastGrantedMslots, 
--    docsIfCmtsUpChnlCtrExtTotalCntnMslots, 
--    docsIfCmtsUpChnlCtrExtUsedCntnMslots, 
--    docsIfCmtsUpChnlCtrCollCntnMslots, 
--    docsIfCmtsUpChnlCtrTotalCntnReqMslots, 
--    docsIfCmtsUpChnlCtrUsedCntnReqMslots, 
--    docsIfCmtsUpChnlCtrCollCntnReqMslots, 
--    docsIfCmtsUpChnlCtrTotalCntnReqDataMslots, 
--    docsIfCmtsUpChnlCtrUsedCntnReqDataMslots, 
--    docsIfCmtsUpChnlCtrCollCntnReqDataMslots, 
--    docsIfCmtsUpChnlCtrTotalCntnInitMaintMslots, 
--    docsIfCmtsUpChnlCtrUsedCntnInitMaintMslots, 
--    docsIfCmtsUpChnlCtrCollCntnInitMaintMslots, 
--    docsIfCmtsUpChnlCtrExtCollCntnMslots, 
--    docsIfCmtsUpChnlCtrExtTotalCntnReqMslots, 
--    docsIfCmtsUpChnlCtrExtUsedCntnReqMslots, 
--    docsIfCmtsUpChnlCtrExtCollCntnReqMslots, 
--    docsIfCmtsUpChnlCtrExtTotalCntnReqDataMslots, 
--    docsIfCmtsUpChnlCtrExtUsedCntnReqDataMslots, 
--    docsIfCmtsUpChnlCtrExtCollCntnReqDataMslots, 
--    docsIfCmtsUpChnlCtrExtTotalCntnInitMaintMslots, 
--    docsIfCmtsUpChnlCtrExtUsedCntnInitMaintMslots, 
--    docsIfCmtsUpChnlCtrExtCollCntnInitMaintMslots, 
--    docsIfDownChannelStorageType, docsIfQosProfStorageType

docsIfBasicCompliance OBJECT IDENTIFIER ::= { docsIfCompliances 1 }
-- MODULE-COMPLIANCE
--  Status
--    deprecated
--  Descr
--    The compliance statement for devices that implement
--     DOCSIS 1.x compliant Radio Frequency Interfaces.
--  Module
--    >>current<<
--   MandGroup
--    docsIfBasicGroup
--   OptGroup
--    docsIfCmGroup
--   OptGroup
--    docsIfCmtsGroup
--   ObjVar
--    docsIfDownChannelFrequency
--   ObjVar
--    docsIfDownChannelWidth
--   ObjVar
--    docsIfDownChannelModulation
--   ObjVar
--    docsIfDownChannelInterleave
--   ObjVar
--    docsIfDownChannelPower
--   ObjVar
--    docsIfUpChannelFrequency
--   ObjVar
--    docsIfUpChannelWidth
--   ObjVar
--    docsIfUpChannelModulationProfile
--   ObjVar
--    docsIfUpChannelSlotSize
--   ObjVar
--    docsIfUpChannelRangingBackoffStart
--   ObjVar
--    docsIfUpChannelRangingBackoffEnd
--   ObjVar
--    docsIfUpChannelTxBackoffStart
--   ObjVar
--    docsIfUpChannelTxBackoffEnd
--   ObjVar
--    docsIfQosProfPriority
--   ObjVar
--    docsIfQosProfMaxUpBandwidth
--   ObjVar
--    docsIfQosProfGuarUpBandwidth
--   ObjVar
--    docsIfQosProfMaxDownBandwidth
--   ObjVar
--    docsIfQosProfMaxTxBurst
--   ObjVar
--    docsIfQosProfBaselinePrivacy
--   ObjVar
--    docsIfQosProfStatus
--   ObjVar
--    docsIfCmtsServiceAdminStatus
--   ObjVar
--    docsIfCmtsSyncInterval
--   ObjVar
--    docsIfCmtsUcdInterval
--   ObjVar
--    docsIfCmtsInsertInterval
--   ObjVar
--    docsIfCmtsInvitedRangingAttempts
--   ObjVar
--    docsIfCmtsQosProfilePermissions
--   ObjVar
--    docsIfCmtsModType
--   ObjVar
--    docsIfCmtsModPreambleLen
--   ObjVar
--    docsIfCmtsModFECErrorCorrection

docsIfBasicComplianceV2 OBJECT IDENTIFIER ::= { docsIfCompliances 2 }
-- MODULE-COMPLIANCE
--  Status
--    mandatory
--  Descr
--    The compliance statement for devices that implement
--     DOCSIS 2.0 Radio Frequency Interfaces.
--  Module
--    >>current<<
--   MandGroup
--    docsIfBasicGroupV2
--   OptGroup
--    docsIfCmGroupV2
--   OptGroup
--    docsIfCmtsGroupV2
--   ObjVar
--    docsIfDownChannelFrequency
--   ObjVar
--    docsIfDownChannelWidth
--   ObjVar
--    docsIfDownChannelModulation
--   ObjVar
--    docsIfDownChannelInterleave
--   ObjVar
--    docsIfDownChannelPower
--   ObjVar
--    docsIfUpChannelFrequency
--   ObjVar
--    docsIfUpChannelWidth
--   ObjVar
--    docsIfUpChannelModulationProfile
--   ObjVar
--    docsIfUpChannelSlotSize
--   ObjVar
--    docsIfUpChannelRangingBackoffStart
--   ObjVar
--    docsIfUpChannelRangingBackoffEnd
--   ObjVar
--    docsIfUpChannelTxBackoffStart
--   ObjVar
--    docsIfUpChannelTxBackoffEnd
--   ObjVar
--    docsIfUpChannelScdmaActiveCodes
--   ObjVar
--    docsIfUpChannelScdmaCodesPerSlot
--   ObjVar
--    docsIfUpChannelScdmaFrameSize
--   ObjVar
--    docsIfUpChannelScdmaHoppingSeed
--   ObjVar
--    docsIfUpChannelCloneFrom
--   ObjVar
--    docsIfUpChannelUpdate
--   ObjVar
--    docsIfUpChannelStatus
--   ObjVar
--    docsIfUpChannelPreEqEnable
--   ObjVar
--    docsIfQosProfPriority
--   ObjVar
--    docsIfQosProfMaxUpBandwidth
--   ObjVar
--    docsIfQosProfGuarUpBandwidth
--   ObjVar
--    docsIfQosProfMaxDownBandwidth
--   ObjVar
--    docsIfQosProfBaselinePrivacy
--   ObjVar
--    docsIfQosProfStatus
--   ObjVar
--    docsIfQosProfMaxTransmitBurst
--   ObjVar
--    docsIfCmRangingTimeout
--   ObjVar
--    docsIfCmStatusModulationType
--   ObjVar
--    docsIfCmtsServiceAdminStatus
--   ObjVar
--    docsIfCmtsSyncInterval
--   ObjVar
--    docsIfCmtsUcdInterval
--   ObjVar
--    docsIfCmtsInsertInterval
--   ObjVar
--    docsIfCmtsInvitedRangingAttempts
--   ObjVar
--    docsIfCmtsQosProfilePermissions
--   ObjVar
--    docsIfCmtsModType
--   ObjVar
--    docsIfCmtsCmStatusModulationType


END
