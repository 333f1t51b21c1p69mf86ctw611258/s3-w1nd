GWSNADSMIB DEFINITIONS ::= BEGIN

IMPORTS
        Counter, TimeTicks, Gauge, enterprises  FROM RFC1155-SMI
        DisplayString                           FROM RFC1213-MIB
        TRAP-TYPE                               FROM RFC-1215
        OBJECT-TYPE                             FROM RFC-1212;

novell          OBJECT IDENTIFIER   ::= { enterprises 922 }
gateways        OBJECT IDENTIFIER   ::= { novell        2 }
ngwsnads         OBJECT IDENTIFIER   ::= { gateways     42 }
ngwsnadsInfo     OBJECT IDENTIFIER   ::= { ngwsnads       1 }
ngwsnadsTrapInfo OBJECT IDENTIFIER   ::= { ngwsnads       2 }


-- ====================================== NGWSNADS Get/Set Variables =========
ngwsnadsGatewayName OBJECT-TYPE
       SYNTAX  DisplayString (SIZE (0..255))
       ACCESS  read-only
       STATUS  mandatory
       DESCRIPTION
       "The GroupWise SNADS Gateway name."
   ::= { ngwsnadsInfo 1 }

ngwsnadsUptime OBJECT-TYPE
       SYNTAX  TimeTicks
       ACCESS  read-only
       STATUS  mandatory
       DESCRIPTION
      "Uptime of the GroupWise SNADS Gateway."
   ::= { ngwsnadsInfo 2 }

ngwsnadsGroupWiseLink OBJECT-TYPE
       SYNTAX  DisplayString (SIZE (0..5))
       ACCESS  read-only
       STATUS  mandatory
       DESCRIPTION
      "GroupWise SNADS Gateway Link: UP or DOWN"
   ::= { ngwsnadsInfo 3 }

ngwsnadsFrgnLink OBJECT-TYPE
       SYNTAX  DisplayString (SIZE (0..5))
       ACCESS  read-only
       STATUS  mandatory
       DESCRIPTION
      "GroupWise SNADS Gateway Foreign Link: UP or DOWN"
   ::= { ngwsnadsInfo 4 }

ngwsnadsOutBytes OBJECT-TYPE
       SYNTAX  Counter
       ACCESS  read-only
       STATUS  mandatory
       DESCRIPTION
      "The number of message bytes sent to GroupWise SNADS."
   ::= { ngwsnadsInfo 5 }

ngwsnadsInBytes OBJECT-TYPE
       SYNTAX  Counter
       ACCESS  read-only
       STATUS  mandatory
       DESCRIPTION
      "The number of message bytes received from GroupWise SNADS."
   ::= { ngwsnadsInfo 6 }

ngwsnadsOutMsgs OBJECT-TYPE
       SYNTAX  Counter
       ACCESS  read-only
       STATUS  mandatory
       DESCRIPTION
      "The number of messages sent to GroupWise SNADS."
   ::= { ngwsnadsInfo 7 }

ngwsnadsInMsgs OBJECT-TYPE
       SYNTAX  Counter
       ACCESS  read-only
       STATUS  mandatory
       DESCRIPTION
      "The number of messages received from SNADS."
   ::= { ngwsnadsInfo 8 }

ngwsnadsOutStatuses OBJECT-TYPE
       SYNTAX  Counter
       ACCESS  read-only
       STATUS  mandatory
       DESCRIPTION
      "The number of statuses sent to SNADS."
   ::= { ngwsnadsInfo 9 }

ngwsnadsInStatuses OBJECT-TYPE
       SYNTAX  Counter
       ACCESS  read-only
       STATUS  mandatory
       DESCRIPTION
      "The number of statuses received from SNADS."
   ::= { ngwsnadsInfo 10 }

ngwsnadsOutErrors OBJECT-TYPE
       SYNTAX  Counter
       ACCESS  read-only
       STATUS  mandatory
       DESCRIPTION
      "The number of failed transfers to SNADS."
   ::= { ngwsnadsInfo 11 }

ngwsnadsInErrors OBJECT-TYPE
       SYNTAX  Counter
       ACCESS  read-only
       STATUS  mandatory
       DESCRIPTION
      "The number of failed transfers from SNADS."
   ::= { ngwsnadsInfo 12 }


-- ================================================== ngwsnadsTrapInfo ========
-- The ngwsnadsTrapInfo group
-- These objects are used only in traps produced by NGWSNADS

ngwsnadsTrapTime OBJECT-TYPE
                SYNTAX  INTEGER
                ACCESS  not-accessible
                STATUS  mandatory
                DESCRIPTION "The time the trap occurred. Seconds since Jan 1, 1970 (GMT)"
        ::= { ngwsnadsTrapInfo 1 }

-- ================================================== NGWSNADS Traps =========
ngwsnadsStartTrap TRAP-TYPE
                ENTERPRISE    ngwsnadsInfo
                VARIABLES     {ngwsnadsTrapTime, ngwsnadsGatewayName}
                DESCRIPTION   "GroupWise SNADS Gateway start."
                --NMS Trap annotation
                --#TYPE       "GroupWise SNADS Gateway start."
                --#SUMMARY    "GroupWise SNADS Gateway %s has started."
                --#ARGUMENTS  {1}
                --#SEVERITY   INFORMATIONAL
                --#TIMEINDEX  0
                --#HELP       "NGWALARM.HLP"
                --#HELPTAG    101
                --#STATE      OPERATIONAL
                ::= 1

ngwsnadsStopTrap TRAP-TYPE
                ENTERPRISE    ngwsnadsInfo
                VARIABLES     {ngwsnadsTrapTime, ngwsnadsGatewayName}
                DESCRIPTION   "GroupWise SNADS Gateway stop."
                --NMS Trap annotation
                --#TYPE       "GroupWise SNADS Gateway stop."
                --#SUMMARY    "GroupWise SNADS Gateway %s has stopped."
                --#ARGUMENTS  {1}
                --#SEVERITY   CRITICAL
                --#TIMEINDEX  0
                --#HELP       "NGWALARM.HLP"
                --#HELPTAG    102
                --#STATE      NONOPERATIONAL
                ::= 2

ngwsnadsRestartTrap TRAP-TYPE
                ENTERPRISE    ngwsnadsInfo
                VARIABLES     {ngwsnadsTrapTime, ngwsnadsGatewayName}
                DESCRIPTION   "GroupWise SNADS Gateway restart."
                --NMS Trap annotation
                --#TYPE       "GroupWise SNADS Gateway restart."
                --#SUMMARY    "GroupWise SNADS Gateway %s has been restarted."
                --#ARGUMENTS  {1}
                --#SEVERITY   INFORMATIONAL
                --#TIMEINDEX  0
                --#HELP       "NGWALARM.HLP"
                --#HELPTAG    503
                --#STATE      OPERATIONAL
                ::= 3

ngwsnadsGroupWiseLinkTrap TRAP-TYPE
                ENTERPRISE    ngwsnadsInfo
                VARIABLES     {ngwsnadsTrapTime, ngwsnadsGatewayName}
                DESCRIPTION   "GroupWise Link lost by GroupWise SNADS Gateway"
                --NMS Trap annotation
                --#TYPE       "GroupWise Link lost by GroupWise SNADS Gateway"
                --#SUMMARY    "GroupWise SNADS Gateway %s has lost its GroupWise Link"
                --#ARGUMENTS  {1}
                --#SEVERITY   INFORMATIONAL
                --#TIMEINDEX  0
                --#HELP       "NGWALARM.HLP"
                --#HELPTAG    504
                --#STATE      OPERATIONAL
                ::= 4

ngwsnadsFgnLinkTrap TRAP-TYPE
                ENTERPRISE    ngwsnadsInfo
                VARIABLES     {ngwsnadsTrapTime, ngwsnadsGatewayName}
                DESCRIPTION   "SNADS Link lost by GroupWise SNADS Gateway"
                --NMS Trap annotation
                --#TYPE       "SNADS Link lost by GroupWise SNADS Gateway"
                --#SUMMARY    "GroupWise SNADS Gateway %s has lost its SNADS Link"
                --#ARGUMENTS  {1}
                --#SEVERITY   INFORMATIONAL
                --#TIMEINDEX  0
                --#HELP       "NGWALARM.HLP"
                --#HELPTAG    505
                --#STATE      OPERATIONAL
                ::= 5


END
