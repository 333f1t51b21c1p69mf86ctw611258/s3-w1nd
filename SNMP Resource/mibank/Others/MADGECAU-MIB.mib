------------------------------------------------------------------------------
--
-- MIB      : madgeCau                                  Madge Networks Ltd
--
-- Version  : 2.11                                                May 1999
--
------------------------------------------------------------------------------
--
-- Overview :
--
-- The Madge CAU MIB defines enterprise specific objects to allow the 
-- management of Madge SmartCAU, SmartCAU Plus and Smart RAM.
--
-- The Madge box MIB contains the following groups :-
--
--  madgeCauTop       - Variables relating to the topology of the ring.
--  madgeCauInfo      - Miscellaneous non-saveable variables.
--  madgeCauLam       - Variables relating to the LAMs.
--  madgeCauLCD       - Variables relating to the LCD displays.
--  madgeCauAddr      - Table of addresses of all ports.
--  madgeCauConfig    - Miscallaneous saveable variables.
--  madgeCauNewConfig - More miscellaneous saveable varibles (V2+)
--  madgeCauSecurity  - Variables relating to CAU Security (V2+)
--  madgeCauFault     - Variables relating to CAU Fault Finding (V2+)
--  madgeCauKill      - Information about nodes removed, reinserted, etc. (V2+)
--  madgeCauTrapInfo  - Information used within traps.
--
------------------------------------------------------------------------------

        MADGECAU-MIB DEFINITIONS ::= BEGIN

        IMPORTS
                  enterprises, NetworkAddress, IpAddress, Counter, Gauge,
                          TimeTicks
                      FROM RFC1155-SMI
                  OBJECT-TYPE
                          FROM RFC-1212
                  TRAP-TYPE
                          FROM RFC-1215;

        madge        OBJECT IDENTIFIER ::= { enterprises 494 }
        madgeCau          OBJECT IDENTIFIER ::= { madge 2 }

        -- Groups in the MadgeCAU MIB

        madgeCauTop       OBJECT IDENTIFIER ::= { madgeCau 1 }
        madgeCauInfo      OBJECT IDENTIFIER ::= { madgeCau 2 }
        madgeCauLam       OBJECT IDENTIFIER ::= { madgeCau 3 }
        madgeCauLCD       OBJECT IDENTIFIER ::= { madgeCau 5 }
        madgeCauAddr      OBJECT IDENTIFIER ::= { madgeCau 6 }
        madgeCauConfig    OBJECT IDENTIFIER ::= { madgeCau 7 }
        madgeCauNewConfig OBJECT IDENTIFIER ::= { madgeCau 8 }
        madgeCauSecurity  OBJECT IDENTIFIER ::= { madgeCau 9 }
        madgeCauFault     OBJECT IDENTIFIER ::= { madgeCau 10 }
        madgeCauKill      OBJECT IDENTIFIER ::= { madgeCau 11 }
        madgeCauTrapInfo  OBJECT IDENTIFIER ::= { madgeCau 12 }

-- Cau topology group.
                
        madgeCauTopWrap OBJECT-TYPE
            SYNTAX  INTEGER {
                        normal(1),    -- normal
                        wrap-ri(2),   -- wrap ring in
                        wrap-ro(3),   -- wrap ring out
                        wrap-both(4)  -- wrap both ring in and ring out
                    }
            ACCESS  read-only
            STATUS  mandatory
            DESCRIPTION
                    "The current wrap state of the cau."
            ::= { madgeCauTop 1 }

        madgeCauTopWrapCtrl OBJECT-TYPE
            SYNTAX  INTEGER {
                        normal(1),    -- normal
                        wrap-ri(2),   -- wrap ring in
                        wrap-ro(3),   -- wrap ring out
                        wrap-both(4)  -- wrap both ring in and ring out
                    }
            ACCESS  read-write
            STATUS  mandatory
            DESCRIPTION
                    "The administratively-assigned wrap state of the cau."
            ::= { madgeCauTop 2 }

        madgeCauTopRIType OBJECT-TYPE
            SYNTAX  INTEGER {
                        fibre(1),    -- Fibre-optic cabling
                        copper(2),   -- Copper cabling (STP)
                        utp(3)       -- Unshielded Twisted Pair
                    }
            ACCESS  read-only
            STATUS  mandatory
            DESCRIPTION
                    "The cable type of the Ring In (RI) port."
            ::= { madgeCauTop 3 }

        madgeCauTopRIState OBJECT-TYPE
            SYNTAX  INTEGER {
                        noSignal(1),      -- No valid Token Ring signal
                        yesSignal(2)      -- Valid Token Ring signal
                    }
            ACCESS  read-only
            STATUS  mandatory
            DESCRIPTION
                    "The state of the Token Ring Signal associated with the 
                     Ring In (RI) port."
            ::= { madgeCauTop 4 }

        madgeCauTopROType OBJECT-TYPE
            SYNTAX  INTEGER {
                        fibre(1),    -- Fibre-optic cabling
                        copper(2),   -- Copper cabling
                        utp(3)       -- Unshielded Twisted Pair
                    }
            ACCESS  read-only
            STATUS  mandatory
            DESCRIPTION
                    "The cable type of the Ring Out (RO) port."
            ::= { madgeCauTop 5 }

        madgeCauTopROState OBJECT-TYPE
            SYNTAX  INTEGER {
                        noSignal(1),      -- No valid Token Ring signal
                        yesSignal(2)      -- Valid Token Ring signal
                    }
            ACCESS  read-only
            STATUS  mandatory
            DESCRIPTION
                    "The state of the Token Ring Signal associated with the 
                     Ring Out (RO) port."
            ::= { madgeCauTop 6 }
        
        madgeCauTopBackupRing OBJECT-TYPE
            SYNTAX  INTEGER {
                        beaconing(1),   -- Backup ring is beaconing
                        normal(2),      -- Backup ring is OK
                        badly-cabled(3) -- RI/RO connected incorrectly
                    }
            ACCESS  read-only
            STATUS  mandatory
            DESCRIPTION
                    "The state of the backup ring."
            ::= { madgeCauTop 7 }
        
        madgeCauTopBackupUsed OBJECT-TYPE
            SYNTAX  INTEGER {
                        unUsed(1),   -- Backup ring is not used
                        used(2)      -- Backup ring is used
                    }
            ACCESS  read-only
            STATUS  mandatory
            DESCRIPTION
                    "Whether the backup ring is in use or not."
            ::= { madgeCauTop 8 }

-- Cau information group.
                
        madgeCauInfoVersion OBJECT-TYPE
            SYNTAX  OCTET STRING (SIZE(32))
            ACCESS  read-only
            STATUS  mandatory
            DESCRIPTION
                    "The version information. It has the following format:-
                    
                        chars[0-12] are the file name of the download image
                        char[13] is the major version number
                        char[14] is the minor version number
                        char[15] is the development version number
                        char[16] is the hardware version number"
            ::= { madgeCauInfo 1 }
        
        madgeCauInfoRemoval OBJECT-TYPE
            SYNTAX  INTEGER (0 .. 255)
            ACCESS  read-write
            STATUS  mandatory
            DESCRIPTION
                    "The removal threshold, this controls how many times a 
                     faulty but persistent node is allowed to attempt to 
                     insert into the ring before its port is permanently 
                     disabled."
            ::= { madgeCauInfo 2 }
                    
        madgeCauInfoSRNet OBJECT-TYPE
            SYNTAX  INTEGER (0 .. 4095)
            ACCESS  read-only
            STATUS  mandatory
            DESCRIPTION
                    "The source-routing ring number of the device."
            ::= { madgeCauInfo 3 }
                    
        madgeCauInfoIPXNet OBJECT-TYPE
            SYNTAX  INTEGER 
            ACCESS  read-only
            STATUS  mandatory
            DESCRIPTION
                    "The IPX network number of the device."
            ::= { madgeCauInfo 4 }
                    
        madgeCauInfoFanSpeed OBJECT-TYPE
            SYNTAX  INTEGER 
            ACCESS  read-only
            STATUS  mandatory
            DESCRIPTION
                    "The fan speed of the device in rps (revolutions per
                    second."
            ::= { madgeCauInfo 5 }

        madgeCauInfoTherm OBJECT-TYPE
            SYNTAX  INTEGER 
            ACCESS  read-only
            STATUS  mandatory
            DESCRIPTION
                    "The temperature of the device in degrees Celsius."
            ::= { madgeCauInfo 6 }
                    
        madgeCauInfoType OBJECT-TYPE
            SYNTAX  INTEGER {
                        smartCau(2),    -- SmartCAU 
                        smartCauPlus(3),-- SmartCAU Plus
                        smartRam(5),    -- Smart RAM
                        smartRamPlus(7) -- Smart RAM Plus
                    }
            ACCESS  read-only
            STATUS  mandatory
            DESCRIPTION
                    "The product identity of the device."
            ::= { madgeCauInfo 7 }
        
-- LAM information group.

        madgeCauLamTable OBJECT-TYPE
            SYNTAX  SEQUENCE OF MadgeCauLamEntry
            ACCESS  not-accessible
            STATUS  mandatory
            DESCRIPTION
                      "The table of information on all LAMs."
            ::= { madgeCauLam 1 }

        madgeCauLamEntry OBJECT-TYPE
            SYNTAX  MadgeCauLamEntry
            ACCESS  not-accessible
            STATUS  mandatory
            DESCRIPTION
                      "Information on one LAM."
            INDEX   { madgeCauLamNo }
            ::= { madgeCauLamTable 1 }

        MadgeCauLamEntry ::=
            SEQUENCE {
                madgeCauLamNo
                      INTEGER,
                madgeCauLamType
                      INTEGER,
                madgeCauLamState
                      INTEGER,
                madgeCauLamAdminState
                      INTEGER,
                madgeCauLamAllPorts
                      OCTET STRING (SIZE(20)),
                madgeCauLamSpeedDetect
                      INTEGER
              }

        madgeCauLamNo OBJECT-TYPE
            SYNTAX  INTEGER
            ACCESS  read-only
            STATUS  mandatory
            DESCRIPTION
                    "The LAM to which this entry's addressing
                    information pertains."
            ::= { madgeCauLamEntry 1 }

        madgeCauLamType OBJECT-TYPE
            SYNTAX  INTEGER {
                        noLam(1),       -- No LAM is present
                        ibmLam(2),      -- IBM LAM
                        utpLam(3),      -- Madge UTP LAM
                        stpLam(4),      -- Madge STP LAM
                        node(5),        -- A node is connected to this port
                        badlyCabled(6), -- A badly cabled LAM
                        mau(8),         -- An auto detected MAU
                        userMau(9),     -- A user defined MAU
                        raylanLam(10),  -- RAYLAN LAM
                        utpLam2(11)     -- Madge UTP LAM Plus
                    }
            ACCESS  read-only
            STATUS  mandatory
            DESCRIPTION
                    "The type of LAM."
            ::= { madgeCauLamEntry 2 }

        madgeCauLamState OBJECT-TYPE
            SYNTAX  INTEGER {
                        noLam(1),           -- No LAM is present
                        nodeInserting(4),   -- LAM is inserting
                        inserted(5),        -- LAM is inserted
                        wrongSpeed(7),      -- LAM disabled due to wrong speed
                        fault(8)            -- LAM disabled due to fault
                    }
            ACCESS  read-only
            STATUS  mandatory
            DESCRIPTION
                    "The LAM status of the LAM."
            ::= { madgeCauLamEntry 3 }

        madgeCauLamAdminState OBJECT-TYPE
            SYNTAX  INTEGER {
                        lamEnabled(1),  -- LAM is enabled
                        lamDisabled(2)  -- LAM has been disabled by user
                    }
            ACCESS  read-write
            STATUS  mandatory
            DESCRIPTION
                    "The administrated status of the LAM."
            ::= { madgeCauLamEntry 4 }

        madgeCauLamAllPorts OBJECT-TYPE
            SYNTAX  OCTET STRING (SIZE(20))
            ACCESS  read-only
            STATUS  mandatory
            DESCRIPTION
                    "An array of states for all 20 ports on the LAM."
            ::= { madgeCauLamEntry 5 }

        madgeCauLamSpeedDetect OBJECT-TYPE
            SYNTAX  INTEGER {
                        sdDisabled(1),  -- Speed Detect is disabled
                        sdEnabled(2)    -- Speed Detect is enabled
                    }
            ACCESS  read-write
            STATUS  mandatory
            DESCRIPTION
                    "Whether or not automatic speed detection is enabled."
            ::= { madgeCauLamEntry 6 }

-- CAU LCD information

        madgeCauLCDMax OBJECT-TYPE
            SYNTAX  INTEGER 
            ACCESS  read-only
            STATUS  mandatory
            DESCRIPTION
                    "The maximum number of LCD messages."
            ::= { madgeCauLCD 1 }
                    
        madgeCauLCDCurrent OBJECT-TYPE
            SYNTAX  INTEGER 
            ACCESS  read-only
            STATUS  mandatory
            DESCRIPTION
                    "The current LCD message number."
            ::= { madgeCauLCD 2 }
                    
        madgeCauLCDTable OBJECT-TYPE
            SYNTAX  SEQUENCE OF MadgeCauLCDEntry
            ACCESS  not-accessible
            STATUS  mandatory
            DESCRIPTION
                    "The table of information on all LCDs."
              ::= { madgeCauLCD 3 }

        madgeCauLCDEntry OBJECT-TYPE
            SYNTAX  MadgeCauLCDEntry
            ACCESS  not-accessible
            STATUS  mandatory
            DESCRIPTION
                    "Information on one LCD."
            INDEX   { madgeCauLCDNo }
            ::= { madgeCauLCDTable 1 }

        MadgeCauLCDEntry ::=
            SEQUENCE {
                  madgeCauLCDNo
                      INTEGER,
                  madgeCauLCDInfo
                      OCTET STRING (SIZE(32))
              }

        madgeCauLCDNo OBJECT-TYPE
            SYNTAX  INTEGER
            ACCESS  read-only
            STATUS  mandatory
            DESCRIPTION
                    "The LCD number."
            ::= { madgeCauLCDEntry 1 }

        madgeCauLCDInfo OBJECT-TYPE
            SYNTAX  OCTET STRING (SIZE(32))
            ACCESS  read-only
            STATUS  mandatory
            DESCRIPTION
                    "The LCD message."
            ::= { madgeCauLCDEntry 2 }
            
-- CAU port address group

        madgeCauAddrTable OBJECT-TYPE
            SYNTAX  SEQUENCE OF MadgeCauAddrEntry
            ACCESS  not-accessible
            STATUS  mandatory
            DESCRIPTION
                    "The table of addresses of all Ports."
              ::= { madgeCauAddr 1 }

        madgeCauAddrEntry OBJECT-TYPE
            SYNTAX  MadgeCauAddrEntry
            ACCESS  not-accessible
            STATUS  mandatory
            DESCRIPTION
                    "Address information on one Port."
            INDEX   { madgeCauAddrLamNo,
                      madgeCauAddrPortNo }
            ::= { madgeCauAddrTable 1 }

        MadgeCauAddrEntry ::=
            SEQUENCE {
                  madgeCauAddrLamNo
                      INTEGER,
                  madgeCauAddrPortNo
                      INTEGER,
                  madgeCauAddrInfo
                      OCTET STRING (SIZE(48)),
                  madgeCauAddrAllowedNode
                      OCTET STRING (SIZE(6))
              }

        madgeCauAddrLamNo OBJECT-TYPE
            SYNTAX  INTEGER (1 .. 4)
            ACCESS  read-only
            STATUS  mandatory
            DESCRIPTION
                    "The LAM number."
            ::= { madgeCauAddrEntry 1 }
                    
        madgeCauAddrPortNo OBJECT-TYPE
            SYNTAX  INTEGER (1 .. 21)
            ACCESS  read-only
            STATUS  mandatory
            DESCRIPTION
                    "The port number.
                     Note that port number 21 refers to the LAM itself."
            ::= { madgeCauAddrEntry 2 }

        madgeCauAddrInfo OBJECT-TYPE
            SYNTAX  OCTET STRING
            ACCESS  read-only
            STATUS  mandatory
            DESCRIPTION
                    "An array of MacAddresses."
            ::= { madgeCauAddrEntry 3 }

        madgeCauAddrAllowedNode OBJECT-TYPE
            SYNTAX  OCTET STRING (SIZE(6))
            ACCESS  read-write
            STATUS  mandatory
            DESCRIPTION
                    "Node address of node allowed on this LAM port.
                     If this value is 000000000000 then any nodes are allowed."
            ::= { madgeCauAddrEntry 4 }

-- CAU config group

        madgeCauConfigLAA OBJECT-TYPE
            SYNTAX  OCTET STRING (SIZE(6))
            ACCESS  read-write
            STATUS  mandatory
            DESCRIPTION
                    "The current MacAddresses of the device. This can be
                    set to a LAA (Locally Administrated Address) with an
                    address range of 4000 XXXX XXXX - 7FEF XXXX XXXX."
            ::= { madgeCauConfig 1 }

        madgeCauConfigNodePort OBJECT-TYPE
            SYNTAX  INTEGER {
                        noActiveNodeMatching(1),   -- does nothing
                        doActiveNodeMatching(2)    -- forces a node-matching
                        }
            ACCESS  read-write
            STATUS  mandatory
            DESCRIPTION
                    "Setting this value forces the device to perform 
                    a node-port matching algorithm."
            ::= { madgeCauConfig 2 }

        madgeCauConfig24HourClock OBJECT-TYPE
            SYNTAX  INTEGER {
                        clock12Hour(1),      -- 12 hour clock
                        clock24Hour(2),      -- 24 hour clock
                        clockNotSupported(3) -- No clock on this device.
                        }
            ACCESS  read-write
            STATUS  mandatory
            DESCRIPTION
                    "Whether the clock displayed on the device is 24 
                    or 12 hour based."
            ::= { madgeCauConfig 3 }

        madgeCauConfigClock OBJECT-TYPE
            SYNTAX  INTEGER
            ACCESS  read-write
            STATUS  mandatory
            DESCRIPTION
                    "The time in seconds since 1st Jan 1980."
            ::= { madgeCauConfig 4 }

        madgeCauConfigPromiscousRmon OBJECT-TYPE
            SYNTAX  INTEGER {
                        -- notConfigured(1),   OBSOLETE
                        promiscuousRmonOff(2), -- Traffic info is off
                        promiscuousRmonOn(3)   -- Traffic info is on
                        }
            ACCESS  read-write
            STATUS  mandatory
            DESCRIPTION
                    "The current state of Promiscuous Remote Network
                     Monitoring (RMON) on the device."
            ::= { madgeCauConfig 5 }

-- Cau new configuration group.

        madgeCauNewConfigMauStore OBJECT-TYPE
            SYNTAX  INTEGER {
                        mauDeduce(1),   -- Calculate where MAUs are
                        mauRecall(2)    -- Recall where MAUs are
                    }
            ACCESS  read-write
            STATUS  mandatory
            DESCRIPTION
                    "MAU devices attached to the ring may be deduced in
                     real time, however, sometimes the CAU will get it wrong.
                     This is an unsolvable problem. To get round this, the
                     MAU topology may be saved in the configuation ROM so
                     that the calculation does not have to be performed each
                     time. This variable determines how the MAU topology
                     will be found."
            ::= { madgeCauNewConfig 1 }


        madgeCauNewConfigNonPromiscuousRmon OBJECT-TYPE
            SYNTAX  INTEGER {
                        nonPromiscuousRmonOff(1),       -- Standard agent
                        nonPromiscuousRmonOn(2)         -- Advanced agent
                        }
            ACCESS  read-write
            STATUS  mandatory
            DESCRIPTION
                    "The current state of Non-Promiscuous Remote Network
                     Monitoring (RMON) on the device."
            ::= { madgeCauNewConfig 2 }


        madgeCauNewConfigSAPControl OBJECT-TYPE
            SYNTAX  INTEGER {
                        sapsDisabled(1),        -- don't generate SAPs
                        sapsEnabled(2)          -- generate SAPs
                        }
            ACCESS  read-write
            STATUS  mandatory
            DESCRIPTION
                    "Enables or disables the generation of IPX service
                     advert (SAP) frames."
            ::= { madgeCauNewConfig 3 }

-- Cau security group.

        madgeCauSecurityPMAnnounce OBJECT-TYPE
            SYNTAX  INTEGER {
                        pmAnnounceOff(1),       -- Never transmit PM frames
                        pmAnnounceOn(2)         -- Transmit PM frames if reqd
                        }
            ACCESS  read-write
            STATUS  mandatory
            DESCRIPTION
                    "Whether or not to transmit Promiscuous Mode
                     announcement frames when promiscuous RMON is in use."
            ::= { madgeCauSecurity 1 }

        madgeCauSecurityPMSafePollTimer OBJECT-TYPE
            SYNTAX  INTEGER (1 .. 65535)
            ACCESS  read-write
            STATUS  mandatory
            DESCRIPTION
                    "The period, in seconds, between each poll to discover
                     rogue nodes, etc.."
            ::= { madgeCauSecurity 2 }

        madgeCauSecurityPMSafeReplyTimeout OBJECT-TYPE
            SYNTAX  INTEGER (1 .. 255)
            ACCESS  read-write
            STATUS  mandatory
            DESCRIPTION
                    "The interval, in seconds, within which a reply must
                     be recieved for a pm-safe? request."
            ::= { madgeCauSecurity 3 }

        madgeCauSecurityPMSafeRetries OBJECT-TYPE
            SYNTAX  INTEGER (1 .. 255)
            ACCESS  read-write
            STATUS  mandatory
            DESCRIPTION
                    "The number of attempts which will be made to determine
                     whether a node is pm-safe before giving up."
            ::= { madgeCauSecurity 4 }

        madgeCauSecurityAllowedManufacturers OBJECT-TYPE
            SYNTAX  INTEGER {
                        allManufacturers(1),    -- everything allowed
                        madgeIBMOnly(2),        -- Madge and IBM only allowed
                        madgeOnly(3)            -- Madge only allowed
                    }
            ACCESS  read-write
            STATUS  mandatory
            DESCRIPTION
                    "Defines which manufacturers are legal on the ring."
            ::= { madgeCauSecurity 5 }


        madgeCauSecurityActionPM OBJECT-TYPE
            SYNTAX  INTEGER {
                        ignore(1),        -- ignore transgression
                        inform(2),        -- inform manager
                        remove(3)         -- remove offending node
                    }
            ACCESS  read-write
            STATUS  mandatory
            DESCRIPTION
                    "Defines what happens when the CAU detects a
                     node in Promiscuous Mode that shouldn't be."
            ::= { madgeCauSecurity 6 }

        madgeCauSecurityActionPMUnsafe OBJECT-TYPE
            SYNTAX  INTEGER {
                        ignore(1),        -- ignore transgression
                        inform(2),        -- inform manager
                        remove(3)         -- remove offending node
                    }
            ACCESS  read-write
            STATUS  mandatory
            DESCRIPTION
                    "Defines what happens when the CAU detects a node
                     that is not PM-safe (unless listed as an exception)."
            ::= { madgeCauSecurity 7 }

        madgeCauSecurityActionRogueNode OBJECT-TYPE
            SYNTAX  INTEGER {
                        ignore(1),        -- ignore transgression
                        inform(2),        -- inform manager
                        remove(3)         -- remove offending node
                    }
            ACCESS  read-write
            STATUS  mandatory
            DESCRIPTION
                    "Defines what happens when the CAU detects a
                     rogue node (unless listed as an exception)."
            ::= { madgeCauSecurity 8 }

        madgeCauSecurityActionIllegalMF OBJECT-TYPE
            SYNTAX  INTEGER {
                        ignore(1),        -- ignore transgression
                        inform(2),        -- inform manager
                        remove(3)         -- remove offending node
                    }
            ACCESS  read-write
            STATUS  mandatory
            DESCRIPTION
                    "Defines what happens when the CAU detects a node
                     whose manufacturer is considered illegal (unless
                     the node is listed as an exception)."
            ::= { madgeCauSecurity 9 }

        madgeCauSecurityTable OBJECT-TYPE
            SYNTAX  SEQUENCE OF MadgeCauSecurityEntry
            ACCESS  not-accessible
            STATUS  mandatory
            DESCRIPTION
                    "Table of information on all nodes which are allowed
                     to be on the ring despite some disqualifying factor.
                     Note that this is a sparse table - see description of
                     madgeCauSecurityNodeAddress."
            ::= { madgeCauSecurity 10 }

        madgeCauSecurityEntry OBJECT-TYPE
            SYNTAX  MadgeCauSecurityEntry
            ACCESS  not-accessible
            STATUS  mandatory
            DESCRIPTION
                    "Information on one node which is allowed to be on
                     the ring despite some disqualifying factor."
            INDEX   { madgeCauSecurityIndex }
            ::= { madgeCauSecurityTable 1 }

        MadgeCauSecurityEntry ::=
            SEQUENCE {
                madgeCauSecurityIndex
                    INTEGER,
                madgeCauSecurityNodeAddress
                    OCTET STRING (SIZE(6)),
                madgeCauSecurityExceptionPM
                    INTEGER,
                madgeCauSecurityExceptionPMUnsafe
                    INTEGER,
                madgeCauSecurityExceptionRogueNode
                    INTEGER,
                madgeCauSecurityExceptionIllegalMF
                    INTEGER,
                madgeCauSecurityExceptionWrongNode
                    INTEGER
            }

        madgeCauSecurityIndex OBJECT-TYPE
            SYNTAX  INTEGER
            ACCESS  read-only
            STATUS  mandatory
            DESCRIPTION
                    "The table entry to which this entry's information
                     pertains."
            ::= { madgeCauSecurityEntry 1}

        madgeCauSecurityNodeAddress OBJECT-TYPE
            SYNTAX  OCTET STRING (SIZE(6))
            ACCESS  read-write
            STATUS  mandatory
            DESCRIPTION
                    "The node address of the node which is allowed on the
                     ring if the right conditions are met. If this entry
                     reads as all zeros then this is an empty table entry.
                     Writing all zeroes to this field will clear the table
                     entry completely (including all exceptions)."
            ::= { madgeCauSecurityEntry 2 }

        madgeCauSecurityExceptionPM OBJECT-TYPE
            SYNTAX  INTEGER {
                        disallow(1),    -- reject if node enters PM
                        allow(2)        -- allow node to enter PM
                    }
            ACCESS  read-write
            STATUS  mandatory
            DESCRIPTION
                    "Whether or not the CAU allows the node on the ring if it
                     enters Promiscuous Mode."
            ::= { madgeCauSecurityEntry 3 }

        madgeCauSecurityExceptionPMUnsafe OBJECT-TYPE
            SYNTAX  INTEGER {
                        disallow(1),    -- reject if node PM-unsafe
                        allow(2)        -- allow node to be PM-unsafe
                    }
            ACCESS  read-write
            STATUS  mandatory
            DESCRIPTION
                    "Whether or not the CAU allows the node on the ring if it
                     is Promiscuous-Mode-Unsafe."
            ::= { madgeCauSecurityEntry 4 }
             
        madgeCauSecurityExceptionRogueNode OBJECT-TYPE
            SYNTAX  INTEGER {
                        disallow(1),    -- reject if node is rogue
                        allow(2)        -- allow node to be rogue
                    }
            ACCESS  read-write
            STATUS  mandatory
            DESCRIPTION
                    "Whether or not the CAU allows the node on the ring if it
                     is considered a rogue node."
            ::= { madgeCauSecurityEntry 5 }
             
        madgeCauSecurityExceptionIllegalMF OBJECT-TYPE
            SYNTAX  INTEGER {
                        disallow(1),    -- reject if illegal m/f
                        allow(2)        -- allow illegal m/f
                    }
            ACCESS  read-write
            STATUS  mandatory
            DESCRIPTION
                    "Whether or not the CAU allows the node on the ring if 
                     it's manufacturer is consdered illegal."
            ::= { madgeCauSecurityEntry 6 }

        madgeCauSecurityExceptionWrongNode OBJECT-TYPE
            SYNTAX  INTEGER {
                        disallow(1),    -- reject if wrong node for port
                        allow(2)        -- allow if wrong node for port
                    }
            ACCESS  read-write
            STATUS  mandatory
            DESCRIPTION
                    "Whether or not the CAU allows the node on the ring if it
                     is plugged into the wrong port."
            ::= { madgeCauSecurityEntry 7 }


        madgeCauSecurityActionWrongNode OBJECT-TYPE
            SYNTAX  INTEGER {
                        ignore(1),        -- ignore transgression
                        inform(2),        -- inform manager
                        remove(3)         -- remove offending node
                    }
            ACCESS  read-write
            STATUS  mandatory
            DESCRIPTION
                    "Defines what happens when the CAU detects a
                     node trying to open on a port for which it
                     does not have legal access."
            ::= { madgeCauSecurity 11 }

        madgeCauSecurityExtendedException OBJECT-TYPE
            SYNTAX  INTEGER {
                        oldModeOnly(1),      -- only supports old mode
                        inOldMode(2),        -- in old mode
                        inNewMode(3)         -- in new mode
                    }
            ACCESS  read-write
            STATUS  mandatory
            DESCRIPTION
                    "The new mode extends the exception list from 24 nodes
		     to 160 nodes. However, to do this it must reduce
		     the location and comments fields and not save the port
		     security data. This might not be possible in some cases
		     and an erase configuration is the only cure. This is
		     supported in microcode 4.20 and later."
            ::= { madgeCauSecurity 12 }

-- Cau fault-finding group.


        madgeCauFaultRPFailAction OBJECT-TYPE
            SYNTAX  INTEGER {
                        ignore(1),        -- ignore transgression
                        inform(2),        -- inform manager
                        remove(3)         -- remove offending node
                    }
            ACCESS  read-write
            STATUS  mandatory
            DESCRIPTION
                    "Defines what happens when the CAU detects a
                     ring poll failure."
            ::= { madgeCauFault 1 }

        madgeCauFaultBeaconDefault OBJECT-TYPE
            SYNTAX  INTEGER (1 .. 255)
            ACCESS  read-only
            STATUS  mandatory
            DESCRIPTION
                    "DEFAULT number of successive beacon frames from one node
                     before a problem is noticed."
            ::= { madgeCauFault 2 }

        madgeCauFaultBeaconThreshold OBJECT-TYPE
            SYNTAX  INTEGER (1 .. 255)
            ACCESS  read-write
            STATUS  mandatory
            DESCRIPTION
                    "Number of successive beacon frames from one node
                     before a problem is noticed."
            ::= { madgeCauFault 3 }

        madgeCauFaultBeaconAction OBJECT-TYPE
            SYNTAX  INTEGER {
                        ignore(1),        -- ignore transgression
                        inform(2),        -- inform manager
                        remove(3)         -- remove offending node
                    }
            ACCESS  read-write
            STATUS  mandatory
            DESCRIPTION
                    "Defines what happens when the CAU detects a
                     succession of beacon frames from the same node."
            ::= { madgeCauFault 4 }

        madgeCauFaultRingPurgeDefault OBJECT-TYPE
            SYNTAX  INTEGER (0 .. 255)
            ACCESS  read-only
            STATUS  mandatory
            DESCRIPTION
                    "DEFAULT number of successive ring purge frames from
                     one node before a problem is noticed."
            ::= { madgeCauFault 5 }

        madgeCauFaultRingPurgeThreshold OBJECT-TYPE
            SYNTAX  INTEGER (0 .. 255)
            ACCESS  read-write
            STATUS  mandatory
            DESCRIPTION
                    "Number of successive ring purge frames from one node
                     before a problem is noticed."
            ::= { madgeCauFault 6 }

        madgeCauFaultRingPurgeAction OBJECT-TYPE
            SYNTAX  INTEGER {
                        ignore(1),        -- ignore transgression
                        inform(2),        -- inform manager
                        remove(3)         -- remove offending node
                    }
            ACCESS  read-write
            STATUS  mandatory
            DESCRIPTION
                    "Defines what happens when the CAU detects a
                     succession of ring purge frames from the same node."
            ::= { madgeCauFault 7 }

        madgeCauFaultIsoErrDefault OBJECT-TYPE
            SYNTAX  INTEGER (0 .. 255)
            ACCESS  read-only
            STATUS  mandatory
            DESCRIPTION
                    "DEFAULT number of isolating errors (scaled by a
                     factor of 6) before a problem is noticed."
            ::= { madgeCauFault 8 }

        madgeCauFaultIsoErrThreshold OBJECT-TYPE
            SYNTAX  INTEGER (0 .. 255)
            ACCESS  read-write
            STATUS  mandatory
            DESCRIPTION
                    "Number of isolating errors (scaled by a factor of 6)
                     before a problem is noticed."
            ::= { madgeCauFault 9 }

        madgeCauFaultIsoErrAction OBJECT-TYPE
            SYNTAX  INTEGER {
                        ignore(1),        -- ignore transgression
                        inform(2),        -- inform manager
                        remove(3)         -- remove offending node
                    }
            ACCESS  read-write
            STATUS  mandatory
            DESCRIPTION
                    "Defines what happens when the CAU detects
                     too many isolating errors."
            ::= { madgeCauFault 10 }


-- Cau kill information group.


        madgeCauKillNodeAddress OBJECT-TYPE
            SYNTAX  OCTET STRING (SIZE(6))
            ACCESS  read-only
            STATUS  mandatory
            DESCRIPTION
                    "The node address to which the rest of the
                     information in this group pertains."
            ::= { madgeCauKill 1 }

        madgeCauKillReason OBJECT-TYPE
            SYNTAX  INTEGER {
                        reasonUnknown(1),       -- None of the reasons below
                        pmViolation(2),         -- Node entered Promiscuous Mode
                        pmUnsafe(3),            -- Node is PM-unsafe
                        rogueNode(4),           -- Node is rogue
                        illegalManufacturer(5), -- Node has illegal manufacturer
                        ringPollFailure(6),     -- Node caused ring poll failure
                        beaconing(7),           -- Node keeps beaconing
                        ringPurges(8),          -- Node keeps purging ring
                        isolatingErrors(9),     -- Node has isolating errors
                        wrongNode(10)           -- Unauthorised node in port
                        }
            ACCESS  read-only
            STATUS  mandatory
            DESCRIPTION
                    "The reason the node was noticed."
            ::= { madgeCauKill 2 }

        madgeCauKillStatus OBJECT-TYPE
            SYNTAX  INTEGER {
                        information(1),         -- No action taken.
                        aboutToKill(2),         -- CAU about to kill node.
                        killFailed(3),          -- Tried to kill, but failed.
                        killed(4),              -- Node removed from ring.
                        killAbandoned(5),       -- Not going to kill after all.
                        resurrected(6)          -- Node reinserted onto ring.
                        }
            ACCESS  read-only
            STATUS  mandatory
            DESCRIPTION
                    "What exactly has happened to the node."
            ::= { madgeCauKill 3 }

        madgeCauKillLamNo OBJECT-TYPE
            SYNTAX  INTEGER (1 .. 4)
            ACCESS  read-only
            STATUS  mandatory
            DESCRIPTION
                    "LAM into which offending node is plugged."
            ::= { madgeCauKill 4 }

        madgeCauKillPortNo OBJECT-TYPE
            SYNTAX  INTEGER (1 .. 20)
            ACCESS  read-only
            STATUS  mandatory
            DESCRIPTION
                    "LAM port into which offending node is plugged."
            ::= { madgeCauKill 5 }

-- Cau trap information group.

        madgeCauTrapInfoLamNo OBJECT-TYPE
            SYNTAX  INTEGER (1 .. 4)
            ACCESS  read-only
            STATUS  mandatory
            DESCRIPTION
                    "Relevant LAM number."
            ::= { madgeCauTrapInfo 1 }

        madgeCauTrapInfoPortNo OBJECT-TYPE
            SYNTAX  INTEGER (1 .. 21)
            ACCESS  read-only
            STATUS  mandatory
            DESCRIPTION
                    "Relevant Port number.
                     A port number of 21 refers to the LAM itself"
            ::= { madgeCauTrapInfo 2 }

        madgeCauTrapInfoState OBJECT-TYPE
            SYNTAX  INTEGER {
                        noNode(1),      -- No Node is present
                        inserted(2),    -- Node is inserted
                        wrongSpeed(3),  -- Node disabled due to wrong speed
                        fault(4)        -- Node disabled due to fault
                    }
            ACCESS  read-only
            STATUS  mandatory
            DESCRIPTION
                    "The status of the node."
            ::= { madgeCauTrapInfo 3 }

-- Madge Cau specific traps
--
-- The agent throttles the generation of consecutive traps so that there is
-- at least a five-second gap between them.                                  

        backupPathStateChange TRAP-TYPE
            ENTERPRISE madgeCau
            VARIABLES { madgeCauTopBackupRing }
            DESCRIPTION
                    "This trap is sent when the state of the backup 
                    ring changes."
            ::= 1

        backupPathStateUse TRAP-TYPE
            ENTERPRISE madgeCau
            VARIABLES { madgeCauTopBackupUsed }
            DESCRIPTION
                    "This trap is sent when the state of the backup 
                    usage changes."
            ::= 2

        wrapStateChange TRAP-TYPE
            ENTERPRISE madgeCau
            VARIABLES { madgeCauTopWrap }
            DESCRIPTION
                    "This trap is sent when the wrap state of the cau  
                    changes."
            ::= 3

        lamPortDisabled TRAP-TYPE
            ENTERPRISE madgeCau
            DESCRIPTION
                    "This trap is sent when a LAM port is disabled due to
                    either a wrong speed node inserting or a faulty node
                    being detected."
            ::= 4

        mCaufanSpeedFailed TRAP-TYPE
            ENTERPRISE madgeCau
            VARIABLES { madgeCauInfoFanSpeed }
            DESCRIPTION
                    "This trap is sent when the fan has failed." 
            ::= 5

        temperatureExceeded TRAP-TYPE
            ENTERPRISE madgeCau
            VARIABLES { madgeCauInfoTherm }
            DESCRIPTION
                    "This trap is sent when the temperature of the 
                    device has exceeded safe limits."
            ::= 6

        killInformation TRAP-TYPE
            ENTERPRISE madgeCau
            VARIABLES {
                    madgeCauKillNodeAddress,
                    madgeCauKillReason,
                    madgeCauKillStatus
                    }
            DESCRIPTION
                    "A node has been noticed, and possibly removed from or
                    reinserted onto the ring."
            ::= 7

        killInformation2 TRAP-TYPE
            ENTERPRISE madgeCau
            VARIABLES {
                    madgeCauKillNodeAddress,
                    madgeCauKillReason,
                    madgeCauKillStatus,
                    madgeCauKillLamNo,
                    madgeCauKillPortNo
                    }
            DESCRIPTION
                    "A node has been noticed, and possibly removed from or
                    reinserted onto the ring. Same as killInformation
                    but with extra information."
            ::= 8

        lamPortDisabled2 TRAP-TYPE
            ENTERPRISE madgeCau
            VARIABLES {
                    madgeCauTrapInfoLamNo,
                    madgeCauTrapInfoPortNo,
                    madgeCauTrapInfoState
                    }
            DESCRIPTION
                    "This trap is sent when a LAM port is disabled due to
                    either a wrong speed node inserting or a faulty node
                    being detected."
            ::= 9

        lamStateChanged TRAP-TYPE
            ENTERPRISE madgeCau
            VARIABLES {
                    madgeCauTrapInfoLamNo,
                    madgeCauTrapInfoState
                    }
            DESCRIPTION
            "A LAM has joined or left the ring."
        ::= 10

        END
