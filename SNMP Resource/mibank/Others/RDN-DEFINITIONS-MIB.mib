-- *****************************************************************
-- 
-- RDN-DEFINITIONS-MIB:
--             RiverDelta Definitions Object Identifier Assignments
--             (riverdelta.rdnDefinitions - 1.3.6.1.4.1.4981.4)
--
-- April 2001, Thor Kirleis (thor@riverdelta.com)
--
-- Copyright (c) 2001 RiverDelta Networks, all rights reserved.
-- 
-- *****************************************************************

RDN-DEFINITIONS-MIB DEFINITIONS ::= BEGIN

    IMPORTS
        MODULE-IDENTITY
            FROM SNMPv2-SMI
        riverdelta
            FROM RDN-MIB;

    -- riverdelta definitions mib module

    rdnDefinitions MODULE-IDENTITY
        LAST-UPDATED "0104180000Z" -- example "9501201225Z"
                                   -- Fri Jan 20 12:25:50 PST 1995
        ORGANIZATION "Motorola"
        CONTACT-INFO "Motorola
                      3 Highwood Drive
                      Tewksbury, MA 01867
                      Tel: +1 978 858 2000
                      Fax: +1 978 858 2399
                      E-mail:  BSRSNMP@maillist2001.mot.com

                      Tom Keske
                      Motorola BCS
                      20 Cabot Blvd. MA07 M2-330
                      Mansfield, MA 02048
                      Tel: 1-508-851-8325
                      Fax: 1-508-851-8510
                      E-mail: Tom.Keske@motorola.com"
        DESCRIPTION
                "MIB module for Motorola definitions."
        REVISION     "0104180000Z"
        DESCRIPTION
                "Initial creation."
        ::= { riverdelta 4 }

END


-- *****************************************************************
-- 
-- RDN-PRODUCTS-MIB:
--             RiverDelta Product Object Identifier Assignments
--
-- April 2001, Thor Kirleis (thor@riverdelta.com)
--             (riverdelta.rdnDefinitions.rdnProducts
--                                           - 1.3.6.1.4.1.4981.4.1)
--
-- Copyright (c) 2001 RiverDelta Networks, all rights reserved.
-- 
-- *****************************************************************
