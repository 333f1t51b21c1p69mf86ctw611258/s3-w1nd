-- **************************************************************************
-- *							        	    *
-- *  CSI Netlink					    	            *	
-- *							    	            *	
-- * File: netlink-mib.txt				    		    *
-- * Release: 4.0.0 (with some pre 4.0.2 Voice Additions     		    *
-- * Release Date:  April 3, 1998			    		    *
-- *							    		    *
-- **************************************************************************
-- *                                                                        *
-- * Copyright (c) 1998 by CSI Netlink.  All rights reserved. No part of    *
-- * this work covered by copyrights herein may be reproduced or copied in  *
-- * any form or by any means - electronic, graphic, or mechanical,         *
-- * including photocopying, recording, taping, or using information and    *
-- * retrieval systems - without prior written permission from CSI Netlink. *
-- *                                                                        *
-- * This is proprietary information which is protected by copyright.       *
-- * Netlink, FRX4000 (TM), FRX6000 (TM), FRX7000 (TM), and FRX8000 (TM)    *
-- * are trademarks of Cabletron Systems, Inc. NetFRAD (TM) and OmniLinx    *
-- * Switch (TM) are trademarks of CSI Netlink. All other product           *
-- * designations are the property of their respective owners.              *
-- *                                                                        *
-- **************************************************************************

NETLINK-SPECIFIC-MIB DEFINITIONS ::= BEGIN

IMPORTS
    OBJECT-TYPE
        FROM RFC-1212
    RowStatus, MacAddress, TimeInterval
        FROM SNMPv2-TC
    mib-2
        FROM RFC1213-MIB
    enterprises, mgmt, TimeTicks, Gauge, Counter, IpAddress, NetworkAddress
        FROM RFC1155-SMI;

--  This MIB module uses the extended OBJECT-TYPE macro as
--  defined in RFC 1212.

-- textual conventions

DisplayString ::=
    OCTET STRING
-- This data type is used to model textual information taken
-- from the NVT ASCII character set.  By convention, objects
-- with this syntax are declared as having
--
--      SIZE (0..255)

PhysAddress ::=
    OCTET STRING
-- This data type is used to model media addresses.  For many
-- types of media, this will be in a binary representation.
-- For example, an ethernet address would be represented as
-- a string of 6 octets.

NlSubscriberAddress ::= OCTET STRING (SIZE(1..15))
-- this should really be a X121Address, which is defined in RFC 1382 as
--           X121Address ::= OCTET STRING (SIZE(0..17))
             -- 0 to 17 bytes in length containing the ASCII
             -- characters [0-9], each octet contains one digit
             -- of the address.
-- Since we only support non-TOA/NPI type addresses (see X.25 Blue Book)
-- our addresses are upto 15 digits.
-- Since we cannot configure empty addresses, the minimum is 1 digit,
-- which suits us, since indices need at least one component.
-- NOTE: need to support wildcard characters '?' and '*'.
-- NOTE: the screen interface allows 'U' and 'G', which is a bug.
-- Also, since we use it as an index, we could use the binary equivalent
-- of decimal digits, rather than the ASCII equivalent. But, since digits
-- besides decimal digits are used (?, *) we prefer the ASCII representation.
-- This will make usage from most management applications (ie. browsers) a
-- little more complicated, but no funny mapping is done.
-- We use the SMI rules for variable-string indexing (first subid specifies
-- the length, the rest of the subids are big-endian).

-- the following RFC 1747 object type is used by the SDLC link station
-- tables defined in this mib.
snaDLC              OBJECT IDENTIFIER ::= {mib-2 41}
sdlc                OBJECT IDENTIFIER ::= {snaDLC 1}
sdlcLSGroup         OBJECT IDENTIFIER ::= {sdlc 2}
sdlcLSAdminTable    OBJECT IDENTIFIER ::= {sdlcLSGroup 1}
sdlcLSAdminEntry    OBJECT IDENTIFIER ::= {sdlcLSAdminTable 1}
sdlcLSAddress       OBJECT-TYPE
                    SYNTAX      INTEGER (1..255)
                    ACCESS      read-only
                    STATUS      mandatory
                    DESCRIPTION
                         "This value is the poll address of the
                         secondary link station for this SDLC link.  It
                         uniquely identifies the SDLC link station
                         within a single SDLC port."
                    ::= { sdlcLSAdminEntry 1 }

netlink OBJECT IDENTIFIER ::= { enterprises 173 }

-- ***********************
-- *  THE NETWORK GROUP  *
-- ***********************

network OBJECT IDENTIFIER ::= { netlink 6 }
netstat OBJECT IDENTIFIER ::=     { network 1 }

--
--  The netstat group is used to describe network status information for
--  a node. It only applies to the FRX8000 nodes since the FRX4000s and
--  FRX6000s have no knowledge of any other nodes.               
--

nsMaxNeigh OBJECT-TYPE
	SYNTAX INTEGER
	ACCESS read-only
	STATUS mandatory
	DESCRIPTION "Maximum number of neighbor nodes. This value is currently
	always 64 for FRX8000 and 20 for an N7400 or 7500. 
	A neighbor is the closest node in a path from the local node."
	::= { netstat 1 }

nsThisNode OBJECT-TYPE
	SYNTAX INTEGER
	ACCESS read-only
	STATUS mandatory
	DESCRIPTION "This nodes number. (1-250) "
	::= { netstat 2 }

nsNodTable OBJECT-TYPE
	SYNTAX SEQUENCE OF NsEntry
	ACCESS not-accessible
	STATUS mandatory
	DESCRIPTION "A table showing all nodes known to this node
	along with status and neighbor information."
	::= { netstat 3 }

nsEntry OBJECT-TYPE
	SYNTAX NsEntry
	ACCESS not-accessible
	STATUS mandatory
	DESCRIPTION "Each entry of the node table is indexed by 
	node number."
	INDEX { nsNodNum }
	::= { nsNodTable 1 }

NsEntry ::=
	SEQUENCE {
		nsNodNum
			INTEGER,
		nsStatus
			INTEGER,
		nsNumNeigh
			INTEGER
	}

nsNodNum OBJECT-TYPE
	SYNTAX INTEGER
	ACCESS read-only
	STATUS mandatory
	DESCRIPTION "The node number of the desired node. This is the
	index into the node table."
	::= { nsEntry 1 }

nsStatus OBJECT-TYPE
	SYNTAX INTEGER
	ACCESS read-only
	STATUS mandatory
	DESCRIPTION "The operational status of the node. The status is 
	given as:
	    1 = Node is defined in the database;
	    9 = Node is operational;"
	::= { nsEntry 2 }

nsNumNeigh OBJECT-TYPE
	SYNTAX INTEGER
	ACCESS read-only
	STATUS mandatory
	DESCRIPTION "Current number of neighbor nodes to this node."
	::= { nsEntry 3 }

nsNeighTable OBJECT-TYPE
	SYNTAX SEQUENCE OF NsNeighEntry
	ACCESS not-accessible
	STATUS mandatory
	DESCRIPTION "The neighbor table lists the status of a nodes
	neighbors."
	::= { netstat 4 }

nsNeighEntry OBJECT-TYPE
	SYNTAX NsNeighEntry
	ACCESS not-accessible
	STATUS mandatory
	DESCRIPTION "The table entries are indexed by the node number and 
	the neighbors node number."
	INDEX { nsNTNode, nsNTNeigh }
	::= { nsNeighTable 1 }

NsNeighEntry ::=
	SEQUENCE {
		nsNTNode
			INTEGER,
		nsNTNeigh
			INTEGER,
		nsNTNeighStat
			INTEGER
	}

nsNTNode OBJECT-TYPE
	SYNTAX INTEGER
	ACCESS read-only
	STATUS mandatory
	DESCRIPTION "The node number of the node whose neighbor's status
	is being sought."
	::= { nsNeighEntry 1 }

nsNTNeigh OBJECT-TYPE
	SYNTAX INTEGER
	ACCESS read-only
	STATUS mandatory
	DESCRIPTION "The node number of the neighbor whose status is being
	sought."
	::= { nsNeighEntry 2 }

nsNTNeighStat OBJECT-TYPE
	SYNTAX INTEGER { notConnected(1),
			 connected(2) }
	ACCESS read-only
	STATUS mandatory
	DESCRIPTION "The status of the neighbor node given as:
	    1 = previously, but not currently, connected;
	    2 = Currently connected; "
	::= { nsNeighEntry 3 }

-- ********************
-- *  THE NODE GROUP  *
-- ********************

local OBJECT IDENTIFIER ::=   { netlink 7 }
node OBJECT IDENTIFIER ::= 	    { local 1 }
nodeCfgTable OBJECT IDENTIFIER ::=   { node 1 }
nodeAlmTable OBJECT IDENTIFIER ::=   { node 2 }
nodeSNMPGroup OBJECT IDENTIFIER ::=  { node 3 }

--
--  The NODE group is used to describe configuration of the node
--

nodeModel OBJECT-TYPE
	SYNTAX INTEGER { model1(1),
					 model2(2),
					 rackmount(3),
					 highavail(4),
					 netfrad(5),
					 frx4000(6),
					 ss1800(7)
					}
	ACCESS read-only
	STATUS mandatory
	DESCRIPTION "Describes the unit model"
	::= { nodeSNMPGroup 1 }

--
--  The Traps group provides information about Traps on the node
--

nodeTrapText OBJECT-TYPE
	SYNTAX DisplayString
	ACCESS read-only
	STATUS mandatory
	DESCRIPTION "Text of the last alarm generated"
	::= {  nodeSNMPGroup 2 }

nodeTrapAdrTable OBJECT-TYPE
	SYNTAX SEQUENCE OF TpAdrEntry
	ACCESS not-accessible
	STATUS mandatory
	DESCRIPTION "A table used to define the IP address of end-nodes
	to receive alarms generated by this node. Up to 16 addresses
	can be specified."
	::= { nodeSNMPGroup 3 }

tpAdrEntry OBJECT-TYPE
	SYNTAX TpAdrEntry
	ACCESS not-accessible
	STATUS mandatory
	DESCRIPTION "A Trap entry containing objects relating to SNMP traps."
	INDEX { tpAdrIdx }
	::= { nodeTrapAdrTable 1 }

TpAdrEntry ::=
	SEQUENCE {
		tpAdrIdx
			INTEGER,
		tpAddress
			IpAddress,
		tpAdrFlag
			INTEGER,
		tpAdrSLev
			INTEGER
	}
tpAdrIdx OBJECT-TYPE
	SYNTAX INTEGER
	ACCESS read-only
	STATUS mandatory
	DESCRIPTION "The index into the trap configuration table"
	::= { tpAdrEntry 1 }

tpAddress OBJECT-TYPE
	SYNTAX IpAddress
	ACCESS read-write
	STATUS mandatory
	DESCRIPTION "The IP Address of the end-station to send alarms"
	::= { tpAdrEntry 2 }

tpAdrFlag OBJECT-TYPE
	SYNTAX INTEGER { disableTraps(1), 
			 enableTraps(2), 
			 delete(3) }
	ACCESS read-write
	STATUS mandatory
	DESCRIPTION "Defines the state of this entry as:
	    0 = Do not send traps to the Address;
	    1 = Send traps to the Address;
	    2 = This Address entry is deleted from the table; "
	::= { tpAdrEntry 3 }

tpAdrSLev OBJECT-TYPE
	SYNTAX INTEGER { critical(1),
			 major(2),
			 minor(3),
			 informational(4) }
	ACCESS read-write
	STATUS mandatory
	DESCRIPTION "Lowest severity level traps that will be sent to 
	this Address; 1 is the highest, 4 is the lowest."
	::= { tpAdrEntry 4 }

nodeBagTable OBJECT IDENTIFIER ::=   { node 4 }

-- *****************************
-- *  THE HARDWARE CARD GROUP  *
-- *****************************

hwcard OBJECT IDENTIFIER ::= 	   	{ local 2 }

--
--  This item describes the Max number of Protocols allowed on each RLP
--

rlpMaxProtos OBJECT-TYPE
	SYNTAX INTEGER
	ACCESS read-only
	STATUS mandatory
	DESCRIPTION "Maximum number of protocols allowed on each RLP.
    This value is currently 11 for FRX4000s, 9 for FRX6000s, and
	5 for FRX7000s and FRX8000s."
	::= { hwcard 1 }

--
--  The RLP Table used to describe each RLP on a node
--

rlpConfigTable OBJECT-TYPE
	SYNTAX SEQUENCE OF RlpEntry
	ACCESS not-accessible
	STATUS mandatory
	DESCRIPTION "A Table to describe each RLP on the node"
	::= { hwcard 2 }

rlpEntry OBJECT-TYPE
	SYNTAX RlpEntry
	ACCESS not-accessible
	STATUS mandatory
	DESCRIPTION "An RLP entry containing objects relating to RLPs."
	INDEX { rlpIndex }
	::= { rlpConfigTable 1 }

RlpEntry ::=
	SEQUENCE {
		rlpIndex
			INTEGER,
		rlpStatus
			INTEGER,
		rlpMemorySize
			INTEGER,
		rlpLIC1Type
			INTEGER,
		rlpLIC2Type
			INTEGER,
		rlpProtocol
			OCTET STRING,
		rlpGroupNumber
			INTEGER,
		rlpGroupResponsibility
			INTEGER
	}

rlpIndex OBJECT-TYPE
	SYNTAX INTEGER
	ACCESS read-only
	STATUS mandatory
	DESCRIPTION "The RLP number on the node"
	::= { rlpEntry 1 }

rlpStatus OBJECT-TYPE
	SYNTAX INTEGER { installed(1),
			 configured(2),
			 load-failed(3),
			 loading(4),
			 ipl-failed(5),
			 ipl-in-progress(6),
			 failed(7),
			 operational(8),
			 power-off(9),
			 power-on(10) }
	ACCESS read-only
	STATUS mandatory
	DESCRIPTION "The current state of this RLP"
	::= { rlpEntry 2 }

rlpMemorySize OBJECT-TYPE
	SYNTAX INTEGER
	ACCESS read-only
	STATUS mandatory
	DESCRIPTION "The amount of memory installed on this RLP"
	::= { rlpEntry 3 }

rlpLIC1Type OBJECT-TYPE
	SYNTAX INTEGER { none(1),
					 rs232(2),
					 rs422(3),
					 v35(4) ,
					 hs-rs232(5),
					 x21(6),
					 rs449(7),
					 universal(8),
					 t1(10),
					 e1(11),
					 voice(13) 
                }
	ACCESS read-only
	STATUS mandatory
	DESCRIPTION "The Type of Line Interface card in the first position"
	::= { rlpEntry 4 }

rlpLIC2Type OBJECT-TYPE
	SYNTAX INTEGER { none(1),
			 		 rs232(2),
					 rs422(3),
					 v35(4) ,
					 hs-rs232(5),
					 x21(6),
					 rs449(7),
					 universal(8),
					 t1(10),
					 e1(11),
					 voice(13) 
	}
	ACCESS read-only
	STATUS mandatory
	DESCRIPTION "The Type of Line Interface card in the second position"
	::= { rlpEntry 5 }

rlpProtocol OBJECT-TYPE
	SYNTAX OCTET STRING
	ACCESS read-write
	STATUS mandatory
	DESCRIPTION "The protocols configured on this RLP. This is an OCTET 
	STRING where each octet represents a protocol type. The size of this
	is the maximum number of protocols allowed on an RLP (rlpMaxProtos).
	The protocol types are defined as:
		00 = none 
		01 = X.25
		02 = Frame Relay
		03 = Async
		04 = SDLC
		05 = BSC Interactive
		07 = IP
		08 = SNMP
		09 = RIP
		0A = LLC2
		0B = Trunk
		0C = IPX
		0D = Config
		0E = LLC2-R
		0F = IP-R
		10 = NVSP
		11 = Bridge
	"
	::= { rlpEntry 6 }

rlpGroupNumber OBJECT-TYPE
	SYNTAX INTEGER (1..4)
	ACCESS read-only
	STATUS mandatory
	DESCRIPTION "The group to which this RLP belongs- always 1 if not
	FRX7000."
	::= { rlpEntry 7 }

rlpGroupResponsibility OBJECT-TYPE
	SYNTAX INTEGER {
		primary (1),
		secondary (2)
        }	
	ACCESS	read-only
	STATUS	mandatory
	DESCRIPTION "The responsibility of this RLP within its group, always
	primary if not FRX7000."
	::= { rlpEntry 8 }

-- ********************
-- *  THE PORT GROUP  *
-- ********************

port OBJECT IDENTIFIER ::= 	   	{ local 3 }
portX25Group OBJECT IDENTIFIER ::=  { port 1 }

portPhyX25AdminTable  OBJECT-TYPE
       SYNTAX      SEQUENCE OF PortPhyX25AdminEntry
       ACCESS      not-accessible
       STATUS      mandatory
       DESCRIPTION
               "This table contains Netlink Enterprise specific
               objects to manage an X25 port. Changing one of
               these parameters may take effect in the operating
               port immediately or may wait until the interface is
               restarted depending on the details of the
               implementation.

               Most of the objects in this read-write table have
               corresponding read-only objects in the
               portX25OperTable that return the current
               operating value.

               The operating values may be different from these
               configured values if a configured parameter was
               configured after the interface was started."
       ::= { portX25Group 1 }

portPhyX25AdminEntry  OBJECT-TYPE
       SYNTAX      PortPhyX25AdminEntry
       ACCESS      not-accessible
       STATUS      mandatory
       DESCRIPTION
               "A list of configured values for an X25 port."
       INDEX   { nlIfRlp, nlIfPort }
                    ::= { portPhyX25AdminTable 1 }

PortPhyX25AdminEntry  ::= SEQUENCE
{
        portPhyX25AdminConnector   	INTEGER,
        portPhyX25AdminSpeed       	INTEGER,
        portPhyX25AdminGenerateClock 	INTEGER,
        portPhyX25AdminRcvClockFromDTE INTEGER,
        portPhyX25AdminDialOut		   	INTEGER,
        portPhyX25AdminInactivityTimer	INTEGER,
        portPhyX25AdminDisconnectTimer	INTEGER,
        portPhyX25AdminSetupTimer		INTEGER,
        portPhyX25AdminTrunkFlag	 	INTEGER,
        portPhyX25AdminTrunkGroup	 	OCTET STRING,
        portPhyX25AdminRowStatus   	RowStatus
}

portPhyX25AdminConnector    OBJECT-TYPE
        SYNTAX      INTEGER{
        	rs232 (3),
           	v35 (5),
           	rs449 (6),
           	rs530 (7),
           	x21 (8),
           	t1 (10),
           	e1 (11)
           }
        ACCESS      read-write
        STATUS      mandatory
        DESCRIPTION
			"Physical port interface connector type."
        ::= { portPhyX25AdminEntry 1 }

portPhyX25AdminSpeed      OBJECT-TYPE
        SYNTAX      INTEGER 
        ACCESS      read-write
        STATUS      mandatory
        DESCRIPTION
		"This object defines the speed of the X25 port.  The speed may
	 	only be set to one of a series of reasonable values, and if an attempt 
		is made to set the speed to a value which is within the valid range
		but not equal to one of these values, the speed will be rounded up. 
		If the connector type of the port is RS232, the port could be a
		standard port or a high speed port.  If the port is a high speed
		RS232 port, the maximum valid speed is 256000.  If the port is a 
		standard RS232 port, the maximum valid speed is 64000 on the 
		FRX4000/SS1840 and 19200 on all other products.  It may be possible
		to set the speed of a standard RS232 port to a speed which is valid
		for a high speed RS232 port but invalid for a standard RS232 port.
		In this case, the port may not end up having the invalid speed.  
		The default speed for a standard RS232 port on the FRX6000 is 19200."
    	DEFVAL { 64000 }

        ::= { portPhyX25AdminEntry 2 }

portPhyX25AdminGenerateClock      OBJECT-TYPE
        SYNTAX      INTEGER {
            no (1),
            yes (2)
         }
        ACCESS      read-write
        STATUS      mandatory
        DESCRIPTION
    		"Specifies whether the port will generate the clock
            necessary to synchronize traffic over the link."
		DEFVAL { no }
        ::= { portPhyX25AdminEntry 3 }

portPhyX25AdminRcvClockFromDTE      OBJECT-TYPE
        SYNTAX      INTEGER {
            no (1),
            yes (2)
            }
        ACCESS      read-write
        STATUS      mandatory
        DESCRIPTION
			"This object defines whether the receive clock
			will be used from the DTE."
		DEFVAL { no }
        ::= { portPhyX25AdminEntry 4 }

portPhyX25AdminDialOut      OBJECT-TYPE
    	SYNTAX  INTEGER {
               none(1),
               dialIn(2),
			   dialOut(3) 
               }
        ACCESS      read-write
        STATUS      mandatory
        DESCRIPTION
			"This flag indicates whether the port is connected to a dial
			modem, and whethter connections will be initiated through
			dial-in or dial-out calls." 
		DEFVAL { none }
        ::= { portPhyX25AdminEntry 5 }

portPhyX25AdminInactivityTimer      OBJECT-TYPE
        SYNTAX      INTEGER  (1..30)
        ACCESS      read-write
        STATUS      mandatory
        DESCRIPTION
			"This timer defines in minutes, the period of inactivity
			allowed between calls. Once the timer expires, the port
			is disabled untill the next call is placed, if a Dial out
			port, or the Disconnect Timer expires, if a Dial in port.
			This variable is only meaningful if the port is a Dial port."
		DEFVAL { 5 }
        ::= { portPhyX25AdminEntry 6 }

portPhyX25AdminDisconnectTimer      OBJECT-TYPE
        SYNTAX      INTEGER   (1..255)
        ACCESS      read-write
        STATUS      mandatory
        DESCRIPTION
			"This timer defines, in seconds, the length of time a
			dial-in port will remain disabled after expiration of the
			InActivity Timer."
		DEFVAL { 5 }
        ::= { portPhyX25AdminEntry 7 }

portPhyX25AdminSetupTimer      OBJECT-TYPE
        SYNTAX      INTEGER   (1..255)
        ACCESS      read-write
        STATUS      mandatory
        DESCRIPTION
			"This  timer determines the length of time, in seconds, that
			a response must be received by the port, after entering the
			Linkup state. If a response is not received, the port enters
			a Failed state."
		DEFVAL { 5 }
        ::= { portPhyX25AdminEntry 8 }

portPhyX25AdminTrunkFlag      OBJECT-TYPE
    	SYNTAX  INTEGER {
               no(1),
               yes(2)
               }
        ACCESS      read-write
        STATUS      mandatory
        DESCRIPTION
			"This flag, when set, indicates the port is associated
			with a network trunk group.  It will be disabled/enabled
			if the network trunk is not operational."
		DEFVAL { no }
        ::= { portPhyX25AdminEntry 9 }

portPhyX25AdminTrunkGroup      OBJECT-TYPE
        SYNTAX      OCTET STRING
        ACCESS      read-write
        STATUS      mandatory
        DESCRIPTION
			"This variable contains a string of 8 bytes, with each
			byte indicating 8 ports on an RLP that may be a part of
			a trunk group. Since a TurboFrad has only 1 RLP, only the
			first byte is valid if the node is an FRX4000. Each
			port is represented by a single bit within the RLP byte.
			The bit position represents the port number...for example,
			if port 2 on RLP 0 was in a trunk group, the first byte of
			the string would contain x04 and all other bytes would be 0."
        ::= { portPhyX25AdminEntry 10 }

portPhyX25AdminRowStatus      OBJECT-TYPE
        SYNTAX      RowStatus
        ACCESS      read-write
        STATUS      mandatory
        DESCRIPTION
            "This variable is used to manage the creation and deletion
            of conceptual rows in the portPhyX25AdminTable and follows the
            SNMPv2 RowStatus conventions by supporting the following values:

                 - `active', which indicates that the conceptual row is
                available for use by the managed device, and which is
                supplied by a management station wishing to exercise an
                on-line update of the existing conceptual row.  For a
                management protocol set operation, a genErr response is
                returned when the row does not exist.

                 - `createAndGo', which is supplied by a management
                 station wishing to create a new instance of a
                 conceptual row and to have its status automatically set
                 to active, making it available for use by the managed
                 device.  For a management protocol set operation, a
                 genErr response is returned when the row already exists.

                 - `destroy', which is supplied by a management station
                 wishing to delete all of the instances associated with
                 an existing conceptual row.

            Note that all of the above values may be specified in a
            management protocol set operation, and only the 'active'
            value will be returned in response to a management protocol
            retrieval operation.  For a management protocol set operation,
            if other variable bindings are included in the same PDU, then
            a genErr response is returned."
        ::= { portPhyX25AdminEntry 11 }

portPhyX25OperTable  OBJECT-TYPE
       SYNTAX      SEQUENCE OF PortPhyX25OperEntry
       ACCESS      not-accessible
       STATUS      mandatory
       DESCRIPTION
               "This table contains Netlink Enterprise specific
               objects to manage an X25 port. Changing one of
               these parameters may take effect in the operating
               port immediately or may wait until the interface is
               restarted depending on the details of the
               implementation.

               All of the objects in this table are read-only.

               The operating values may be different from these
               configured values if a configured parameter was
               configured after the interface was started."
           ::= { portX25Group 2 }

portPhyX25OperEntry  OBJECT-TYPE
                    SYNTAX      PortPhyX25OperEntry
                    ACCESS      not-accessible
                    STATUS      mandatory
                    DESCRIPTION
                            "A list of configured values for an X25 port."
                    INDEX   { nlIfRlp, nlIfPort }
                    ::= { portPhyX25OperTable 1 }

PortPhyX25OperEntry  ::= SEQUENCE
{
        portPhyX25OperConnector   		INTEGER,
        portPhyX25OperSpeed       		INTEGER,
        portPhyX25OperGenerateClock 	INTEGER,
        portPhyX25OperRcvClockFromDTE 	INTEGER,
        portPhyX25OperDialOut		   	INTEGER,
        portPhyX25OperInactivityTimer	INTEGER,
        portPhyX25OperDisconnectTimer	INTEGER,
        portPhyX25OperSetupTimer		INTEGER,
        portPhyX25OperTrunkFlag	 		INTEGER,
        portPhyX25OperTrunkGroup	 	OCTET STRING
}

portPhyX25OperConnector    OBJECT-TYPE
        SYNTAX      INTEGER{
        	rs232 (3),
           	v35 (5),
           	rs449 (6),
           	rs530 (7),
           	x21 (8),
           	t1 (10),
           	e1 (11)
           }
        ACCESS      read-only
        STATUS      mandatory
        DESCRIPTION
			"Physical port interface connector type."
        ::= { portPhyX25OperEntry 1 }

portPhyX25OperSpeed      OBJECT-TYPE
        SYNTAX      INTEGER 
        ACCESS      read-only
        STATUS      mandatory
        DESCRIPTION
		"This object defines the speed of the X25 port.  The speed may
	 	only be set to one of a series of reasonable values, and if an attempt 
		is made to set the speed to a value which is within the valid range
		but not equal to one of these values, the speed will be rounded up. 
		If the connector type of the port is RS232, the port could be a
		standard port or a high speed port.  If the port is a high speed
		RS232 port, the maximum valid speed is 256000.  If the port is a 
		standard RS232 port, the maximum valid speed is 64000 on the 
		FRX4000/SS1840 and 19200 on all other products.  It may be possible
		to set the speed of a standard RS232 port to a speed which is valid
		for a high speed RS232 port but invalid for a standard RS232 port.
		In this case, the port may not end up having the invalid speed.  
		The default speed for a standard RS232 port on the FRX6000 is 19200."
        ::= { portPhyX25OperEntry 2 }

portPhyX25OperGenerateClock      OBJECT-TYPE
        SYNTAX      INTEGER {
            no (1),
            yes (2)
         }
        ACCESS      read-only
        STATUS      mandatory
        DESCRIPTION
    		"Specifies whether the port will generate the clock
            necessary to synchronize traffic over the link."
        ::= { portPhyX25OperEntry 3 }

portPhyX25OperRcvClockFromDTE      OBJECT-TYPE
        SYNTAX      INTEGER {
            no (1),
            yes (2)
            }
        ACCESS      read-only
        STATUS      mandatory
        DESCRIPTION
			"This object defines whether the receive clock will be
			used from the DTE."
        ::= { portPhyX25OperEntry 4 }

portPhyX25OperDialOut      OBJECT-TYPE
    	SYNTAX  INTEGER {
               none(1),
               dialIn(2),
               dialOut(3)
               }
        ACCESS      read-only
        STATUS      mandatory
        DESCRIPTION
			"This flag indicates whether the port is connected to a dial
			modem, and whethter connections will be initiated through
			dial-in or dial-out calls." 
        ::= { portPhyX25OperEntry 5 }

portPhyX25OperInactivityTimer      OBJECT-TYPE
        SYNTAX      INTEGER  (1..30)
        ACCESS      read-only
        STATUS      mandatory
        DESCRIPTION
			"This timer defines in minutes, the period of inactivity
			allowed between calls. Once the timer expires, the port
			is disabled untill the next call is placed, if a Dial out
			port, or the Disconnect Timer expires, if a Dial in port.
			This variable is only meaningful if the port is a Dial port."
        ::= { portPhyX25OperEntry 6 }

portPhyX25OperDisconnectTimer      OBJECT-TYPE
        SYNTAX      INTEGER   (1..255)
        ACCESS      read-only
        STATUS      mandatory
        DESCRIPTION
			"This timer defines, in seconds, the length of time a
			dial-in port will remain disabled after expiration of the
			InActivity Timer."
        ::= { portPhyX25OperEntry 7 }

portPhyX25OperSetupTimer      OBJECT-TYPE
        SYNTAX      INTEGER   (1..255)
        ACCESS      read-only
        STATUS      mandatory
        DESCRIPTION
			"This  timer determines the length of time, in seconds, that
			a response must be received by the port, after entering the
			Linkup state. If a response is not received, the port enters
			a Failed state."
        ::= { portPhyX25OperEntry 8 }

portPhyX25OperTrunkFlag      OBJECT-TYPE
    	SYNTAX  INTEGER {
               no(1),
               yes(2)
               }
        ACCESS      read-only
        STATUS      mandatory
        DESCRIPTION
			"This flag, when set, indicates the port is associated
			with a network trunk group.  It will be disabled/enabled
			if the network trunk is not operational."
        ::= { portPhyX25OperEntry 9 }

portPhyX25OperTrunkGroup      OBJECT-TYPE
        SYNTAX      OCTET STRING
        ACCESS      read-only
        STATUS      mandatory
        DESCRIPTION
			"This variable contains a string of 8 bytes, with each
			byte indicating a port on this RLP that may be a part of
			a trunk group."
        ::= { portPhyX25OperEntry 10 }

-- Admin Table for X25 logical ports

portLogicalX25AdminTable  OBJECT-TYPE
        SYNTAX      SEQUENCE OF PortLogicalX25AdminEntry
        ACCESS      not-accessible
        STATUS      mandatory
        DESCRIPTION
           "This table contains Netlink Enterprise specific
           objects to manage an X25 Logical port. Changing one of
           these parameters may take effect in the operating
           port immediately or may wait until the interface is
           restarted depending on the details of the
           implementation.

           The operating values may be different from these
           configured values if a configured parameter was
           configured after the interface was started."
           ::= { portX25Group 3 }

portLogicalX25AdminEntry  OBJECT-TYPE
       SYNTAX      PortLogicalX25AdminEntry
       ACCESS      not-accessible
       STATUS      mandatory
       DESCRIPTION
           "A list of configured values for an X25 logical port."
       INDEX   { nlIfRlp, nlIfPhyPort, nlIfPort }
                    ::= { portLogicalX25AdminTable 1 }

PortLogicalX25AdminEntry  ::= SEQUENCE
{
        portLogicalX25AdminFrDlci	INTEGER,
        portLogicalX25AdminCxnPriority INTEGER,
        portLogicalX25AdminRfc1490 	INTEGER,
        portLogicalX25AdminBAG	 	INTEGER,
        portLogicalX25AdminRowStatus 	RowStatus 
}

portLogicalX25AdminFrDlci      OBJECT-TYPE
        SYNTAX      INTEGER   (16..991)
        ACCESS      read-write
        STATUS      mandatory
        DESCRIPTION
            " The DLCI number used to identify the entry in the table. The
            range is 16-991. "
		DEFVAL { 16 }
        ::= { portLogicalX25AdminEntry 1 }

portLogicalX25AdminCxnPriority      OBJECT-TYPE
        SYNTAX      INTEGER   (0..9)
        ACCESS      read-write
        STATUS      mandatory
        DESCRIPTION
            " This field sets the priority of the connection among others on the
            physical port. The range is 0 for lowest priority to 9 for
            the highest priority. "
		DEFVAL { 0 }
        ::= { portLogicalX25AdminEntry 2 }

portLogicalX25AdminRfc1490      OBJECT-TYPE
        SYNTAX      INTEGER  {
				annexG (1),
				rfc1490 (2)
				}
        ACCESS      read-write
        STATUS      mandatory
        DESCRIPTION
			" This field indicates the encapsulation method used"
		DEFVAL { rfc1490 }
        ::= { portLogicalX25AdminEntry 3 }

portLogicalX25AdminBAG      OBJECT-TYPE
        SYNTAX      INTEGER   (0..16)
        ACCESS      read-write
        STATUS      mandatory
        DESCRIPTION
          "Assigns this DLCI to one of sixteen groups whose parameters
          regulate bandwidth usage. A 0 value indicates the DLCI does
          not use BAGs"
		DEFVAL { 0 }
        ::= { portLogicalX25AdminEntry 4 }

portLogicalX25AdminRowStatus      OBJECT-TYPE
        SYNTAX      RowStatus
        ACCESS      read-write
        STATUS      mandatory
        DESCRIPTION
            "This variable is used to manage the creation and deletion
            of conceptual rows in the portLogicalX25AdminTable and follows the
            SNMPv2 RowStatus conventions by supporting the following values:

                 - `active', which indicates that the conceptual row is
                available for use by the managed device, and which is
                supplied by a management station wishing to exercise an
                on-line update of the existing conceptual row.  For a
                management protocol set operation, a genErr response is
                returned when the row does not exist.

                 - `createAndGo', which is supplied by a management
                 station wishing to create a new instance of a
                 conceptual row and to have its status automatically set
                 to active, making it available for use by the managed
                 device.  For a management protocol set operation, a
                 genErr response is returned when the row already exists.

                 - `destroy', which is supplied by a management station
                 wishing to delete all of the instances associated with
                 an existing conceptual row.

            Note that all of the above values may be specified in a
            management protocol set operation, and only the 'active'
            value will be returned in response to a management protocol
            retrieval operation.  For a management protocol set operation,
            if other variable bindings are included in the same PDU, then
            a genErr response is returned."
        ::= { portLogicalX25AdminEntry 5 }

-- Oper Table for X25 logical ports

portLogicalX25OperTable  OBJECT-TYPE

        SYNTAX      SEQUENCE OF PortLogicalX25OperEntry
        ACCESS      not-accessible
        STATUS      mandatory
        DESCRIPTION
           "This table contains Netlink Enterprise specific
           objects to manage an X25 Logical port. Changing one of
           these parameters may take effect in the operating
           port immediately or may wait until the interface is
           restarted depending on the details of the
           implementation.

           The operating values may be different from these
           configured values if a configured parameter was
           configured after the interface was started."
           ::= { portX25Group 4 }

portLogicalX25OperEntry  OBJECT-TYPE
       SYNTAX      PortLogicalX25OperEntry
       ACCESS      not-accessible
       STATUS      mandatory
       DESCRIPTION
           "A list of configured values for an X25 port."
       INDEX   { nlIfRlp, nlIfPhyPort, nlIfPort }
                    ::= { portLogicalX25OperTable 1 }

PortLogicalX25OperEntry  ::= SEQUENCE
{
        portLogicalX25OperFrDlci	INTEGER,
        portLogicalX25OperCxnPriority INTEGER,
        portLogicalX25OperRfc1490 	INTEGER,
        portLogicalX25OperBAG	 	INTEGER
}

portLogicalX25OperFrDlci      OBJECT-TYPE
        SYNTAX      INTEGER   (1..255)
        ACCESS      read-only
        STATUS      mandatory
        DESCRIPTION
            " The DLCI number used to identify the entry in the table. The
            range is 16-991. "

        ::= { portLogicalX25OperEntry 1 }

portLogicalX25OperCxnPriority      OBJECT-TYPE
        SYNTAX      INTEGER   (0..9)
        ACCESS      read-only
        STATUS      mandatory
        DESCRIPTION
            " This field sets the priority of the connection among others on the
            physical port. The range is 0 for lowest priority to 9 for
            the highest priority. "
        ::= { portLogicalX25OperEntry 2 }

portLogicalX25OperRfc1490      OBJECT-TYPE
        SYNTAX      INTEGER  {
				annexG (1),
				rfc1490 (2)
				}
        ACCESS      read-only
        STATUS      mandatory
        DESCRIPTION
			" This field indicates the encapsulation method used"
        ::= { portLogicalX25OperEntry 3 }

portLogicalX25OperBAG      OBJECT-TYPE
        SYNTAX      INTEGER   (1..16)
        ACCESS      read-only
        STATUS      mandatory
        DESCRIPTION
          "Assigns this DLCI to one of sixteen groups whose parameters
          regulate bandwidth usage."
        ::= { portLogicalX25OperEntry 4 }

-- Admin Table for both logical and physical ports
--

portX25AdminTable  OBJECT-TYPE
       SYNTAX      SEQUENCE OF PortX25AdminEntry
       ACCESS      not-accessible
       STATUS      mandatory
       DESCRIPTION
               "This table contains Netlink Enterprise specific
               objects to manage an X25 port. Changing one of
               these parameters may take effect in the operating
               port immediately or may wait until the interface is
               restarted depending on the details of the
               implementation.

               Most of the objects in this read-write table have
               corresponding read-only objects in the
               portX25OperTable that return the current
               operating value.

               The operating values may be different from these
               configured values if a configured parameter was
               configured after the interface was started."
         ::= { portX25Group 5 }

portX25AdminEntry  OBJECT-TYPE
       SYNTAX      PortX25AdminEntry
       ACCESS      not-accessible
       STATUS      mandatory
       DESCRIPTION
             "A list of configured values for an X25 port."
          INDEX   { nlIfRlp, nlIfPort }

    ::= { portX25AdminTable 1 }

PortX25AdminEntry ::= SEQUENCE
{
        portX25AdminBlockedFlag		INTEGER,
        portX25AdminFlowCtrlNeg 		INTEGER,
        portX25AdminThruptClassNeg 	INTEGER,
        portX25AdminLocChgPrev 		INTEGER,
        portX25AdminRevChgAccpt 	INTEGER,
        portX25AdminFastSelAccpt 	INTEGER,
        portX25AdminInCallBar 		INTEGER,
        portX25AdminOutCallBar 		INTEGER,
        portX25AdminMaxPktSize 		INTEGER,
        portX25AdminDefPktSize 		INTEGER,
        portX25AdminMaxWinSize 		INTEGER,
        portX25AdminDefWinSize 		INTEGER,
        portX25AdminMaxThruptClass 	INTEGER,
        portX25AdminCUGPref   		INTEGER,
        portX25AdminCUGIndex   		INTEGER,
        portX25AdminCUGIncAccess	INTEGER,
        portX25AdminCUGOutAccess   	INTEGER
}

portX25AdminBlockedFlag OBJECT-TYPE
        SYNTAX  INTEGER {
               no(1),
               yes(2)
               }
        ACCESS  read-write
        STATUS  mandatory
        DESCRIPTION
            " A flag which when set, means the port should not be
            enabled after a boot-up of the node. "
		DEFVAL { no }
        ::= { portX25AdminEntry 1 }

portX25AdminFlowCtrlNeg      OBJECT-TYPE
        SYNTAX      INTEGER {
            no (1),
            yes (2)
            }
        ACCESS      read-write
        STATUS      mandatory
        DESCRIPTION
           "A flag which if set, permits negotiation of
           the flow control parameters on a per call basis.
           If N is selected, the default packet and window
           sizes will be used. If Y is selected, the packet
           or window size in a call packet (up to the
           configured Max Packet Size or Max Window Size) is
           used."
		DEFVAL { no }
        ::= { portX25AdminEntry 2 }

portX25AdminThruptClassNeg      OBJECT-TYPE
        SYNTAX      INTEGER {
            no (1),
            yes (2)
            }
        ACCESS      read-write
        STATUS      mandatory
        DESCRIPTION
            "A flag which ,if set, permists negotiation of
            the throughput class for either direction of
            data transmission on a per call basis. If N is
            selected, the configured Max Throughput Class
            value is used.  If Y, any throughput class in
            a call packet (up to the Max Thruput Class) is
            used."
		DEFVAL { no }
         ::= { portX25AdminEntry 3 }

portX25AdminLocChgPrev      OBJECT-TYPE
        SYNTAX      INTEGER {
            no (1),
            yes (2)
            }
        ACCESS      read-write
        STATUS      mandatory
        DESCRIPTION
            "If Y is selected, no calls can be charged to
            port.  Incoming calls from the network with
            reverse charge specified will be rejected. Outgoing
            calls will insert reverse charge in the call packet
            if not already included."
		DEFVAL { no }
         ::= { portX25AdminEntry 4 }

portX25AdminRevChgAccpt      OBJECT-TYPE
        SYNTAX      INTEGER {
            no (1),
            yes (2)
            }
        ACCESS      read-write
        STATUS      mandatory
        DESCRIPTION
            "A flag, if set, that authorizes transmission of
            incoming calls that request the reverse charge
            facility. If N is selected, and a call requests
            it, it will not be transmitted."
		DEFVAL { no }
         ::= { portX25AdminEntry 5 }

portX25AdminFastSelAccpt      OBJECT-TYPE
        SYNTAX      INTEGER {
            no (1),
            yes (2)
            }
        ACCESS      read-write
        STATUS      mandatory
        DESCRIPTION
            "A flag, if set, that authorizes transmission of
            incoming calls that request the Fast Select
            facility."
		DEFVAL { no }
         ::= { portX25AdminEntry 6 }

portX25AdminInCallBar      OBJECT-TYPE
        SYNTAX      INTEGER {
            no (1),
            yes (2)
            }
        ACCESS      read-write
        STATUS      mandatory
        DESCRIPTION
            "An X25 facility that prevents transmission of
            incoming calls to the local DTE."
		DEFVAL { no }
         ::= { portX25AdminEntry 7 }

portX25AdminOutCallBar      OBJECT-TYPE
        SYNTAX      INTEGER {
            no (1),
            yes (2)
            }
        ACCESS      read-write
        STATUS      mandatory
        DESCRIPTION
            "An X25 facility that prevents transmission of
             incoming calls to the local DTE."
		DEFVAL { no }
        ::= { portX25AdminEntry 8 }

portX25AdminMaxPktSize      OBJECT-TYPE
        SYNTAX      INTEGER  (128..4096)
        ACCESS      read-write
        STATUS      mandatory
        DESCRIPTION
			" The maximum data packet size that will be allowed to pass
            through this port."
		DEFVAL { 1024 }
        ::= { portX25AdminEntry 9 }

portX25AdminDefPktSize      OBJECT-TYPE
        SYNTAX      INTEGER		(16..4096)
        ACCESS      read-write
        STATUS      mandatory
        DESCRIPTION
			"This is the size that will be assigned to an incoming call
			setup packet if the packet does not request a packet size."
		DEFVAL { 128 }
        ::= { portX25AdminEntry 10 }

portX25AdminMaxWinSize      OBJECT-TYPE
        SYNTAX      INTEGER  (2..7)
        ACCESS      read-write
        STATUS      mandatory
        DESCRIPTION
			"This is the maximum number of unacknowledged packets
			per logical channel that can pass through this port."
		DEFVAL { 7 }
        ::= { portX25AdminEntry 11 }

portX25AdminDefWinSize      OBJECT-TYPE
        SYNTAX      INTEGER (1..7)
        ACCESS      read-write
        STATUS      mandatory
        DESCRIPTION
			"This size will be assigned to an incoming call
			setup packet if the packet doesn't request a window size."
		DEFVAL { 2 }
        ::= { portX25AdminEntry 12 }

portX25AdminMaxThruptClass      OBJECT-TYPE
        SYNTAX      INTEGER  (3..13)
        ACCESS      read-write
        STATUS      mandatory
        DESCRIPTION
			"This specifies the default throughput class that will be
			inserted into a Call Request packet if Thruput Class
			negotiation is not enabled or if a thruput class is not
			requested in the call request."
        ::= { portX25AdminEntry 13 }

portX25AdminCUGPref      OBJECT-TYPE
    	SYNTAX  INTEGER {
               no(1),
               yes(2)
               }
        ACCESS      read-write
        STATUS      mandatory
        DESCRIPTION
			"This flag, if set, indicates the port belongs to at least
			one CUG."
		DEFVAL { no }
        ::= { portX25AdminEntry 14 }

portX25AdminCUGIndex      OBJECT-TYPE
        SYNTAX      INTEGER  (1..100)
        ACCESS      read-write
        STATUS      mandatory
        DESCRIPTION
			"This number is an index into a Closed User Group table
			which identifies the default Closed User Group for the
			port."
		DEFVAL { 1 }
        ::= { portX25AdminEntry 15 }

portX25AdminCUGIncAccess      OBJECT-TYPE
    	SYNTAX  INTEGER {
               no(1),
               yes(2)
               }
        ACCESS      read-write
        STATUS      mandatory
        DESCRIPTION
			" This flag, when set, indicates whether this port will
			be allowed to receive calls from outside its CUGs."
		DEFVAL { no }
        ::= { portX25AdminEntry 16 }

portX25AdminCUGOutAccess      OBJECT-TYPE
    	SYNTAX  INTEGER {
               no(1),
               yes(2)
               }
        ACCESS      read-write
        STATUS      mandatory
        DESCRIPTION
			" This flag, when set, indicates whether this port will
			be allowed to make calls outside its CUGs."
		DEFVAL { no }
        ::= { portX25AdminEntry 17 }

portX25OperTable  OBJECT-TYPE
       SYNTAX      SEQUENCE OF PortX25OperEntry
       ACCESS      not-accessible
       STATUS      mandatory
       DESCRIPTION
               "This table contains Netlink Enterprise specific
               objects to manage an X25 port. Changing one of
               these parameters may take effect in the operating
               port immediately or may wait until the interface is
               restarted depending on the details of the
               implementation.

               The objects in this read-only table 
               corresponding read-only objects in the
               portX25OperTable that return the current
               operating value.

               The operating values may be different from these
               configured values if a configured parameter was
               configured after the interface was started."
         ::= { portX25Group 6 }

portX25OperEntry  OBJECT-TYPE
       SYNTAX      PortX25OperEntry
       ACCESS      not-accessible
       STATUS      mandatory
       DESCRIPTION
             "A list of configured values for an X25 port."
          INDEX   { nlIfRlp, nlIfPort }
    ::= { portX25OperTable 1 }

PortX25OperEntry ::= SEQUENCE {
        portX25OperBlockedFlag	INTEGER,
        portX25OperFlowCtrlNeg 		INTEGER,
        portX25OperThruptClassNeg 	INTEGER,
        portX25OperLocChgPrev 		INTEGER,
        portX25OperRevChgAccpt 		INTEGER,
        portX25OperFastSelAccpt 	INTEGER,
        portX25OperInCallBar 		INTEGER,
        portX25OperOutCallBar 		INTEGER,
        portX25OperMaxPktSize 		INTEGER,
        portX25OperDefPktSize 		INTEGER,
        portX25OperMaxWinSize 		INTEGER,
        portX25OperDefWinSize 		INTEGER,
        portX25OperMaxThruptClass 	INTEGER,
        portX25OperCUGPref   		INTEGER,
        portX25OperCUGIndex   		INTEGER,
        portX25OperCUGIncAccess		INTEGER,
        portX25OperCUGOutAccess   	INTEGER
}

portX25OperBlockedFlag OBJECT-TYPE
        SYNTAX  INTEGER {
               no(1),
               yes(2)
               }
        ACCESS  read-only
        STATUS  mandatory
        DESCRIPTION
            " A flag which when set, means the port should not be
            enabled after a boot-up of the node. "
        ::= { portX25OperEntry 1 }

portX25OperFlowCtrlNeg      OBJECT-TYPE
        SYNTAX      INTEGER {
            no (1),
            yes (2)
            }
        ACCESS      read-only
        STATUS      mandatory
        DESCRIPTION
           "A flag which if set, permits negotiation of
           the flow control parameters on a per call basis.
           If N is selected, the default packet and window
           sizes will be used. If Y is selected, the packet
           or window size in a call packet (up to the
           configured Max Packet Size or Max Window Size) is
           used."
        ::= { portX25OperEntry 2 }

portX25OperThruptClassNeg      OBJECT-TYPE
        SYNTAX      INTEGER {
            no (1),
            yes (2)
            }
        ACCESS      read-only
        STATUS      mandatory
        DESCRIPTION
            "A flag which ,if set, permists negotiation of
            the throughput class for either direction of
            data transmission on a per call basis. If N is
            selected, the configured Max Throughput Class
            value is used.  If Y, any throughput class in
            a call packet (up to the Max Thruput Class) is
            used."
         ::= { portX25OperEntry 3 }

portX25OperLocChgPrev      OBJECT-TYPE
        SYNTAX      INTEGER {
            no (1),
            yes (2)
            }
        ACCESS      read-only
        STATUS      mandatory
        DESCRIPTION
            "If Y is selected, no calls can be charged to
            port.  Incoming calls from the network with
            reverse charge specified will be rejected. Outgoing
            calls will insert reverse charge in the call packet
            if not already included."
         ::= { portX25OperEntry 4 }

portX25OperRevChgAccpt      OBJECT-TYPE
        SYNTAX      INTEGER {
            no (1),
            yes (2)
            }
        ACCESS      read-only
        STATUS      mandatory
        DESCRIPTION
            "A flag, if set, that authorizes transmission of
            incoming calls that request the reverse charge
            facility. If N is selected, and a call requests
            it, it will not be transmitted."
         ::= { portX25OperEntry 5 }

portX25OperFastSelAccpt     OBJECT-TYPE
        SYNTAX      INTEGER {
            no (1),
            yes (2)
            }
        ACCESS      read-only
        STATUS      mandatory
        DESCRIPTION
            "A flag, if set, that authorizes transmission of
            incoming calls that request the Fast Select
            facility."
         ::= { portX25OperEntry 6 }

portX25OperInCallBar      OBJECT-TYPE
        SYNTAX      INTEGER {
            no (1),
            yes (2)
            }
        ACCESS      read-only
        STATUS      mandatory
        DESCRIPTION
            "An X25 facility that prevents transmission of
            incoming calls to the local DTE."
         ::= { portX25OperEntry 7 }

portX25OperOutCallBar      OBJECT-TYPE
        SYNTAX      INTEGER {
            no (1),
            yes (2)
            }
        ACCESS      read-only
        STATUS      mandatory
        DESCRIPTION
            "An X25 facility that prevents transmission of
             incoming calls to the local DTE."
        ::= { portX25OperEntry 8 }

portX25OperMaxPktSize      OBJECT-TYPE
        SYNTAX      INTEGER  (128..4096)
        ACCESS      read-only
        STATUS      mandatory
        DESCRIPTION
			" The maximum data packet size that will be allowed to pass
            through this port."
        ::= { portX25OperEntry 9 }

portX25OperDefPktSize      OBJECT-TYPE
        SYNTAX      INTEGER		(16..4096)
        ACCESS      read-only
        STATUS      mandatory
        DESCRIPTION
			"This is the size that will be assigned to an incoming call
			setup packet if the packet does not request a packet size."
        ::= { portX25OperEntry 10 }

portX25OperMaxWinSize      OBJECT-TYPE
        SYNTAX      INTEGER  (2..7)
        ACCESS      read-only
        STATUS      mandatory
        DESCRIPTION
			"This is the maximum number of unacknowledged packets
			per logical channel that can pass through this port."
        ::= { portX25OperEntry 11 }

portX25OperDefWinSize      OBJECT-TYPE
        SYNTAX      INTEGER (1..7)
        ACCESS      read-only
        STATUS      mandatory
        DESCRIPTION
			"This size will be assigned to an incoming call
			setup packet if the packet doesn't request a window size."
        ::= { portX25OperEntry 12 }

portX25OperMaxThruptClass      OBJECT-TYPE
        SYNTAX      INTEGER  (3..13)
        ACCESS      read-only
        STATUS      mandatory
        DESCRIPTION
			"This specifies the default throughput class that will be
			inserted into a Call Request packet if Thruput Class
			negotiation is not enabled or if a thruput class is not
			requested in the call request."
        ::= { portX25OperEntry 13 }

portX25OperCUGPref      OBJECT-TYPE
    	SYNTAX  INTEGER {
               no(1),
               yes(2)
               }
        ACCESS      read-only
        STATUS      mandatory
        DESCRIPTION
			"This flag, if set, indicates the port belongs to at least
			one CUG."
        ::= { portX25OperEntry 14 }

portX25OperCUGIndex      OBJECT-TYPE
        SYNTAX      INTEGER  (1..100)
        ACCESS      read-only
        STATUS      mandatory
        DESCRIPTION
			"This number is an index into a Closed User Group table
			which identifies the default Closed User Group for the
			port."
        ::= { portX25OperEntry 15 }

portX25OperCUGIncAccess      OBJECT-TYPE
    	SYNTAX  INTEGER {
               no(1),
               yes(2)
               }
        ACCESS      read-only
        STATUS      mandatory
        DESCRIPTION
			" This flag, when set, indicates whether this port will
			be able to receive calls from outside its CUGs."
        ::= { portX25OperEntry 16 }

portX25OperCUGOutAccess      OBJECT-TYPE
    	SYNTAX  INTEGER {
               no(1),
               yes(2)
               }
        ACCESS      read-only
        STATUS      mandatory
        DESCRIPTION
			" This flag, when set, indicates whether this port will
			be able to make calls outside its CUGs."
        ::= { portX25OperEntry 17 }

portFrGroup OBJECT IDENTIFIER ::=  { port 2 }

-- The Frame Relay Port Configuration table
-- contains information on the FR physical port.

portFrConfigTable OBJECT-TYPE
    SYNTAX  SEQUENCE OF PortFrEntry
    ACCESS  not-accessible
    STATUS  mandatory
    DESCRIPTION
            "A list of Frame Relay ports .  The number of
            entries will be the number of Frame Relay ports on the node."
    ::= { portFrGroup 1 }

portFrEntry OBJECT-TYPE
    SYNTAX  PortFrEntry
    ACCESS  not-accessible
    STATUS  mandatory
    DESCRIPTION
            "An Frame Relay Port entry containing objects
            relating to the port that are configurable
            by the user."
    INDEX   {  portFrRlpIndex , portFrPortIndex }
    ::= { portFrConfigTable 1 }

PortFrEntry ::=
    SEQUENCE {
        portFrRlpIndex
            INTEGER,
        portFrPortIndex
        INTEGER,
        portFrBlockedFlag
            INTEGER,
        portFrMaxBytesPerFrame
            INTEGER,
        portFrT392Timer
            INTEGER,
        portFrOutgoingRateControl
            INTEGER,
        portFrBandwidthAllocation
            INTEGER,
        portFrConnector
         INTEGER,
        portFrLogicalDCE
         INTEGER,
        portFrGenClock
            INTEGER,
        portFrRcvClkFrmDTE
            INTEGER,
        portFrLLM
            INTEGER,
        portFrRowStatus
            RowStatus,
        portFrSpeed
            INTEGER,
        portFrBackupUseOnly
            INTEGER
    }
portFrRlpIndex OBJECT-TYPE
    SYNTAX  INTEGER
    ACCESS  read-only
    STATUS  mandatory
    DESCRIPTION
            " The RLP number of the Frame Relay port. It will be in the
            range 1-8."
    ::= { portFrEntry 1 }
portFrPortIndex OBJECT-TYPE
    SYNTAX  INTEGER
    ACCESS  read-only
    STATUS  mandatory
    DESCRIPTION
            " The Port number of the Frame Relay port. It will
            be in the range 1-8 for a physical port. It will be in the range
            9-64 for a Frame Relay logical port."
    ::= { portFrEntry 2 }

portFrBlockedFlag OBJECT-TYPE
    SYNTAX  INTEGER {
                no(1),
                yes(2)
                }
    ACCESS  read-write
    STATUS  mandatory
    DESCRIPTION
            " A flag which when set, means the port should not be
            enabled after a boot-up of the node. "
    DEFVAL { no }
    ::= { portFrEntry 3 }

portFrMaxBytesPerFrame OBJECT-TYPE
    SYNTAX  INTEGER (16..4096)
    ACCESS  read-write
    STATUS  mandatory
    DESCRIPTION
            " The maximum number of bytes allowed in an I Frame for this
            Frame Relay port."
    DEFVAL { 1600 }
    ::= { portFrEntry 4 }

portFrT392Timer OBJECT-TYPE
    SYNTAX  INTEGER (5..30)
    ACCESS  read-write
    STATUS  mandatory
    DESCRIPTION
            "This timer indicates how long the network will wait between
            Status Enquiry messages before recording an error.  It
            should be greater than or equal to the frDlcmiPollingInterval
            variable in the RFC1315 Mib."
    DEFVAL { 15 }
    ::= { portFrEntry 5 }

portFrOutgoingRateControl OBJECT-TYPE
    SYNTAX  INTEGER {
                no(1),
                yes(2)
                }
    ACCESS  read-write
    STATUS  mandatory
    DESCRIPTION
            " This is a flag which, when set, enables the enforcement of
            the Outgoing Rate Control parameters."
    DEFVAL { no }
    ::= { portFrEntry 6 }

portFrBandwidthAllocation OBJECT-TYPE
    SYNTAX  INTEGER {
                no(1),
                yes(2)
                }
    ACCESS  read-write
    STATUS  mandatory
    DESCRIPTION
            " This is a flag which, when set, enables whether the bandwidth
            allocation will be enforced. "
    DEFVAL { no }
    ::= { portFrEntry 7 }

portFrConnector OBJECT-TYPE
    SYNTAX  INTEGER {
                rs232 (3),
                v35 (5),
                rs449 (6),
                rs530 (7),
                x21 (8),
                t1 (10),
                e1 (11)
            }
    ACCESS  read-write
    STATUS  mandatory
    DESCRIPTION
            "This defines the connector type of the Frame Relay port."
    ::= { portFrEntry 8 }

portFrLogicalDCE OBJECT-TYPE
    SYNTAX  INTEGER {
                no(1),
                yes(2)
            }
    ACCESS  read-write
    STATUS  mandatory
    DESCRIPTION
            "This defines the port as logical DCE or DTE."
    DEFVAL { no }
    ::= { portFrEntry 9 }

portFrGenClock OBJECT-TYPE
    SYNTAX  INTEGER {
                no(1),
                yes(2)
            }
    ACCESS  read-write
    STATUS  mandatory
    DESCRIPTION
            "This specifies whether the port will generate the clock
             necessary to synchronize traffic over the link."
    DEFVAL { no }
    ::= { portFrEntry 10 }

portFrRcvClkFrmDTE OBJECT-TYPE
    SYNTAX  INTEGER {
                no(1),
                yes(2)
            }
    ACCESS  read-write
    STATUS  mandatory
    DESCRIPTION
            "This allows the clock to be looped back from the DTE using
             the TT (Terminal Timing) signal, which can be helpful on
             high-speed lines."
    DEFVAL { no }
    ::= { portFrEntry 11 }

portFrLLM OBJECT-TYPE
    SYNTAX  INTEGER {
                none(1),
                lmi(2),
                annexd(3)
            }
    ACCESS  read-write
    STATUS  mandatory
    DESCRIPTION
            "This determines whether, and what type of, configurable
             network management (status enquiries) will be allowed."
    DEFVAL { annexd }
    ::= { portFrEntry 12 }

portFrRowStatus OBJECT-TYPE
    SYNTAX  RowStatus
    ACCESS  read-write
    STATUS  mandatory
    DESCRIPTION
            "This variable is used to manage the creation and deletion
            of conceptual rows in the portFrConfigTable and follows the
            SNMPv2 RowStatus conventions by supporting the following values:

                 - `active', which indicates that the conceptual row is
                available for use by the managed device, and which is
                supplied by a management station wishing to exercise an
                on-line update of the existing conceptual row.  For a
                management protocol set operation, a genErr response is
                returned when the row does not exist.

                 - `createAndGo', which is supplied by a management
                 station wishing to create a new instance of a
                 conceptual row and to have its status automatically set
                 to active, making it available for use by the managed
                 device.  For a management protocol set operation, a
                 genErr response is returned when the row already exists.

                 - `destroy', which is supplied by a management station
                 wishing to delete all of the instances associated with
                 an existing conceptual row.

            Note that all of the above values may be specified in a
            management protocol set operation, and only the 'active'
            value will be returned in response to a management protocol
            retrieval operation.  For a management protocol set operation,
            if other variable bindings are included in the same PDU, then
            a genErr response is returned."
    ::= { portFrEntry 13 }

portFrSpeed OBJECT-TYPE
    SYNTAX      INTEGER (75..2048000)
    ACCESS      read-write
    STATUS      mandatory
    DESCRIPTION
    "This object defines the speed of the Frame Relay port.  The speed may
     only be set to one of a series of reasonable values, and if an attempt is made
     to set the speed to a value which is within the valid range but not equal to one
     of these values, the speed will be rounded up.  If the connector type of the port
     is RS232, the port could be a standard port or a high speed port.  If the port is
     a high speed RS232 port, the maximum valid speed is 256000.  If the port is a standard
     RS232 port, the maximum valid speed is 64000 on the FRX4000/SS1840 and 19200
     on all other products.  It may be possible to set the speed of a standard RS232 port
     to a speed which is valid for a high speed RS232 port but invalid for a standard
     RS232 port. In this case, the port may not end up having the invalid speed.  The default
     speed for a standard RS232 port on the FRX6000 is 19200."
    DEFVAL { 64000 }
    ::= { portFrEntry 14 }

portFrBackupUseOnly OBJECT-TYPE
    SYNTAX      INTEGER {
                no(1),
                yes(2)
                }
    ACCESS      read-write
    STATUS      mandatory
    DESCRIPTION "This object determines whether all DLCIs on the port will
                be reserved exclusively as backups for other DLCIs in the
                same node. If yes is specified for this object, the port
                will remain disabled until needed for backup."
    DEFVAL { no }
    ::= { portFrEntry 15 }

-- The Frame Relay DLCI Configuration table
-- The DLCI contains information about the DCLI configured on a FR
-- port. Note that deleting of a DLCI entry does not affect the existence
-- of the DLCI for the running protocol. The DLCI record is removed from
-- the database file, but will remain known to the node until it is
-- rebooted. This is consistent with the way DLCI information is handled
-- when configuring through the user interface menu system.

portDLCIConfigTable OBJECT-TYPE
    SYNTAX  SEQUENCE OF PortDLCIEntry
    ACCESS  not-accessible
    STATUS  mandatory
    DESCRIPTION
            "A list of DLCI's on Frame Relay ports .  The number of
            entries will be the number of DLCIs on all the Frame Relay
            ports on a node."
    ::= { portFrGroup 2 }

portDLCIEntry OBJECT-TYPE
    SYNTAX  PortDLCIEntry
    ACCESS  not-accessible
    STATUS  mandatory
    DESCRIPTION
            "An Frame Relay Port DLCI entry
            relating to the Rate Control Information that is configurable
            by the user."
    INDEX   {  portDLCIRlpIndex , portDLCIPortIndex, portDLCIIndex }
    ::= { portDLCIConfigTable 1 }

PortDLCIEntry ::=
    SEQUENCE {
        portDLCIRlpIndex
            INTEGER,
        portDLCIPortIndex
            INTEGER,
        portDLCIIndex
            INTEGER,
        portDLCIIncomingCIR
            INTEGER,
        portDLCIOutgoingCIR
            INTEGER,
        portDLCIIncomingBc
            INTEGER,
        portDLCIOutgoingBc
            INTEGER,
        portDLCIIncomingBe
            INTEGER,
        portDLCIOutgoingBe
            INTEGER,
        portDLCIBecnRecoveryCnt
            INTEGER,
        portDLCIPriority
            INTEGER,
        portDLCIRowStatus
            RowStatus,
        portDLCIBackupGroup
            INTEGER,
        portDLCIBackupProtEnb
            INTEGER
    }
portDLCIRlpIndex OBJECT-TYPE
    SYNTAX  INTEGER
    ACCESS  read-only
    STATUS  mandatory
    DESCRIPTION
            " The RLP number on which the DLCI is located. The range for
            this is 1-8. "
    ::= { portDLCIEntry 1 }
portDLCIPortIndex OBJECT-TYPE
    SYNTAX  INTEGER
    ACCESS  read-only
    STATUS  mandatory
    DESCRIPTION
            " The port number on which the DLCI is located. The range for
            this is 1-8 for a physical FR port and 9-64 for a logical FR port. "
    ::= { portDLCIEntry 2 }
portDLCIIndex OBJECT-TYPE
    SYNTAX  INTEGER
    ACCESS  read-only
    STATUS  mandatory
    DESCRIPTION
            " The DLCI number used to identify the entry in the table. The
            range is 16-991. "
    ::= { portDLCIEntry 3 }
portDLCIIncomingCIR OBJECT-TYPE
    SYNTAX  INTEGER (0..2000)
    ACCESS  read-write
    STATUS  mandatory
    DESCRIPTION
            " The committed information rate that is supported on the
            DLCI for incoming data. "
    DEFVAL { 0 }
    ::= { portDLCIEntry 4 }
portDLCIOutgoingCIR OBJECT-TYPE
    SYNTAX  INTEGER (0..2000)
    ACCESS  read-write
    STATUS  mandatory
    DESCRIPTION
            " The committed information rate that is supported on the
            DLCI for outgoing data. "
    DEFVAL { 0 }
    ::= { portDLCIEntry 5 }
portDLCIIncomingBc OBJECT-TYPE
    SYNTAX  INTEGER
    ACCESS  read-write
    STATUS  mandatory
    DESCRIPTION
            " The committed burst size is the maximum amount of data
            to be transmitted under normal conditions within the time
            period defined by Bc/Cir that is supported on the
            DLCI for incoming data. "
    DEFVAL { 0 }
    ::= { portDLCIEntry 6 }
portDLCIOutgoingBc OBJECT-TYPE
    SYNTAX  INTEGER
    ACCESS  read-write
    STATUS  mandatory
    DESCRIPTION
            " The committed burst size is the maximum amount of data
            to be transmitted under normal conditions within the time
            period defined by Bc/Cir that is supported on the
            DLCI for Outgoing data. "
    DEFVAL { 0 }
    ::= { portDLCIEntry 7 }
portDLCIIncomingBe OBJECT-TYPE
    SYNTAX  INTEGER (0..32767)
    ACCESS  read-write
    STATUS  mandatory
    DESCRIPTION
            " The excess burst size is the maximum amount of incoming data
            in excess of the committed burst size that the network will try to
            transfer during the time interval determined by Bc/Cir on this
            DLCI. "
    DEFVAL { 0 }
    ::= { portDLCIEntry 8 }
portDLCIOutgoingBe OBJECT-TYPE
    SYNTAX  INTEGER (0..32767)
    ACCESS  read-write
    STATUS  mandatory
    DESCRIPTION
            " The excess burst size is the maximum amount of incoming data
            in excess of the committed burst size that the network will try to
            transfer during the time interval determined by Bc/Cir on this
            DLCI. "
    DEFVAL { 0 }
    ::= { portDLCIEntry 9 }
portDLCIBecnRecoveryCnt OBJECT-TYPE
    SYNTAX  INTEGER (0..255)
    ACCESS  read-write
    STATUS  mandatory
    DESCRIPTION
            " The BECN recovery Count is a method of controlling the rate
            of return to max traffic flow after it has been reduced due to
            congestion. The value determines the number of packets received
            sequentially without BECN set, before increasing the Excess Burst
            Size by 1/8 of it's configured value. "
    DEFVAL { 0 }
    ::= { portDLCIEntry 10 }

portDLCIPriority OBJECT-TYPE
    SYNTAX  INTEGER (0..4)
    ACCESS  read-write
    STATUS  mandatory
    DESCRIPTION
            " This field sets the priority of the DLCI among others on the
            physical port. The range is 0 for lowest priority to 4 for
            the highest priority. "
    DEFVAL { 0 }
    ::= { portDLCIEntry 11 }

portDLCIRowStatus OBJECT-TYPE
    SYNTAX  RowStatus
    ACCESS  read-write
    STATUS  mandatory
    DESCRIPTION
            "This variable is used to manage the creation and deletion
            of conceptual rows in the portDLCIConfigTable and follows the
            SNMPv2 RowStatus conventions by supporting the following values:

                 - `active', which indicates that the conceptual row is
                available for use by the managed device.  For a management
                protocol set operation, a genErr response is returned when
                the row does not exist.

                 - `createAndGo', which is supplied by a management
                 station wishing to create a new instance of a
                 conceptual row and to have its status automatically set
                 to active, making it available for use by the managed
                 device.  For a management protocol set operation, a
                 genErr response is returned when the row already exists.

                 - `destroy', which is supplied by a management station
                 wishing to delete all of the instances associated with
                 an existing conceptual row.

            Note that all of the above values may be specified in a
            management protocol set operation, and only the 'active'
            value will be returned in response to a management protocol
            retrieval operation.  For a management protocol set operation,
            if other variable bindings are included in the same PDU, then
            a genErr response is returned.

            Also note that deleting a DLCI entry will only remove it from
            the database file, and it's existence will still be known by
            the protocol until the node is rebooted."
    ::= { portDLCIEntry 12 }

portDLCIBackupGroup OBJECT-TYPE
    SYNTAX  INTEGER
    ACCESS  read-write
    STATUS  mandatory
    DESCRIPTION
            "This object specifies (if configured as any number other than
            zero) that this is a primary DLCI, and identifies the backup
            DLCI(s) (in a Frame Relay backup group) that will take over if
            this DLCI fails. This is applicable only on an initiating node,
            which is the node that will initiate the switchover to a backup
            DLCI. At switchover, the initiating node notifies the remote
            node of the change."
    DEFVAL { 0 }
    ::= { portDLCIEntry 13 }

portDLCIBackupProtEnb OBJECT-TYPE
    SYNTAX  INTEGER {
                no(1),
                yes(2)
            }
    ACCESS  read-write
    STATUS  mandatory
    DESCRIPTION
            "This object specifies whether the DLCI will be used as a
            non-initiating backup DLCI. The DLCI will wait for a backup
            protocol message from the initiating end, telling the backup
            where to send the rest of the messages."
    DEFVAL { no }
    ::= { portDLCIEntry 14 }

-- The Frame Relay Backup Group Configuration table

-- A Frame Relay Backup Group is one or more DLCIs (on the same RLP)
-- that can act as a backup for one or more "primary" DLCIs (also on
-- the same RLP). If a node detects a failure in a primary DLCI
-- connection, the software will search any DLCI in the backup group
-- configured for the primary DLCI, and will select the first
-- available one as a backup. The backup will become operational and
-- will remain in that state until the primary becomes active again.
-- If the backup fails while in use, the software will check the
-- status of the primary, then (if necessary) search the primary's
-- backup group for another backup.

portFrBackupGroupTable OBJECT-TYPE
    SYNTAX  SEQUENCE OF FrBackupEntry
    ACCESS  not-accessible
    STATUS  mandatory
    DESCRIPTION
            "   A Table describes the Frame Relay Backup MIB . "
    ::= { portFrGroup 3 }

portFrBackupEntry OBJECT-TYPE
    SYNTAX  FrBackupEntry
    ACCESS  not-accessible
    STATUS  mandatory
    DESCRIPTION
            "   This Entry contains the  SNMP objects that are used for
                configurating the Frame Relay Backup. "
    INDEX  { portFrBackupRLP, portFrBackupPort, portFrBackupDLCI, portFrBackupGroup }

 ::= { portFrBackupGroupTable 1 }

FrBackupEntry ::=
    SEQUENCE  {
        portFrBackupRLP
            INTEGER,
        portFrBackupPort
            INTEGER,
        portFrBackupDLCI
            INTEGER,
        portFrBackupGroup
            INTEGER,
        portFrBackupWaitTimer
            INTEGER,
        portFrBackupProtEnab
            INTEGER,
        portFrBackupRowStatus
            RowStatus
    }

portFrBackupRLP   OBJECT-TYPE
    SYNTAX  INTEGER (1..8)
    ACCESS  read-only
    STATUS  mandatory
    DESCRIPTION
            " This RLP number identifies the RLP containing the
             primary and backup DLCIs. "
    ::= { portFrBackupEntry 1 }

portFrBackupPort  OBJECT-TYPE
    SYNTAX  INTEGER (1..8)
    ACCESS  read-only
    STATUS  mandatory
    DESCRIPTION
            " This Port number is the physical port on which
             the backup DLCI is being configured. "
    ::= { portFrBackupEntry 2 }

portFrBackupDLCI  OBJECT-TYPE
    SYNTAX  INTEGER (16..991)
    ACCESS  read-only
    STATUS  mandatory
    DESCRIPTION
            " This DLCI number is the backup being configured. "
    ::= { portFrBackupEntry 3 }

portFrBackupGroup OBJECT-TYPE
    SYNTAX  INTEGER (1..255)
    ACCESS  read-only
    STATUS  mandatory
    DESCRIPTION
            " This Group number is the backup being configured. "
    ::= { portFrBackupEntry 4 }

portFrBackupWaitTimer OBJECT-TYPE
    SYNTAX  INTEGER (0..65535)
    ACCESS  read-write
    STATUS  mandatory
    DESCRIPTION
            " This is the time after a primary DLCI failure that the
             software will wait for this DLCI to become active before
             checking the next backup DLCI. If the backup does not
             become active before the timer expires, the software will
             search the backup group for the next available backup."
    DEFVAL { 120 }
    ::= { portFrBackupEntry 5 }

portFrBackupProtEnab  OBJECT-TYPE
    SYNTAX  INTEGER {
                no(1),
                yes(2)
            }
    ACCESS  read-write
    STATUS  mandatory
    DESCRIPTION
        " This enables or disables the backup protocol on the specified
         DLCI. It should be set to yes if and only if the remote device
         is an FRX4000 or FRX6000 with the backup protocol enabled on the
         remote DLCI connected to this backup group entry. "
    DEFVAL { no }
    ::= { portFrBackupEntry 6 }

portFrBackupRowStatus OBJECT-TYPE
    SYNTAX  RowStatus
    ACCESS  read-write
    STATUS  mandatory
    DESCRIPTION
            "This variable is used to manage the creation and deletion
            of conceptual rows in the portFrBackupGroupTable and follows the
            SNMPv2 RowStatus conventions by supporting the following values:

                 - `active', which indicates that the conceptual row is
                available for use by the managed device.  For a management
                protocol set operation, a genErr response is returned when
                the row does not exist.

                 - `createAndGo', which is supplied by a management
                 station wishing to create a new instance of a
                 conceptual row and to have its status automatically set
                 to active, making it available for use by the managed
                 device.  For a management protocol set operation, a
                 genErr response is returned when the row already exists.

                 - `destroy', which is supplied by a management station
                 wishing to delete all of the instances associated with
                 an existing conceptual row.

            Note that all of the above values may be specified in a
            management protocol set operation, and only the 'active'
            value will be returned in response to a management protocol
            retrieval operation.  For a management protocol set operation,
            if other variable bindings are included in the same PDU, then
            a genErr response is returned."
    ::= { portFrBackupEntry 7 }

portBsciGroup	OBJECT IDENTIFIER ::=	{ port 4 }

--
--  BSC Interactive Port Administrative Table
--

portBsciAdminTable OBJECT-TYPE
	SYNTAX SEQUENCE OF PortBsciAdminEntry
	ACCESS not-accessible
	STATUS mandatory
	DESCRIPTION
			"A list of BSC Interactive ports . The number of
			entries will be the number of BSC Interactive ports on the node."
	::= { portBsciGroup 1 }

portBsciAdminEntry OBJECT-TYPE
	SYNTAX PortBsciAdminEntry
	ACCESS not-accessible
	STATUS mandatory
	DESCRIPTION
			"A BSCI Interactive Port entry containing objects
			relating to the port that are configurable by the user."
	INDEX { nlIfRlp, nlIfPort }
	::= { portBsciAdminTable 1 }

PortBsciAdminEntry ::=
	SEQUENCE {
		portBsciAdminBlockedFlag				INTEGER,
		portBsciAdminConnector					INTEGER,
		portBsciAdminSpeed						INTEGER,
		portBsciAdminRetransmitInterval			INTEGER,
		portBsciAdminMAXRetransmits				INTEGER,
		portBsciAdminMaxBytesPerFrame			INTEGER,
		portBsciAdminGenerateClock				INTEGER,
		portBsciAdminRcvClockFromDTE			INTEGER,
		portBsciAdminPadType					INTEGER,
		portBsciAdminUseEBCDIC					INTEGER,
		portBsciAdminCallInfoInRequestPacket	INTEGER,
		portBsciAdminClearVCOnLastDeviceDown	INTEGER,
		portBsciAdminTransTextSupported			INTEGER,
		portBsciAdminEndToEndAck				INTEGER,
		portBsciAdminFullDuplex					INTEGER,
		portBsciAdminMultidrop					INTEGER,
		portBsciAdminSlowPollRetryCount			INTEGER,
		portBsciAdminSlowPollRetryFreq			INTEGER,
		portBsciAdminStartSynchChars			INTEGER,
		portBsciAdminEndPadChars				INTEGER,
		portBsciAdminPollInterval				INTEGER,
		portBsciAdminNoResponseTimer			INTEGER,
		portBsciAdminNoResponseRetryCount		INTEGER,
		portBsciAdminErrorRetransmitCount		INTEGER,
		portBsciAdminNAKRetryCount				INTEGER,
		portBsciAdminBlockCheck					INTEGER,
		portBsciAdminDataMode					INTEGER,
		portBsciAdminRowStatus					RowStatus,
	 	portBsciAdminAnswerNonConfigured			INTEGER,
		portBsciAdminActivateConnectionWithoutPoll		INTEGER
	}

portBsciAdminBlockedFlag OBJECT-TYPE
	SYNTAX 	INTEGER {
				disabled(1),
				enabled(2)
				}
	ACCESS read-write
	STATUS mandatory
	DESCRIPTION "Causes the port to be enabled or disabled at node IPL."
	DEFVAL { disabled }
	::= { portBsciAdminEntry 1 }

portBsciAdminConnector OBJECT-TYPE
	SYNTAX INTEGER {
				rs232(3),
				v35(5),
				rs449(6),
				rs530(7),
				x21(8),
				t1(10)
				}
	ACCESS read-write
	STATUS mandatory
	DESCRIPTION "Physical port interface connector type."
	::= { portBsciAdminEntry 2 }

portBsciAdminSpeed OBJECT-TYPE
	SYNTAX 	INTEGER (75..19200)
	ACCESS read-write
	STATUS mandatory
	DESCRIPTION "Data transmission rate in bits per second."
	DEFVAL { 9600 }
	::= { portBsciAdminEntry 3 }

portBsciAdminRetransmitInterval OBJECT-TYPE
	SYNTAX 	INTEGER (1..9999)
	ACCESS read-write
	STATUS mandatory
	DESCRIPTION "Length of time before the node will transmit an I-frame
				if the previous transmission is not acknowledged."
	DEFVAL { 2000}
	::= { portBsciAdminEntry 4 }

portBsciAdminMAXRetransmits OBJECT-TYPE
	SYNTAX 	INTEGER (1..99)
	ACCESS read-write
	STATUS mandatory
	DESCRIPTION "Maximum number of times the node will attempt to send
				an I-frame after a retransmission period expiration."
	DEFVAL { 5 }
	::= { portBsciAdminEntry 5 }

portBsciAdminMaxBytesPerFrame OBJECT-TYPE
	SYNTAX 	INTEGER (25..4105)
	ACCESS read-write
	STATUS mandatory
	DESCRIPTION "Maximum frame size that will be transmitted on the port."
	DEFVAL { 4105 }
	::= { portBsciAdminEntry 6 }

portBsciAdminGenerateClock OBJECT-TYPE
	SYNTAX 	INTEGER {
				no(1),
				yes(2)
				}
	ACCESS read-write
	STATUS mandatory
	DESCRIPTION "Specifies whether the port will generate the clock
				necessary to synchronize traffic over the link."
	DEFVAL { yes }
	::= { portBsciAdminEntry 7 }

portBsciAdminRcvClockFromDTE OBJECT-TYPE
	SYNTAX 	INTEGER {
				no(1),
				yes(2)
				}
	ACCESS read-write
	STATUS mandatory
	DESCRIPTION "Allows the clock to be looped back from the DTE
				using the TT (Terminal Timing) signal."
	DEFVAL { no }
	::= { portBsciAdminEntry 8 }

portBsciAdminPadType OBJECT-TYPE
	SYNTAX 	INTEGER {
				tpad(1),
				hpad(2)
				}
	ACCESS read-write
	STATUS mandatory
	DESCRIPTION "BSCI Pad Type"
	DEFVAL { tpad }
	::= { portBsciAdminEntry 9 }

portBsciAdminUseEBCDIC OBJECT-TYPE
	SYNTAX 	INTEGER {
				no(1),
				yes(2)
				}
	ACCESS read-write
	STATUS mandatory
	DESCRIPTION "Specifies whether all devices on a line use the same
				character set for successive session polls."
	DEFVAL { yes }
	::= { portBsciAdminEntry 10 }

portBsciAdminCallInfoInRequestPacket OBJECT-TYPE
	SYNTAX 	INTEGER {
				no(1),
				yes(2)
				}
	ACCESS read-write
	STATUS mandatory
	DESCRIPTION "Specifies whether the user will have the option of
				including call information in a call request packet."
	DEFVAL { yes }
	::= { portBsciAdminEntry 11 }

portBsciAdminClearVCOnLastDeviceDown OBJECT-TYPE
	SYNTAX 	INTEGER {
				no(1),
				yes(2)
				}
	ACCESS read-write
	STATUS mandatory
	DESCRIPTION "Causes the virtual circuit to be cleared when no
				terminals are using it."
	DEFVAL { no }
	::= { portBsciAdminEntry 12 }

portBsciAdminTransTextSupported OBJECT-TYPE
	SYNTAX 	INTEGER {
				no(1),
				yes(2)
				}
	ACCESS read-write
	STATUS mandatory
	DESCRIPTION "Causes all characters transmitted to be treated as data."
	DEFVAL { no }
	::= { portBsciAdminEntry 13 }

portBsciAdminEndToEndAck OBJECT-TYPE
	SYNTAX 	INTEGER {
				no(1),
				yes(2)
				}
	ACCESS read-write
	STATUS mandatory
	DESCRIPTION "Allows management of acknowledgments end to end across
				the network rather than locally at each end."
	DEFVAL { no }
	::= { portBsciAdminEntry 14 }

portBsciAdminFullDuplex OBJECT-TYPE
	SYNTAX 	INTEGER {
				no(1),
				yes(2)
				}
	ACCESS read-write
	STATUS mandatory
	DESCRIPTION "Specifies full-duplex transmission."
	DEFVAL { yes }
	::= { portBsciAdminEntry 15 }

portBsciAdminMultidrop OBJECT-TYPE
	SYNTAX 	INTEGER {
				no(1),
				yes(2)
				}
	ACCESS read-write
	STATUS mandatory
	DESCRIPTION "Specifies whether transmission will be multidrop."
	DEFVAL { no }
	::= { portBsciAdminEntry 16 }

portBsciAdminSlowPollRetryCount OBJECT-TYPE
	SYNTAX 	INTEGER (10..150)
	ACCESS read-write
	STATUS mandatory
	DESCRIPTION "Specifies how many times the control unit will be polled
				before it is put on the slow poll list."
	DEFVAL { 20 }
	::= { portBsciAdminEntry 17 }

portBsciAdminSlowPollRetryFreq OBJECT-TYPE
	SYNTAX 	INTEGER (1..200)
	ACCESS read-write
	STATUS mandatory
	DESCRIPTION "Specifies the number of times active control units will
				be polled between pollings on the slow poll list."
	DEFVAL { 20 }
	::= { portBsciAdminEntry 18 }

portBsciAdminStartSynchChars OBJECT-TYPE
	SYNTAX 	INTEGER (2..10)
	ACCESS read-write
	STATUS mandatory
	DESCRIPTION "Specifies the number of synchronization characters
				that will be added to the beginning of each frame."
	DEFVAL { 2 }
	::= { portBsciAdminEntry 19 }

portBsciAdminEndPadChars OBJECT-TYPE
	SYNTAX 	INTEGER (1..10)
	ACCESS read-write
	STATUS mandatory
	DESCRIPTION "Specifies the number of padding characters that will
				be added to the end of each frame."
	DEFVAL { 1 }
	::= { portBsciAdminEntry 20 }

portBsciAdminPollInterval OBJECT-TYPE
	SYNTAX 	INTEGER (100..1000)
	ACCESS read-write
	STATUS mandatory
	DESCRIPTION "Specifies the time between passes through the polling list."
	DEFVAL { 500 }
	::= { portBsciAdminEntry 21 }

portBsciAdminNoResponseTimer OBJECT-TYPE
	SYNTAX 	INTEGER (2..10)
	ACCESS read-write
	STATUS mandatory
	DESCRIPTION "Activated after transmission of a general poll or a
				data frame."
	DEFVAL { 2 }
	::= { portBsciAdminEntry 22 }

portBsciAdminNoResponseRetryCount OBJECT-TYPE
	SYNTAX 	INTEGER (1..255)
	ACCESS read-write
	STATUS mandatory
	DESCRIPTION "Specifies how many times the user device will be polled
				before control is passed on the next cluster."
	DEFVAL { 5 }
	::= { portBsciAdminEntry 23 }

portBsciAdminErrorRetransmitCount OBJECT-TYPE
	SYNTAX 	INTEGER (1..255)
	ACCESS read-write
	STATUS mandatory
	DESCRIPTION "Specifies the number of times the Netlink device will
				resend a block of data after the receiving device has
				detected an error in that block."
	DEFVAL { 5 }
	::= { portBsciAdminEntry 24 }

portBsciAdminNAKRetryCount OBJECT-TYPE
	SYNTAX 	INTEGER (1..255)
	ACCESS read-write
	STATUS mandatory
	DESCRIPTION "Specifies the number of times the Netlink device will
				send a frame when the receiving device is unable to
				acknowledge."
	DEFVAL { 5 }
	::= { portBsciAdminEntry 25 }

portBsciAdminBlockCheck OBJECT-TYPE
	SYNTAX 	INTEGER {
				crc16(1),
				even-lrc(2),
				odd-lrc(3)
				}
	ACCESS read-write
	STATUS mandatory
	DESCRIPTION "Sets the redundancy check parameter."
	DEFVAL { even-lrc }
	::= { portBsciAdminEntry 26 }

portBsciAdminDataMode OBJECT-TYPE
	SYNTAX 	INTEGER {
				odd-7bit(1),
				even-7bit(2),
				none-8bit(3)
				}
	ACCESS read-write
	STATUS mandatory
	DESCRIPTION "Sets the parity parameter."
	DEFVAL { none-8bit }
	::= { portBsciAdminEntry 27 }

portBsciAdminRowStatus OBJECT-TYPE
	SYNTAX RowStatus
	ACCESS read-write
	STATUS mandatory
	DESCRIPTION 
            "This variable is used to manage the creation and deletion
            of conceptual rows in the portBsciAdminTable and follows the
            SNMPv2 RowStatus conventions by supporting the following values:

                 - `active', which indicates that the conceptual row is
                available for use by the managed device, and which is
                supplied by a management station wishing to exercise an
                on-line update of the existing conceptual row.  For a
                management protocol set operation, a genErr response is
                returned when the row does not exist.

                 - `createAndGo', which is supplied by a management
                 station wishing to create a new instance of a
                 conceptual row and to have its status automatically set
                 to active, making it available for use by the managed
                 device.  For a management protocol set operation, a
                 genErr response is returned when the row already exists.

                 - `destroy', which is supplied by a management station
                 wishing to delete all of the instances associated with
                 an existing conceptual row.

            Note that all of the above values may be specified in a
            management protocol set operation, and only the 'active'
            value will be returned in response to a management protocol
            retrieval operation.  For a management protocol set operation,
            if other variable bindings are included in the same PDU, then
            a genErr response is returned."
	::= { portBsciAdminEntry 28 }

portBsciAdminAnswerNonConfigured OBJECT-TYPE
	SYNTAX 	INTEGER {
				no(1),
				yes(2)
				}
	ACCESS read-write
	STATUS mandatory
	DESCRIPTION "Only valid if pad type is HPAD.  If yes, the HPAD will
		     respond to all devices on the line.  If no, the HPAD will
		     respond only to those devices that are configured on the
                     node."
	DEFVAL { yes }
	::= { portBsciAdminEntry 29 }

portBsciAdminActivateConnectionWithoutPoll OBJECT-TYPE
	SYNTAX 	INTEGER {
				no(1),
				yes(2)
				}
	ACCESS read-write
	STATUS mandatory
	DESCRIPTION "Only valid if pad type is TPAD.  If yes, will active the 
		     TPAD connection without a poll of the connected device."
	DEFVAL { no }
	::= { portBsciAdminEntry 30 }

--
--  BSC Interactive Port Operational Table
--

portBsciOperTable OBJECT-TYPE
	SYNTAX SEQUENCE OF PortBsciOperEntry
	ACCESS not-accessible
	STATUS mandatory
	DESCRIPTION
			"A list of BSC Interactive ports . The number of
			entries will be the number of BSC Interactive ports on the node."
	::= { portBsciGroup 2 }

portBsciOperEntry OBJECT-TYPE
	SYNTAX PortBsciOperEntry
	ACCESS not-accessible
	STATUS mandatory
	DESCRIPTION
			"A BSCI Interactive Port entry containing objects
			relating to the port that are configurable by the user."
	INDEX { nlIfRlp, nlIfPort }
	::= { portBsciOperTable 1 }

PortBsciOperEntry ::=
	SEQUENCE {
		portBsciOperBlockedFlag					INTEGER,
		portBsciOperConnector					INTEGER,
		portBsciOperSpeed						INTEGER,
		portBsciOperRetransmitInterval			INTEGER,
		portBsciOperMAXRetransmits				INTEGER,
		portBsciOperMaxBytesPerFrame			INTEGER,
		portBsciOperGenerateClock				INTEGER,
		portBsciOperRcvClockFromDTE				INTEGER,
		portBsciOperPadType						INTEGER,
		portBsciOperUseEBCDIC					INTEGER,
		portBsciOperCallInfoInRequestPacket		INTEGER,
		portBsciOperClearVCOnLastDeviceDown		INTEGER,
		portBsciOperTransTextSupported			INTEGER,
		portBsciOperEndToEndAck					INTEGER,
		portBsciOperFullDuplex					INTEGER,
		portBsciOperMultidrop					INTEGER,
		portBsciOperSlowPollRetryCount			INTEGER,
		portBsciOperSlowPollRetryFreq			INTEGER,
		portBsciOperStartSynchChars				INTEGER,
		portBsciOperEndPadChars					INTEGER,
		portBsciOperPollInterval				INTEGER,
		portBsciOperNoResponseTimer				INTEGER,
		portBsciOperNoResponseRetryCount		INTEGER,
		portBsciOperErrorRetransmitCount		INTEGER,
		portBsciOperNAKRetryCount				INTEGER,
		portBsciOperBlockCheck					INTEGER,
		portBsciOperDataMode					INTEGER,
	 	portBsciOperAnswerNonConfigured			INTEGER,
		portBsciOperActivateConnectionWithoutPoll		INTEGER
	}

portBsciOperBlockedFlag OBJECT-TYPE
	SYNTAX 	INTEGER {
				disabled(1),
				enabled(2)
				}
	ACCESS read-only
	STATUS mandatory
	DESCRIPTION "Causes the port to be enabled or disabled at node IPL."
	::= { portBsciOperEntry 1 }

portBsciOperConnector OBJECT-TYPE
	SYNTAX INTEGER {
				rs232(3),
				v35(5),
				rs449(6),
				rs530(7),
				x21(8),
				t1(10)
				}
	ACCESS read-only
	STATUS mandatory
	DESCRIPTION "Physical port interface connector type."
	::= { portBsciOperEntry 2 }

portBsciOperSpeed OBJECT-TYPE
	SYNTAX 	INTEGER
	ACCESS read-only
	STATUS mandatory
	DESCRIPTION "Data transmission rate in bits per second."
	::= { portBsciOperEntry 3 }

portBsciOperRetransmitInterval OBJECT-TYPE
	SYNTAX 	INTEGER (1..9999)
	ACCESS read-only
	STATUS mandatory
	DESCRIPTION "Length of time before the node will transmit an I-frame
				if the previous transmission is not acknowledged."
	::= { portBsciOperEntry 4 }

portBsciOperMAXRetransmits OBJECT-TYPE
	SYNTAX 	INTEGER (1..99)
	ACCESS read-only
	STATUS mandatory
	DESCRIPTION "Maximum number of times the node will attempt to send
				an I-frame after a retransmission period expiration."
	::= { portBsciOperEntry 5 }

portBsciOperMaxBytesPerFrame OBJECT-TYPE
	SYNTAX 	INTEGER (25..4105)
	ACCESS read-only
	STATUS mandatory
	DESCRIPTION "Maximum frame size that will be transmitted on the port."
	::= { portBsciOperEntry 6 }

portBsciOperGenerateClock OBJECT-TYPE
	SYNTAX 	INTEGER {
				no(1),
				yes(2)
				}
	ACCESS read-only
	STATUS mandatory
	DESCRIPTION "Specifies whether the port will generate the clock
				necessary to synchronize traffic over the link."
	::= { portBsciOperEntry 7 }

portBsciOperRcvClockFromDTE OBJECT-TYPE
	SYNTAX 	INTEGER {
				no(1),
				yes(2)
				}
	ACCESS read-only
	STATUS mandatory
	DESCRIPTION "Allows the clock to be looped back from the DTE
				using the TT (Terminal Timing) signal."
	::= { portBsciOperEntry 8 }

portBsciOperPadType OBJECT-TYPE
	SYNTAX 	INTEGER {
				tpad(1),
				hpad(2)
				}
	ACCESS read-only
	STATUS mandatory
	DESCRIPTION "BSCI Pad Type"
	::= { portBsciOperEntry 9 }

portBsciOperUseEBCDIC OBJECT-TYPE
	SYNTAX 	INTEGER {
				no(1),
				yes(2)
				}
	ACCESS read-only
	STATUS mandatory
	DESCRIPTION "Specifies whether all devices on a line use the same
				character set for successive session polls."
	::= { portBsciOperEntry 10 }

portBsciOperCallInfoInRequestPacket OBJECT-TYPE
	SYNTAX 	INTEGER {
				no(1),
				yes(2)
				}
	ACCESS read-only
	STATUS mandatory
	DESCRIPTION "Specifies whether the user will have the option of
				including call information in a call request packet."
	::= { portBsciOperEntry 11 }

portBsciOperClearVCOnLastDeviceDown OBJECT-TYPE
	SYNTAX 	INTEGER {
				no(1),
				yes(2)
				}
	ACCESS read-only
	STATUS mandatory
	DESCRIPTION "Causes the virtual circuit to be cleared when no
				terminals are using it."
	::= { portBsciOperEntry 12 }

portBsciOperTransTextSupported OBJECT-TYPE
	SYNTAX 	INTEGER {
				no(1),
				yes(2)
				}
	ACCESS read-only
	STATUS mandatory
	DESCRIPTION "Causes all characters transmitted to be treated as data."
	::= { portBsciOperEntry 13 }

portBsciOperEndToEndAck OBJECT-TYPE
	SYNTAX 	INTEGER {
				no(1),
				yes(2)
				}
	ACCESS read-only
	STATUS mandatory
	DESCRIPTION "Allows management of acknowledgments end to end across
				the network rather than locally at each end."
	::= { portBsciOperEntry 14 }

portBsciOperFullDuplex OBJECT-TYPE
	SYNTAX 	INTEGER {
				no(1),
				yes(2)
				}
	ACCESS read-only
	STATUS mandatory
	DESCRIPTION "Specifies full-duplex transmission."
	::= { portBsciOperEntry 15 }

portBsciOperMultidrop OBJECT-TYPE
	SYNTAX 	INTEGER {
				no(1),
				yes(2)
				}
	ACCESS read-only
	STATUS mandatory
	DESCRIPTION "Specifies whether transmission will be multidrop."
	::= { portBsciOperEntry 16 }

portBsciOperSlowPollRetryCount OBJECT-TYPE
	SYNTAX 	INTEGER (10..150)
	ACCESS read-only
	STATUS mandatory
	DESCRIPTION "Specifies how many times the control unit will be polled
				before it is put on the slow poll list."
	::= { portBsciOperEntry 17 }

portBsciOperSlowPollRetryFreq OBJECT-TYPE
	SYNTAX 	INTEGER (1..200)
	ACCESS read-only
	STATUS mandatory
	DESCRIPTION "Specifies the number of times active control units will
				be polled between pollings on the slow poll list."
	::= { portBsciOperEntry 18 }

portBsciOperStartSynchChars OBJECT-TYPE
	SYNTAX 	INTEGER (2..10)
	ACCESS read-only
	STATUS mandatory
	DESCRIPTION "Specifies the number of synchronization characters
				that will be added to the beginning of each frame."
	::= { portBsciOperEntry 19 }

portBsciOperEndPadChars OBJECT-TYPE
	SYNTAX 	INTEGER (1..10)
	ACCESS read-only
	STATUS mandatory
	DESCRIPTION "Specifies the number of padding characters that will
				be added to the end of each frame."
	::= { portBsciOperEntry 20 }

portBsciOperPollInterval OBJECT-TYPE
	SYNTAX 	INTEGER (100..1000)
	ACCESS read-only
	STATUS mandatory
	DESCRIPTION "Specifies the time between passes through the polling list."
	::= { portBsciOperEntry 21 }

portBsciOperNoResponseTimer OBJECT-TYPE
	SYNTAX 	INTEGER (2..10)
	ACCESS read-only
	STATUS mandatory
	DESCRIPTION "Activated after transmission of a general poll or a
				data frame."
	::= { portBsciOperEntry 22 }

portBsciOperNoResponseRetryCount OBJECT-TYPE
	SYNTAX 	INTEGER (1..255)
	ACCESS read-only
	STATUS mandatory
	DESCRIPTION "Specifies how many times the user device will be polled
				before control is passed on the next cluster."
	::= { portBsciOperEntry 23 }

portBsciOperErrorRetransmitCount OBJECT-TYPE
	SYNTAX 	INTEGER (1..255)
	ACCESS read-only
	STATUS mandatory
	DESCRIPTION "Specifies the number of times the Netlink device will
				resend a block of data after the receiving device has
				detected an error in that block."
	::= { portBsciOperEntry 24 }

portBsciOperNAKRetryCount OBJECT-TYPE
	SYNTAX 	INTEGER (1..255)
	ACCESS read-only
	STATUS mandatory
	DESCRIPTION "Specifies the number of times the Netlink device will
				send a frame when the receiving device is unable to
				acknowledge."
	::= { portBsciOperEntry 25 }

portBsciOperBlockCheck OBJECT-TYPE
	SYNTAX 	INTEGER {
				crc16(1),
				even-lrc(2),
				odd-lrc(3)
				}
	ACCESS read-only
	STATUS mandatory
	DESCRIPTION "Sets the redundancy check parameter."
	::= { portBsciOperEntry 26 }

portBsciOperDataMode OBJECT-TYPE
	SYNTAX 	INTEGER {
				odd-7bit(1),
				even-7bit(2),
				none-8bit(3)
				}
	ACCESS read-only
	STATUS mandatory
	DESCRIPTION "Sets the parity parameter."
	::= { portBsciOperEntry 27 }

portBsciOperAnswerNonConfigured OBJECT-TYPE
	SYNTAX 	INTEGER {
				no(1),
				yes(2)
				}
	ACCESS read-only
	STATUS mandatory
	DESCRIPTION "Only valid if pad type is HPAD.  If yes, the HPAD will
		     respond to all devices on the line.  If no, the HPAD will
		     respond only to those devices that are configured on the
                     node."
	::= { portBsciOperEntry 28 }

portBsciOperActivateConnectionWithoutPoll OBJECT-TYPE
	SYNTAX 	INTEGER {
				no(1),
				yes(2)
				}
	ACCESS read-only
	STATUS mandatory
	DESCRIPTION "Only valid if pad type is TPAD.  If yes, will active the 
		     TPAD connection without a poll of the connected device."
	::= { portBsciOperEntry 29 }

--
-- BSCI Port Subscriber Administrative Table
--

bsciSubscrAdminTable OBJECT-TYPE
	SYNTAX SEQUENCE OF BsciSubscrAdminEntry
	ACCESS not-accessible
	STATUS mandatory
	DESCRIPTION
			"A list of BSC Interactive port subscribers."
	::= { portBsciGroup 3 }

bsciSubscrAdminEntry OBJECT-TYPE
	SYNTAX BsciSubscrAdminEntry
	ACCESS not-accessible
	STATUS mandatory
	DESCRIPTION
			"A BSCI Interactive Port Subscriber entry containing objects
			relating to the port that are configurable by the user."
	INDEX { nlIfRlp, nlIfPort, bsciSubscrAdminSequence }
	::= { bsciSubscrAdminTable 1 }

BsciSubscrAdminEntry ::=
	SEQUENCE {
		bsciSubscrAdminSequence				INTEGER,
		bsciSubscrAdminLocalID				NlSubscriberAddress,
		bsciSubscrAdminRemoteID				NlSubscriberAddress,
		bsciSubscrAdminAutocall				INTEGER,
		bsciSubscrAdminAutocallRtyTimer		INTEGER,
		bsciSubscrAdminAutocallMaxRtry		INTEGER,
		bsciSubscrAdminConnectionID			INTEGER,
		bsciSubscrAdminRowStatus			RowStatus
	}

bsciSubscrAdminSequence OBJECT-TYPE
	SYNTAX 	INTEGER (1..16)
	ACCESS read-only
	STATUS mandatory
	DESCRIPTION "Subscriber index for a specific BSCI port subscriber."
	::= { bsciSubscrAdminEntry 1 }

bsciSubscrAdminLocalID OBJECT-TYPE
	SYNTAX 	NlSubscriberAddress
	ACCESS read-write
	STATUS mandatory
	DESCRIPTION "Subscriber address of the local end of a BSCI connection."
	::= { bsciSubscrAdminEntry 2 }

bsciSubscrAdminRemoteID OBJECT-TYPE
	SYNTAX 	NlSubscriberAddress
	ACCESS read-write
	STATUS mandatory
	DESCRIPTION "Subscriber address of the remote end of a BSCI connection."
	::= { bsciSubscrAdminEntry 3 }

bsciSubscrAdminAutocall OBJECT-TYPE
	SYNTAX 	INTEGER {
				no(1),
				yes(2)
				}
	ACCESS read-write
	STATUS mandatory
	DESCRIPTION "Causes a BSCI TPAD to automatically call its HPAD when
				the controller becomes active."
	DEFVAL { no }
	::= { bsciSubscrAdminEntry 4 }

bsciSubscrAdminAutocallRtyTimer OBJECT-TYPE
	SYNTAX 	INTEGER (15..255)
	ACCESS read-write
	STATUS mandatory
	DESCRIPTION "Time between autocall retries."
	DEFVAL { 60 }
	::= { bsciSubscrAdminEntry 5 }

bsciSubscrAdminAutocallMaxRtry OBJECT-TYPE
	SYNTAX 	INTEGER (0..255)
	ACCESS read-write
	STATUS mandatory
	DESCRIPTION "Maximum number of times an autocall will be sent."
	DEFVAL { 0 }
	::= { bsciSubscrAdminEntry 6 }

bsciSubscrAdminConnectionID OBJECT-TYPE
	SYNTAX 	INTEGER (0..255)
	ACCESS read-write
	STATUS mandatory
	DESCRIPTION "Identifier that will link the BSCI port with a device
				configured in the BSCI Devices Table."
	DEFVAL { 0 }
	::= { bsciSubscrAdminEntry 7 }

bsciSubscrAdminRowStatus OBJECT-TYPE
	SYNTAX RowStatus
	ACCESS read-write
	STATUS mandatory
	DESCRIPTION 
            "This variable is used to manage the creation and deletion
            of conceptual rows in the bsciDevAdminTable and follows the
            SNMPv2 RowStatus conventions by supporting the following values:

                 - `active', which indicates that the conceptual row is
                available for use by the managed device.  For a management
                protocol set operation, a genErr response is returned when
                the row does not exist.

                 - `createAndGo', which is supplied by a management
                 station wishing to create a new instance of a
                 conceptual row and to have its status automatically set
                 to active, making it available for use by the managed
                 device.  For a management protocol set operation, a
                 genErr response is returned when the row already exists.

                 - `destroy', which is supplied by a management station
                 wishing to delete all of the instances associated with
                 an existing conceptual row.

            Note that all of the above values may be specified in a
            management protocol set operation, and only the 'active'
            value will be returned in response to a management protocol
            retrieval operation.  For a management protocol set operation,
            if other variable bindings are included in the same PDU, then
            a genErr response is returned."
	::= { bsciSubscrAdminEntry 8 }

--
-- BSCI Port Subscriber Operational Table
--

bsciSubscrOperTable OBJECT-TYPE
	SYNTAX SEQUENCE OF BsciSubscrOperEntry
	ACCESS not-accessible
	STATUS mandatory
	DESCRIPTION
			"A list of BSC Interactive port subscribers."
	::= { portBsciGroup 4 }

bsciSubscrOperEntry OBJECT-TYPE
	SYNTAX BsciSubscrOperEntry
	ACCESS not-accessible
	STATUS mandatory
	DESCRIPTION
			"A BSCI Interactive Port Subscriber entry containing objects
			relating to the port that are configurable by the user."
	INDEX { nlIfRlp, nlIfPort, bsciSubscrOperSequence }
	::= { bsciSubscrOperTable 1 }

BsciSubscrOperEntry ::=
	SEQUENCE {
		bsciSubscrOperSequence				INTEGER,
		bsciSubscrOperLocalID				NlSubscriberAddress,
		bsciSubscrOperRemoteID				NlSubscriberAddress,
		bsciSubscrOperAutocall				INTEGER,
		bsciSubscrOperAutocallRtyTimer		INTEGER,
		bsciSubscrOperAutocallMaxRtry		INTEGER,
		bsciSubscrOperConnectionID			INTEGER
	}

bsciSubscrOperSequence OBJECT-TYPE
	SYNTAX 	INTEGER (1..16)
	ACCESS read-only
	STATUS mandatory
	DESCRIPTION "Subscriber index for a specific BSCI port subscriber."
	::= { bsciSubscrOperEntry 1 }

bsciSubscrOperLocalID OBJECT-TYPE
	SYNTAX 	NlSubscriberAddress
	ACCESS read-only
	STATUS mandatory
	DESCRIPTION "Subscriber address of the local end of a BSCI connection."
	::= { bsciSubscrOperEntry 2 }

bsciSubscrOperRemoteID OBJECT-TYPE
	SYNTAX 	NlSubscriberAddress
	ACCESS read-only
	STATUS mandatory
	DESCRIPTION "Subscriber address of the remote end of a BSCI connection."
	::= { bsciSubscrOperEntry 3 }

bsciSubscrOperAutocall OBJECT-TYPE
	SYNTAX 	INTEGER {
				no(1),
				yes(2)
				}
	ACCESS read-only
	STATUS mandatory
	DESCRIPTION "Causes a BSCI TPAD to automatically call its HPAD when
				the controller becomes active."
	::= { bsciSubscrOperEntry 4 }

bsciSubscrOperAutocallRtyTimer OBJECT-TYPE
	SYNTAX 	INTEGER (15..255)
	ACCESS read-only
	STATUS mandatory
	DESCRIPTION "Time between autocall retries."
	::= { bsciSubscrOperEntry 5 }

bsciSubscrOperAutocallMaxRtry OBJECT-TYPE
	SYNTAX 	INTEGER (0..255)
	ACCESS read-only
	STATUS mandatory
	DESCRIPTION "Maximum number of times an autocall will be sent."
	::= { bsciSubscrOperEntry 6 }

bsciSubscrOperConnectionID OBJECT-TYPE
	SYNTAX 	INTEGER (0..255)
	ACCESS read-only
	STATUS mandatory
	DESCRIPTION "Identifier that will link the BSCI port with a device
				configured in the BSCI Devices Table."
	::= { bsciSubscrOperEntry 7 }

--
-- BSC Interactive Device Administrative Table
--

bsciDevAdminTable OBJECT-TYPE
	SYNTAX SEQUENCE OF BsciDevAdminEntry
	ACCESS not-accessible
	STATUS mandatory
	DESCRIPTION
			"A list of BSC Interactive devices."
	::= { portBsciGroup 5 }

bsciDevAdminEntry OBJECT-TYPE
	SYNTAX BsciDevAdminEntry
	ACCESS not-accessible
	STATUS mandatory
	DESCRIPTION
			"A BSCI Interactive Device entry containing objects
			relating to the device that are configurable by the user."
	INDEX { nlIfRlp, nlIfPort, bsciDevAdminControlUnitID,
			bsciDevAdminDeviceUnitID }
	::= { bsciDevAdminTable 1 }

BsciDevAdminEntry ::=
	SEQUENCE {
		bsciDevAdminControlUnitID			INTEGER,
		bsciDevAdminDeviceUnitID			INTEGER,
		bsciDevAdminConnectionID			INTEGER,
		bsciDevAdminSingleUserVC			INTEGER,
		bsciDevAdminTransTextSupported		INTEGER,
		bsciDevAdminPrinterAttached			INTEGER,
		bsciDevAdminRowStatus				RowStatus,
	        bsciDevAdminDisableStatusRequest		INTEGER
	}

bsciDevAdminControlUnitID OBJECT-TYPE
	SYNTAX 	INTEGER (0..31)
	ACCESS read-only
	STATUS mandatory
	DESCRIPTION "Control Unit identifier."
	::= { bsciDevAdminEntry 1 }

bsciDevAdminDeviceUnitID OBJECT-TYPE
	SYNTAX 	INTEGER (0..31)
	ACCESS read-only
	STATUS mandatory
	DESCRIPTION "Device Unit identifier."
	::= { bsciDevAdminEntry 2 }

bsciDevAdminConnectionID OBJECT-TYPE
	SYNTAX 	INTEGER (0..255)
	ACCESS read-write
	STATUS mandatory
	DESCRIPTION "The BSCI port connection ID for the device."
	DEFVAL { 0 }
	::= { bsciDevAdminEntry 3 }

bsciDevAdminSingleUserVC OBJECT-TYPE
	SYNTAX 	INTEGER {
				no(1),
				yes(2)
				}
	ACCESS read-write
	STATUS mandatory
	DESCRIPTION "Specifies whether each end of the connection is within
				a same Control Unit/Device Type pair."
	DEFVAL { no }
	::= { bsciDevAdminEntry 4 }

bsciDevAdminTransTextSupported OBJECT-TYPE
	SYNTAX 	INTEGER {
				no(1),
				yes(2)
				}
	ACCESS read-write
	STATUS mandatory
	DESCRIPTION "Causes all characters transmitted to be treated as data."
	DEFVAL { no }
	::= { bsciDevAdminEntry 5 }

bsciDevAdminPrinterAttached OBJECT-TYPE
	SYNTAX 	INTEGER {
				no(1),
				yes(2)
				}
	ACCESS read-write
	STATUS mandatory
	DESCRIPTION "Specifies whether the device has a printer attached."
	DEFVAL { no }
	::= { bsciDevAdminEntry 6 }

bsciDevAdminRowStatus OBJECT-TYPE
	SYNTAX RowStatus
	ACCESS read-write
	STATUS mandatory
	DESCRIPTION 
            "This variable is used to manage the creation and deletion
            of conceptual rows in the bsciDevAdminTable and follows the
            SNMPv2 RowStatus conventions by supporting the following values:

                 - `active', which indicates that the conceptual row is
                available for use by the managed device.  For a management
                protocol set operation, a genErr response is returned when
                the row does not exist.

                 - `createAndGo', which is supplied by a management
                 station wishing to create a new instance of a
                 conceptual row and to have its status automatically set
                 to active, making it available for use by the managed
                 device.  For a management protocol set operation, a
                 genErr response is returned when the row already exists.

                 - `destroy', which is supplied by a management station
                 wishing to delete all of the instances associated with
                 an existing conceptual row.

            Note that all of the above values may be specified in a
            management protocol set operation, and only the 'active'
            value will be returned in response to a management protocol
            retrieval operation.  For a management protocol set operation,
            if other variable bindings are included in the same PDU, then
            a genErr response is returned."
	::= { bsciDevAdminEntry 7 }

bsciDevAdminDisableStatusRequest OBJECT-TYPE
	SYNTAX INTEGER {
			normal (1),
			none (2),
			always-active (3)
			}
	ACCESS read-write
	STATUS mandatory
	DESCRIPTION "Determines how the BSCI port will report the status
		     of the attached device.  Normal status- the port will
		     report what the device reports.  No status- the port will
		     report status only if the device is active.  Always active
		     status- the port will always report the device as active."
	DEFVAL { normal }
	::= { bsciDevAdminEntry 8 }

--
-- BSC Interactive Device Operational Table
--

bsciDevOperTable OBJECT-TYPE
	SYNTAX SEQUENCE OF BsciDevOperEntry
	ACCESS not-accessible
	STATUS mandatory
	DESCRIPTION
			"A list of BSC Interactive devices."
	::= { portBsciGroup 6 }

bsciDevOperEntry OBJECT-TYPE
	SYNTAX BsciDevOperEntry
	ACCESS not-accessible
	STATUS mandatory
	DESCRIPTION
			"A BSCI Interactive Device entry containing objects
			relating to the device that are configurable by the user."
	INDEX { nlIfRlp, nlIfPort, bsciDevOperControlUnitID,
			bsciDevOperDeviceUnitID }
	::= { bsciDevOperTable 1 }

BsciDevOperEntry ::=
	SEQUENCE {
		bsciDevOperControlUnitID			INTEGER,
		bsciDevOperDeviceUnitID				INTEGER,
		bsciDevOperConnectionID				INTEGER,
		bsciDevOperSingleUserVC				INTEGER,
		bsciDevOperTransTextSupported		INTEGER,
		bsciDevOperPrinterAttached			INTEGER,
		bsciDevOperDisableStatusRequest			INTEGER
	}

bsciDevOperControlUnitID OBJECT-TYPE
	SYNTAX 	INTEGER (0..31)
	ACCESS read-only
	STATUS mandatory
	DESCRIPTION "Control Unit identifier."
	::= { bsciDevOperEntry 1 }

bsciDevOperDeviceUnitID OBJECT-TYPE
	SYNTAX 	INTEGER (0..31)
	ACCESS read-only
	STATUS mandatory
	DESCRIPTION "Device Unit identifier."
	::= { bsciDevOperEntry 2 }

bsciDevOperConnectionID OBJECT-TYPE
	SYNTAX 	INTEGER (0..255)
	ACCESS read-only
	STATUS mandatory
	DESCRIPTION "The BSCI port connection ID for the device."
	::= { bsciDevOperEntry 3 }

bsciDevOperSingleUserVC OBJECT-TYPE
	SYNTAX 	INTEGER {
				no(1),
				yes(2)
				}
	ACCESS read-only
	STATUS mandatory
	DESCRIPTION "Specifies whether each end of the connection is within
				a same Control Unit/Device Type pair."
	::= { bsciDevOperEntry 4 }

bsciDevOperTransTextSupported OBJECT-TYPE
	SYNTAX 	INTEGER {
				no(1),
				yes(2)
				}
	ACCESS read-only
	STATUS mandatory
	DESCRIPTION "Causes all characters transmitted to be treated as data."
	::= { bsciDevOperEntry 5 }

bsciDevOperPrinterAttached OBJECT-TYPE
	SYNTAX 	INTEGER {
				no(1),
				yes(2)
				}
	ACCESS read-only
	STATUS mandatory
	DESCRIPTION "Specifies whether the device has a printer attached."
	::= { bsciDevOperEntry 6 }

bsciDevOperDisableStatusRequest OBJECT-TYPE
	SYNTAX INTEGER {
			normal (1),
			none (2),
			always-active (3)
			}
	ACCESS read-only
	STATUS mandatory
	DESCRIPTION "Determines how the BSCI port will report the status
		     of the attached device.  Normal status- the port will
		     report what the device reports.  No status- the port will
		     report status only if the device is active.  Always active
		     status- the port will always report the device as active."
	::= { bsciDevOperEntry 7 }

portSdlcGroup OBJECT IDENTIFIER ::=  { port 5 }

portSdlcAdminTable  OBJECT-TYPE
                    SYNTAX      SEQUENCE OF PortSdlcAdminEntry
                    ACCESS      not-accessible
                    STATUS      mandatory
                    DESCRIPTION
                            "This table contains Netlink Enterprise specific
                            objects to manage SDLC port. Changing on of the
                            these parameters may take effect in the operating
                            port immediately or may wait until the interface is                             restarted depending on the details of the 
                            implementation.

                            Most of the objects in this read-write table have 
                            corresponding read-only objects in the 
                            portSdlcOperTable that return the current 
                            operating value.

                            The operating values may be different from these 
                            configured values if a configured parameter was 
                            configured afterthe interface was started."
                    ::= { portSdlcGroup 1 }

portSdlcAdminEntry  OBJECT-TYPE
                    SYNTAX      PortSdlcAdminEntry
                    ACCESS      not-accessible
                    STATUS      mandatory
                    DESCRIPTION
                            "A list of configured values for an SDLC port."
                    INDEX   { nlIfRlp, nlIfPort }
                    ::= { portSdlcAdminTable 1 }

PortSdlcAdminEntry  ::= SEQUENCE
{
        portSdlcAdminCommit         INTEGER,
        portSdlcAdminMAXRetries     INTEGER,
        portSdlcAdminMAXOut         INTEGER,
        portSdlcAdminPadType        INTEGER,
        portSdlcAdminGenerateClock INTEGER,
        portSdlcAdminRcvClockFromDTE INTEGER,
        portSdlcAdminNrz INTEGER,
        portSdlcAdminPacketSize INTEGER,
        portSdlcAdminDisableRequestDisconnect INTEGER,
        portSdlcAdminLPDASupport INTEGER,
        portSdlcAdminConnector   INTEGER,
        portSdlcAdminSpeed       INTEGER,
		portSdlcAdminRowStatus   RowStatus,
        portSdlcAdminIdleFillChar    INTEGER,
        portSdlcAdminInactivityTimer INTEGER,
        portSdlcAdminL1Duplex        INTEGER
}

portSdlcAdminCommit      OBJECT-TYPE
                         SYNTAX      INTEGER
                         ACCESS      read-write
                         STATUS      obsolete
                         DESCRIPTION
                             "Writing a value to this object commits the
                             the SDLC port related modified configuration
                             values to the database."
                         DEFVAL { 0 }
                         ::= { portSdlcAdminEntry 1 }

portSdlcAdminMAXRetries  OBJECT-TYPE
                         SYNTAX      INTEGER (0..99)
                         ACCESS      read-write
                         STATUS      mandatory
                         DESCRIPTION
                             "This object defines the max. number of retries
                             to a non-responding Link station, before putting
                             the Link station to slow-poll list if it is not
                             Normal response Mode OR disconnecting the link 
                             station if it is data txfr state." 

                         DEFVAL { 5 }
                         ::= { portSdlcAdminEntry 2 }

portSdlcAdminMAXOut      OBJECT-TYPE
                         SYNTAX      INTEGER  (1..7)
                         ACCESS      read-write
                         STATUS      mandatory
                         DESCRIPTION
                             "This object defines the number of outstanding 
                             frames for triggering window full condition."

                         DEFVAL { 7 }
                         ::= { portSdlcAdminEntry 3 }

portSdlcAdminPadType      OBJECT-TYPE
                                    SYNTAX      INTEGER
                                    {
                                        xpad (1),
                                        tpad (2),
                                        hpad (3),
                                        npad (4)
                                    }
                                    ACCESS      read-write
                                    STATUS      mandatory
                                    DESCRIPTION
                                        "This object defines the SNA
                                         PAD types."
                                    DEFVAL { tpad }
                                    ::= { portSdlcAdminEntry 4 }

portSdlcAdminGenerateClock      OBJECT-TYPE
                                SYNTAX      INTEGER
                                {
                                        no (1),
                                        yes (2)
                                }
                                ACCESS      read-write
                                STATUS      mandatory
                                DESCRIPTION
                                    "This object defines if the port would
                                     generate clock."

                                DEFVAL { yes }
                                ::= { portSdlcAdminEntry 5 }

portSdlcAdminRcvClockFromDTE    OBJECT-TYPE
                                SYNTAX      INTEGER
                                {
                                        no (1),
                                        yes (2)
                                }
                                ACCESS      read-write
                                STATUS      mandatory
                                DESCRIPTION
                                    "This object defines if the rcv clock will
                                     be used from DTE."

                                DEFVAL { no }
                                ::= { portSdlcAdminEntry 6 }

portSdlcAdminNrz                OBJECT-TYPE
                                SYNTAX      INTEGER
                                {
                                        no (1),
                                        yes (2)
                                }
                                ACCESS      read-write
                                STATUS      mandatory
                                DESCRIPTION
                                    "This object defines the data encoding
                                     at the physical layer"

                                DEFVAL { yes }
                                ::= { portSdlcAdminEntry 7 }

portSdlcAdminPacketSize         OBJECT-TYPE
                                SYNTAX      INTEGER (16..4096)
                                ACCESS      read-write
                                STATUS      mandatory
                                DESCRIPTION
                                    "This object defines the packet size of the
                                     X25 layer used by SNA PAD"

                                DEFVAL { 1024 }
                                ::= { portSdlcAdminEntry 8 }

portSdlcAdminDisableRequestDisconnect      OBJECT-TYPE
                                           SYNTAX      INTEGER
                                           {
                                                no (1),
                                                yes (2)
                                           }
                                           ACCESS      read-write
                                           STATUS      mandatory
                                           DESCRIPTION
                                    "This object defines if a Request To  
                                    Disconnect(RD) will be sent when remote
                                    PAD clear the connection"

                                           DEFVAL { no }
                                           ::= { portSdlcAdminEntry 9 }

portSdlcAdminLPDASupport     OBJECT-TYPE
                             SYNTAX      INTEGER
                             {  
                                        none (1),
                                        lpda-1 (2),
                                        lpda-2 (3)
                             }
                             ACCESS      read-write
                             STATUS      mandatory
                             DESCRIPTION
                                    "This object defines the type LPDA support
                                     on SDLC port."

                             DEFVAL { none }
                             ::= { portSdlcAdminEntry 10 }

portSdlcAdminConnector     OBJECT-TYPE
                             SYNTAX      INTEGER
                             {  
                                        rs232 (3),
										v35 (5),
										rs449 (6),
										rs530 (7),
										x21 (8),
										t1 (10)
                             }
                             ACCESS      read-write
                             STATUS      mandatory
                             DESCRIPTION
                                    "This object defines the connector type
                                     of the SDLC port."

                             ::= { portSdlcAdminEntry 11 }

portSdlcAdminSpeed     OBJECT-TYPE
	               SYNTAX      INTEGER (75..2048000)
                       ACCESS      read-write
                       STATUS      mandatory
                       DESCRIPTION
			"This object defines the speed of the SDLC port.  The speed may
			 only be set to one of a series of reasonable values, and if an attempt is made 
			 to set the speed to a value which is within the valid range but not equal to one 
			 of these values, the speed will be rounded up.  If the connector type of the port 
			 is RS232, the port could be a standard port or a high speed port.  If the port is 
			 a high speed RS232 port, the maximum valid speed is 256000.  If the port is a standard 
			 RS232 port, the maximum valid speed is 64000 on the FRX4000/SS1840 and 19200
			 on all other products.  It may be possible to set the speed of a standard RS232 port 
			 to a speed which is valid for a high speed RS232 port but invalid for a standard 
			 RS232 port. In this case, the port may not end up having the invalid speed.  The default
			 speed for a standard RS232 port on the FRX6000 is 19200."
			 DEFVAL { 64000 }
                             ::= { portSdlcAdminEntry 12 }

portSdlcAdminRowStatus     OBJECT-TYPE
                             SYNTAX      RowStatus
                             ACCESS      read-write
                             STATUS      mandatory
                             DESCRIPTION
            "This variable is used to manage the creation and deletion
            of conceptual rows in the portSdlcAdminTable and follows the
            SNMPv2 RowStatus conventions by supporting the following values:

                 - `active', which indicates that the conceptual row is
                available for use by the managed device, and which is
                supplied by a management station wishing to exercise an
                on-line update of the existing conceptual row.  For a
                management protocol set operation, a genErr response is
                returned when the row does not exist.

                 - `createAndGo', which is supplied by a management
                 station wishing to create a new instance of a
                 conceptual row and to have its status automatically set
                 to active, making it available for use by the managed
                 device.  For a management protocol set operation, a
                 genErr response is returned when the row already exists.

                 - `destroy', which is supplied by a management station
                 wishing to delete all of the instances associated with
                 an existing conceptual row.

            Note that all of the above values may be specified in a
            management protocol set operation, and only the 'active'
            value will be returned in response to a management protocol
            retrieval operation.  For a management protocol set operation,
            if other variable bindings are included in the same PDU, then
            a genErr response is returned."

                             ::= { portSdlcAdminEntry 13 }

portSdlcAdminIdleFillChar     OBJECT-TYPE
                              SYNTAX      INTEGER
                              {
                                  hex-ff (1),
                                  hex-7e (2)
                              }
                              ACCESS      read-write
                              STATUS      mandatory
                              DESCRIPTION
                                  "This object specifies a character that
                                   wll be inserted into the stream when the
                                   SNA link is idle."
                              DEFVAL { hex-ff }
                              ::= { portSdlcAdminEntry 14 }

portSdlcAdminInactivityTimer  OBJECT-TYPE
                              SYNTAX      INTEGER (15..250)
                              ACCESS      read-write
                              STATUS      mandatory
                              DESCRIPTION
                                  "This object determines how long the node
                                   will wait with no activity on the port
                                   before it will declare the attached device
                                   down."
                              DEFVAL { 50 }
                              ::= { portSdlcAdminEntry 15 }

portSdlcAdminL1Duplex         OBJECT-TYPE
                              SYNTAX      INTEGER
                              {
                                  full-duplex (1),
                                  half-duplex (2)
                              }
                              ACCESS      read-write
                              STATUS      mandatory
                              DESCRIPTION
                                  "This object determines whether level-1
                                   (physical layer) transmission can be in
                                   one (half duplex) or both (full duplex)
                                   directions at once."
                              DEFVAL { full-duplex }
                              ::= { portSdlcAdminEntry 16 }

portSdlcOperTable  OBJECT-TYPE
                   SYNTAX      SEQUENCE OF PortSdlcOperEntry
                   ACCESS      not-accessible
                   STATUS      mandatory
                   DESCRIPTION
                       "This table contains current Netlink enterprise specific
                       port parameters"

                    ::= { portSdlcGroup 2 }

portSdlcOperEntry  OBJECT-TYPE
                   SYNTAX      PortSdlcOperEntry
                   ACCESS      not-accessible
                   STATUS      mandatory
                   DESCRIPTION
                            "A list of operational values for an SDLC port."

                   INDEX   { nlIfRlp, nlIfPort }
                   ::= { portSdlcOperTable 1 }

PortSdlcOperEntry  ::= SEQUENCE
{
        portSdlcOperCommit         INTEGER,
        portSdlcOperMAXRetries     INTEGER,
        portSdlcOperMAXOut         INTEGER,
        portSdlcOperPadType        INTEGER,
        portSdlcOperGenerateClock INTEGER,
        portSdlcOperRcvClockFromDTE INTEGER,
        portSdlcOperNrz INTEGER,
        portSdlcOperPacketSize INTEGER,
        portSdlcOperDisableRequestDisconnect INTEGER,
        portSdlcOperLPDASupport INTEGER,
        portSdlcOperConnector   INTEGER,
        portSdlcOperSpeed       INTEGER,
        portSdlcOperIdleFillChar    INTEGER,
        portSdlcOperInactivityTimer INTEGER,
        portSdlcOperL1Duplex        INTEGER
}

portSdlcOperCommit      OBJECT-TYPE
                        SYNTAX      INTEGER
                        ACCESS      read-only
                        STATUS      obsolete
                        DESCRIPTION
                             "This object is not used."
                        ::= { portSdlcOperEntry 1 }

portSdlcOperMAXRetries  OBJECT-TYPE
                        SYNTAX      INTEGER (0..99)
                        ACCESS      read-only
                        STATUS      mandatory
                        DESCRIPTION
                             "This object defines the max. number of retries
                             to a non-responding Link station, before putting
                             the Link station to slow-poll list if it is not
                             Normal response Mode OR disconnecting the link 
                             station if it is data txfr state." 
                        ::= { portSdlcOperEntry 2 }

portSdlcOperMAXOut      OBJECT-TYPE
                        SYNTAX      INTEGER (1..7)
                        ACCESS      read-only
                        STATUS      mandatory
                        DESCRIPTION
                             "This object defines the number of outstanding 
                             frames for triggering window full condition."

                        ::= { portSdlcOperEntry 3 }

portSdlcOperPadType      OBJECT-TYPE
                                   SYNTAX      INTEGER
                                   {
                                       xpad (1),
                                       tpad (2),
                                       hpad (3),
                                       npad (4)
                                   }
                                   ACCESS      read-only
                                   STATUS      mandatory
                                   DESCRIPTION
                                       "This object defines the SNA
                                       PAD type"

                                   ::= { portSdlcOperEntry 4 }

portSdlcOperGenerateClock      OBJECT-TYPE
                               SYNTAX      INTEGER
                               {
                                       no (1),
                                       yes (2)
                               }
                               ACCESS      read-only
                               STATUS      mandatory
                               DESCRIPTION
                                    "This object defines if the port would
                                     generate clock."
                               ::= { portSdlcOperEntry 5 }

portSdlcOperRcvClockFromDTE    OBJECT-TYPE
                               SYNTAX      INTEGER
                               {
                                       no (1),
                                       yes (2)
                               }
                               ACCESS      read-only
                               STATUS      mandatory
                               DESCRIPTION
                                    "This object defines if the rcv clock will
                                     be used from DTE."
                               ::= { portSdlcOperEntry 6 }

portSdlcOperNrz                OBJECT-TYPE
                               SYNTAX      INTEGER
                               {
                                       no (1),
                                       yes (2)
                               }
                               ACCESS      read-only
                               STATUS      mandatory
                               DESCRIPTION
                                    "This object defines the data encoding
                                    at the physical layer"
                               ::= { portSdlcOperEntry 7 }

portSdlcOperPacketSize         OBJECT-TYPE
                               SYNTAX      INTEGER (16..4096)
                               ACCESS      read-only
                               STATUS      mandatory
                               DESCRIPTION
                                    "This object defines the packet size of the
                                     X25 layer used by SNA PAD"

                               ::= { portSdlcOperEntry 8 }

portSdlcOperDisableRequestDisconnect      OBJECT-TYPE
                                          SYNTAX      INTEGER
                                          {
                                                 no (1),
                                                 yes (2)
                                          }
                                          ACCESS      read-only
                                          STATUS      mandatory
                                          DESCRIPTION
                                    "This object defines if a Request To  
                                    Disconnect(RD) will be sent when remote
                                    PAD clear the connection"
                                          ::= { portSdlcOperEntry 9 }

portSdlcOperLPDASupport     OBJECT-TYPE
                            SYNTAX      INTEGER
                            {  
                                       none (1),
                                       lpda-1 (2),
                                       lpda-2 (3)
                            }
                            ACCESS      read-only
                            STATUS      mandatory
                            DESCRIPTION
                                    "This object defines the type LPDA support
                                     on SDLC port."
                            ::= { portSdlcOperEntry 10 }

portSdlcOperConnector     OBJECT-TYPE
                             SYNTAX      INTEGER
                             {  
                                        rs232 (3),
                                        v35 (5),
                                        rs449 (6),
										rs530 (7),
										x21 (8),
										t1 (10)
                             }
                             ACCESS      read-only
                             STATUS      mandatory
                             DESCRIPTION
                                    "This object defines the operational
									connector type of the SDLC port."

                             ::= { portSdlcOperEntry 11 }

portSdlcOperSpeed     OBJECT-TYPE
                             SYNTAX      INTEGER
                             ACCESS      read-only
                             STATUS      mandatory
                             DESCRIPTION
                                    "This object defines the operational speed
                                     of the SDLC port."

                             ::= { portSdlcOperEntry 12 }

portSdlcOperIdleFillChar      OBJECT-TYPE
                              SYNTAX      INTEGER
                              {
                                  hex-ff (1),
                                  hex-7e (2)
                              }
                              ACCESS      read-only
                              STATUS      mandatory
                              DESCRIPTION
                                  "This object specifies a character that
                                   wll be inserted into the stream when the
                                   SNA link is idle."
                              ::= { portSdlcOperEntry 13 }

portSdlcOperInactivityTimer   OBJECT-TYPE
                              SYNTAX      INTEGER (15..250)
                              ACCESS      read-only
                              STATUS      mandatory
                              DESCRIPTION
                                  "This object determines how long the node
                                   will wait with no activity on the port
                                   before it will declare the attached device
                                   down."
                              ::= { portSdlcOperEntry 14 }

portSdlcOperL1Duplex          OBJECT-TYPE
                              SYNTAX      INTEGER
                              {
                                  full-duplex (1),
                                  half-duplex (2)
                              }
                              ACCESS      read-only
                              STATUS      mandatory
                              DESCRIPTION
                                  "This object determines whether level-1
                                   (physical layer) transmission can be in
                                   one (half duplex) or both (full duplex)
                                   directions at once."
                              ::= { portSdlcOperEntry 15 }

-- The lSSdlcAdminTable contains information about the PUs configured on
-- an SDLC port. Note that deleting of a PU entry does not affect the
-- existence of the PU for the running protocol. The PU record is removed
-- from the database file, but will remain known to the node until it is
-- rebooted or until an online update of the port is performed. This is
-- consistent with the way PU information is handled when configuring
-- through the user interface menu system. 

lSSdlcAdminTable  OBJECT-TYPE
                  SYNTAX      SEQUENCE OF LSSdlcAdminEntry
                  ACCESS      not-accessible
                  STATUS      mandatory
                  DESCRIPTION
                      "This table contains Enterprise specific Link station
                      configurable parameters to manage the link stations."

                  ::= { portSdlcGroup 3 }

lSSdlcAdminEntry  OBJECT-TYPE
                  SYNTAX      LSSdlcAdminEntry
                  ACCESS      not-accessible
                  STATUS      mandatory
                  DESCRIPTION
                      "A list of configured values for an SDLC port."

                  INDEX   { nlIfRlp, nlIfPort, sdlcLSAddress }
                  ::= { lSSdlcAdminTable 1 }

LSSdlcAdminEntry  ::= SEQUENCE
{
        lSSdlcAdminLocalSub         NlSubscriberAddress,
        lSSdlcAdminRemoteSub        NlSubscriberAddress,
        lSSdlcAdminAutoCall         INTEGER,
        lSSdlcAdminRetryTime        INTEGER,
        lSSdlcAdminRetryCount       INTEGER,
        lSSdlcAdminLlc2Conversion   INTEGER,
        lSSdlcAdminLPDAResourceID   INTEGER,
		lSSdlcAdminRowStatus   		RowStatus,
        lSSdlcAdminL2DatMode        INTEGER
}

lSSdlcAdminLocalSub      OBJECT-TYPE
                         SYNTAX      NlSubscriberAddress
                         ACCESS      read-write
                         STATUS      mandatory
                         DESCRIPTION
                             "This object defines the local subscriber ID
                             of the Link Station"

                         ::= { lSSdlcAdminEntry 1 }

lSSdlcAdminRemoteSub      OBJECT-TYPE
                          SYNTAX      NlSubscriberAddress
                          ACCESS      read-write
                          STATUS      mandatory
                          DESCRIPTION
                             "This object defines the remote subscriber ID
                             used to connect to remote Link Station"
                          ::= { lSSdlcAdminEntry 2 }

lSSdlcAdminAutoCall       OBJECT-TYPE
                          SYNTAX      INTEGER
                          {
                                no (1),
                                yes (2)
                          }
                          ACCESS      read-write
                          STATUS      mandatory
                          DESCRIPTION
                              "This object defines if auto call is enabled for
                              the link station. If enabled, the link station
                              will initiate connection establishment, when
                              appropriate. Else, it will passively listen to
                              the connection request for establish a connection
                              with the remote PAD"

                          DEFVAL { no }
                          ::= { lSSdlcAdminEntry 3 }

lSSdlcAdminRetryTime      OBJECT-TYPE
                          SYNTAX      INTEGER (15..225)
                          ACCESS      read-write
                          STATUS      mandatory
                          DESCRIPTION
                              "This object is used, only when 
                              lSSdlcAdminAutoCall object is yes. This defines
                              the time interval measured in seconds in which
                              the connection request is retried"

                          DEFVAL { 60 }
                          ::= { lSSdlcAdminEntry 4 }

lSSdlcAdminRetryCount     OBJECT-TYPE
                          SYNTAX      INTEGER (0..255)
                          ACCESS      read-write
                          STATUS      mandatory
                          DESCRIPTION
                              "This object is used, only when 
                              lSSdlcAdminAutoCall object is yes. This defines
                              the number of times the connection initiation
                              is retried before given up. The value of Zero(0)
                              means to try indefinitely"

                          DEFVAL { 0 }
                          ::= { lSSdlcAdminEntry 5 }

lSSdlcAdminLlc2Conversion   OBJECT-TYPE
                            SYNTAX      INTEGER
                            {
                                no (1),
                                yes (2)
                            }
                            ACCESS      read-write
                            STATUS      mandatory
                            DESCRIPTION
                                "This object defines if this link station 
                                connects to a LLC2 device/host."

                            DEFVAL { no }
                            ::= { lSSdlcAdminEntry 6 }

lSSdlcAdminLPDAResourceID       OBJECT-TYPE
                                SYNTAX      INTEGER (0..255)
                                ACCESS      read-write
                                STATUS      mandatory
                                DESCRIPTION
                                    "This objects the resource ID used during
                                     LPDA command support"

                                DEFVAL { 0 }
                                ::= { lSSdlcAdminEntry 7 }

lSSdlcAdminRowStatus			OBJECT-TYPE
								SYNTAX      RowStatus
								ACCESS      read-write
								STATUS      mandatory
                                DESCRIPTION
            "This variable is used to manage the creation and deletion
            of conceptual rows in the lSSdlcAdminTable and follows the
            SNMPv2 RowStatus conventions by supporting the following values:

                 - `active', which indicates that the conceptual row is
                available for use by the managed device.  For a management
                protocol set operation, a genErr response is returned when
                the row does not exist.

                 - `createAndGo', which is supplied by a management
                 station wishing to create a new instance of a
                 conceptual row and to have its status automatically set
                 to active, making it available for use by the managed
                 device.  For a management protocol set operation, a
                 genErr response is returned when the row already exists.

                 - `destroy', which is supplied by a management station
                 wishing to delete all of the instances associated with
                 an existing conceptual row.

            Note that all of the above values may be specified in a
            management protocol set operation, and only the 'active'
            value will be returned in response to a management protocol
            retrieval operation.  For a management protocol set operation,
            if other variable bindings are included in the same PDU, then
            a genErr response is returned.

            Also note that deleting a PU entry will only remove it from
            the database file, and it's existence will still be known by
            the protocol until the node is rebooted or until an online
            update of the port is performed."

								::= { lSSdlcAdminEntry 8 }

lSSdlcAdminL2DatMode      OBJECT-TYPE
                          SYNTAX      INTEGER
                          {
                                two-way-alternate (1),
                                two-way-simultaneous (2)
                          }
                          ACCESS      read-write
                          STATUS      mandatory
                          DESCRIPTION
                              "This object determines whether transmission
                               can be in one (alternate) or two (simultaneous)
                               directions at the same time."
                          DEFVAL { two-way-alternate }
                          ::= { lSSdlcAdminEntry 9 }

lSSdlcOperTable  OBJECT-TYPE
                 SYNTAX      SEQUENCE OF LSSdlcOperEntry
                 ACCESS      not-accessible
                 STATUS      mandatory
                 DESCRIPTION
                     "This table contains the operational parameters of the
                     SDLC port"
                 ::= { portSdlcGroup 4 }

lSSdlcOperEntry  OBJECT-TYPE
                 SYNTAX      LSSdlcOperEntry
                 ACCESS      not-accessible
                 STATUS      mandatory
                 DESCRIPTION
                      "A list of configured values for an SDLC port."
                 INDEX   { nlIfRlp, nlIfPort, sdlcLSAddress }
                 ::= { lSSdlcOperTable 1 }

LSSdlcOperEntry  ::= SEQUENCE
{
        lSSdlcOperLocalSub         NlSubscriberAddress,
        lSSdlcOperRemoteSub        NlSubscriberAddress,
        lSSdlcOperAutoCall         INTEGER,
        lSSdlcOperRetryTime        INTEGER,
        lSSdlcOperRetryCount       INTEGER,
        lSSdlcOperLlc2Conversion   INTEGER,
        lSSdlcOperLPDAResourceID   INTEGER,
        lSSdlcOperL2DatMode        INTEGER
}

lSSdlcOperLocalSub      OBJECT-TYPE
                        SYNTAX      NlSubscriberAddress
                        ACCESS      read-only
                        STATUS      mandatory
                        DESCRIPTION
                             "This object defines the local subscriber ID
                             of the Link Station"
                        ::= { lSSdlcOperEntry 1 }

lSSdlcOperRemoteSub      OBJECT-TYPE
                         SYNTAX      NlSubscriberAddress
                         ACCESS      read-only
                         STATUS      mandatory
                         DESCRIPTION
                             "This object defines the remote subscriber ID
                             used to connect to remote Link Station"
                         ::= { lSSdlcOperEntry 2 }

lSSdlcOperAutoCall       OBJECT-TYPE
                         SYNTAX      INTEGER
                         {
                               no (1),
                               yes (2)
                         }
                         ACCESS      read-only
                         STATUS      mandatory
                         DESCRIPTION
                              "This object defines if auto call is enabled for
                              the link station. If enabled, the link station
                              will initiate connection establishment, when
                              appropriate. Else, it will passively listen to
                              the connection request for establish a connection
                              with the remote PAD"
                         ::= { lSSdlcOperEntry 3 }

lSSdlcOperRetryTime      OBJECT-TYPE
                         SYNTAX      INTEGER (15..225)
                         ACCESS      read-only
                         STATUS      mandatory
                         DESCRIPTION
                              "This object is valid, only when 
                              lSSdlcAdminAutoCall object is yes. This defines
                              the time interval measured in seconds in which
                              the connection request is retried"
                         ::= { lSSdlcOperEntry 4 }

lSSdlcOperRetryCount     OBJECT-TYPE
                         SYNTAX      INTEGER (0..255)
                         ACCESS      read-only
                         STATUS      mandatory
                         DESCRIPTION
                              "This object is used, only when 
                              lSSdlcAdminAutoCall object is yes. This defines
                              the number of times the connection initiation
                              is retried before given up. The value of Zero(0)
                              means to try indefinitely"
                         ::= { lSSdlcOperEntry 5 }

lSSdlcOperLlc2Conversion   OBJECT-TYPE
                           SYNTAX      INTEGER
                           {
                               no (1),
                               yes (2)
                           }
                           ACCESS      read-only
                           STATUS      mandatory
                           DESCRIPTION
                                "This object defines if this link station 
                                connects to a LLC2 device/host."
                           ::= { lSSdlcOperEntry 6 }

lSSdlcOperLPDAResourceID       OBJECT-TYPE
                               SYNTAX      INTEGER (0..255)
                               ACCESS      read-only
                               STATUS      mandatory
                               DESCRIPTION
                                    "This objects the resource ID used during
                                     LPDA command support"
                               ::= { lSSdlcOperEntry 7 }

lSSdlcOperL2DatMode       OBJECT-TYPE
                          SYNTAX      INTEGER
                          {
                                two-way-alternate (1),
                                two-way-simultaneous (2)
                          }
                          ACCESS      read-only
                          STATUS      mandatory
                          DESCRIPTION
                              "This object determines whether transmission
                               can be in one (alternate) or two (simultaneous)
                               directions at the same time."
                          ::= { lSSdlcOperEntry 8 }

lSSdlcLlc2AdminTable  OBJECT-TYPE
                      SYNTAX      SEQUENCE OF LSSdlcLlc2AdminEntry
                      ACCESS      not-accessible
                      STATUS      mandatory
                      DESCRIPTION
                          "This table contains the LLC2 related parameters
                          used to configure LLC2 session, when the SDLC 
                          station is connected to a LLC2 device at the remote
                          end"
                     ::= { portSdlcGroup 5 }

lSSdlcLlc2AdminEntry  OBJECT-TYPE
                      SYNTAX      LSSdlcLlc2AdminEntry
                      ACCESS      not-accessible
                      STATUS      mandatory
                      DESCRIPTION
                          "A list of configured values for an SDLC port."
                      INDEX   { nlIfRlp, nlIfPort, sdlcLSAddress }
                      ::= { lSSdlcLlc2AdminTable 1 }

-- The lSSdlcLlc2AdminTable contains information about the PUs configured
-- on an SDLC port. Note that deleting of a PU entry does not affect the
-- existence of the PU for the running protocol. The PU record is removed
-- from the database file, but will remain known to the node until it is
-- rebooted or until an online update of the port is performed. This is
-- consistent with the way PU information is handled when configuring
-- through the user interface menu system. 

LSSdlcLlc2AdminEntry  ::= SEQUENCE
{
        lSSdlcLlc2AdminLocalSap    INTEGER,
        lSSdlcLlc2AdminLocalMac    PhysAddress,
        lSSdlcLlc2AdminIdblk       INTEGER,
        lSSdlcLlc2AdminIdnum       INTEGER,
        lSSdlcLlc2AdminLanTi       INTEGER,
        lSSdlcLlc2AdminLanT1       INTEGER,
        lSSdlcLlc2AdminLanT2       INTEGER,
        lSSdlcLlc2AdminLanN2       INTEGER,
        lSSdlcLlc2AdminLanN3       INTEGER,
        lSSdlcLlc2AdminLanTw       INTEGER,
        lSSdlcLlc2AdminBAG         INTEGER,
        lSSdlcLlc2AdminPriority    INTEGER,
		lSSdlcLlc2AdminRowStatus	RowStatus,
        lSSdlcLlc2AdminSuppressXID  INTEGER
}

lSSdlcLlc2AdminLocalSap      OBJECT-TYPE
                             SYNTAX      INTEGER (0..252)
                             ACCESS      read-write
                             STATUS      mandatory
                             DESCRIPTION
                                 "This object defines Local SAP 
                                 address (multiple of 4)"
                             DEFVAL { 4 }
                             ::= { lSSdlcLlc2AdminEntry 1 }

lSSdlcLlc2AdminLocalMac      OBJECT-TYPE
                             SYNTAX      PhysAddress
                             ACCESS      read-write
                             STATUS      mandatory
                             DESCRIPTION
                                 "This object defines the local MAC address"
                             DEFVAL { '000000000000'H }    -- 00:00:00:00:00:00
                             ::= { lSSdlcLlc2AdminEntry 2 }

lSSdlcLlc2AdminIdblk         OBJECT-TYPE
                             SYNTAX      INTEGER (0..4095)
                             ACCESS      read-write
                             STATUS      mandatory
                             DESCRIPTION
                                 "This object defines idblk used in XID"
                             DEFVAL { 0 }
                             ::= { lSSdlcLlc2AdminEntry 3 }

lSSdlcLlc2AdminIdnum         OBJECT-TYPE
                             SYNTAX      INTEGER (0..1048575)
                             ACCESS      read-write
                             STATUS      mandatory
                             DESCRIPTION
                                 "This object defines idnum used in XID"
                             DEFVAL { 0 }
                             ::= { lSSdlcLlc2AdminEntry 4 }

lSSdlcLlc2AdminLanTi         OBJECT-TYPE
                             SYNTAX      INTEGER (1..50)
                             ACCESS      read-write
                             STATUS      mandatory
                             DESCRIPTION
                                 "This object defines LLC2 inactivity timer
                                  measured in units of seconds"
                             DEFVAL { 30 }
                             ::= { lSSdlcLlc2AdminEntry 5 }

lSSdlcLlc2AdminLanT1         OBJECT-TYPE
                             SYNTAX      INTEGER (1..250)
                             ACCESS      read-write
                             STATUS      mandatory
                             DESCRIPTION
                                 "This object defines LLC2 reply timer
                                  measured in units of 100 milliseconds"
                             DEFVAL { 10 }
                             ::= { lSSdlcLlc2AdminEntry 6 }

lSSdlcLlc2AdminLanT2         OBJECT-TYPE
                             SYNTAX      INTEGER (100..5000)
                             ACCESS      read-write
                             STATUS      mandatory
                             DESCRIPTION
                                 "This object defines Receiver Ack Timer
                                  measured in units of milliseconds"
                             DEFVAL { 100 }
                             ::= { lSSdlcLlc2AdminEntry 7 }

lSSdlcLlc2AdminLanN2         OBJECT-TYPE
                             SYNTAX      INTEGER (0..255)
                             ACCESS      read-write
                             STATUS      mandatory
                             DESCRIPTION
                                 "This object defines Maximum Retransmissions"
                             DEFVAL { 8 }
                             ::= { lSSdlcLlc2AdminEntry 8 }

lSSdlcLlc2AdminLanN3         OBJECT-TYPE
                             SYNTAX      INTEGER (1..127)
                             ACCESS      read-write
                             STATUS      mandatory
                             DESCRIPTION
                                 "This object defines count of I-format LPDU's
                                 before sending Ack"

                             DEFVAL { 3 }
                             ::= { lSSdlcLlc2AdminEntry 9 }

lSSdlcLlc2AdminLanTw         OBJECT-TYPE
                             SYNTAX      INTEGER (1..127)
                             ACCESS      read-write
                             STATUS      mandatory
                             DESCRIPTION
                                 "This object defines Outstanding Frames"
                             DEFVAL { 7 }
                             ::= { lSSdlcLlc2AdminEntry 10 }

lSSdlcLlc2AdminBAG           OBJECT-TYPE
                             SYNTAX      INTEGER (0..16)
                             ACCESS      read-write
                             STATUS      mandatory
                             DESCRIPTION
                                 "This object defines bandwidth allocation 
                                 group"
                             DEFVAL { 0 }
                             ::= { lSSdlcLlc2AdminEntry 11 }

lSSdlcLlc2AdminPriority      OBJECT-TYPE
                             SYNTAX      INTEGER (0..9)
                             ACCESS      read-write
                             STATUS      mandatory
                             DESCRIPTION
                                 "This object defines priority for traffic 
                                 within the node"
                             DEFVAL { 0 }
                             ::= { lSSdlcLlc2AdminEntry 12 }

lSSdlcLlc2AdminRowStatus	OBJECT-TYPE
							SYNTAX      RowStatus
							ACCESS      read-write
							STATUS      mandatory
                            DESCRIPTION
            "This variable is used to manage the creation and deletion
            of conceptual rows in the lSSdlcLlc2AdminTable and follows the
            SNMPv2 RowStatus conventions by supporting the following values:

                 - `active', which indicates that the conceptual row is
                available for use by the managed device.  For a management
                protocol set operation, a genErr response is returned when
                the row does not exist.

                 - `createAndGo', which is supplied by a management
                 station wishing to create a new instance of a
                 conceptual row and to have its status automatically set
                 to active, making it available for use by the managed
                 device.  For a management protocol set operation, a
                 genErr response is returned when the row already exists.

                 - `destroy', which is supplied by a management station
                 wishing to delete all of the instances associated with
                 an existing conceptual row.

            Note that all of the above values may be specified in a
            management protocol set operation, and only the 'active'
            value will be returned in response to a management protocol
            retrieval operation.  For a management protocol set operation,
            if other variable bindings are included in the same PDU, then
            a genErr response is returned.

            Also note that deleting a PU entry will only remove it from
            the database file, and it's existence will still be known by
            the protocol until the node is rebooted or until an online
            update of the port is performed."
							::= { lSSdlcLlc2AdminEntry 13 }

lSSdlcLlc2AdminSuppressXID   OBJECT-TYPE
                             SYNTAX      INTEGER
                             {
                                 no (1),
                                 yes (2)
                             }
                             ACCESS      read-write
                             STATUS      mandatory
                             DESCRIPTION
                                 "This object prevents (if yes) the returning
                                  of an XID in response to a null XID. This
                                  might be desirable if the remote TPAD is not
                                  running PU 2.1. It should be noted that even
                                  if an XID is sent, an SNRM (Set Normal
                                  Response Mode) immediately follows, so the
                                  connection will be established."
                             DEFVAL { no }
                             ::= { lSSdlcLlc2AdminEntry 14 }

lSSdlcLlc2OperTable  OBJECT-TYPE
                     SYNTAX      SEQUENCE OF LSSdlcLlc2OperEntry
                     ACCESS      not-accessible
                     STATUS      mandatory
                     DESCRIPTION
                         "This table contains operartional parameters related
                         to LLC2 session of this link station."
                     ::= { portSdlcGroup 6 }

lSSdlcLlc2OperEntry  OBJECT-TYPE
                     SYNTAX      LSSdlcLlc2OperEntry
                     ACCESS      not-accessible
                     STATUS      mandatory
                     DESCRIPTION
                          "A list of configured values for an SDLC port."
                     INDEX   { nlIfRlp, nlIfPort, sdlcLSAddress }
                     ::= { lSSdlcLlc2OperTable 1 }

LSSdlcLlc2OperEntry  ::= SEQUENCE
{
        lSSdlcLlc2OperLocalSap     INTEGER,
        lSSdlcLlc2OperLocalMac     PhysAddress,
        lSSdlcLlc2OperIdblk        INTEGER,
        lSSdlcLlc2OperIdnum        INTEGER,
        lSSdlcLlc2OperLanTi        INTEGER,
        lSSdlcLlc2OperLanT1        INTEGER,
        lSSdlcLlc2OperLanT2        INTEGER,
        lSSdlcLlc2OperLanN2        INTEGER,
        lSSdlcLlc2OperLanN3        INTEGER,
        lSSdlcLlc2OperLanTw        INTEGER,
        lSSdlcLlc2OperBAG          INTEGER,
        lSSdlcLlc2OperPriority     INTEGER,
        lSSdlcLlc2OperSuppressXID  INTEGER
}

lSSdlcLlc2OperLocalSap       OBJECT-TYPE
                             SYNTAX      INTEGER (0..252)
                             ACCESS      read-only
                             STATUS      mandatory
                             DESCRIPTION
                                 "This object defines Local SAP 
                                 address (multiple of 4)"
                             ::= { lSSdlcLlc2OperEntry 1 }

lSSdlcLlc2OperLocalMac       OBJECT-TYPE
                             SYNTAX      PhysAddress
                             ACCESS      read-only
                             STATUS      mandatory
                             DESCRIPTION
                                 "This object defines the local MAC address"
                             ::= { lSSdlcLlc2OperEntry 2 }

lSSdlcLlc2OperIdblk          OBJECT-TYPE
                             SYNTAX      INTEGER (0..4095)
                             ACCESS      read-only
                             STATUS      mandatory
                             DESCRIPTION
                                 "This object defines idblk used in XID"
                             ::= { lSSdlcLlc2OperEntry 3 }

lSSdlcLlc2OperIdnum          OBJECT-TYPE
                             SYNTAX      INTEGER (0..1048575)
                             ACCESS      read-only
                             STATUS      mandatory
                             DESCRIPTION
                                 "This object defines idnum used in XID"
                             ::= { lSSdlcLlc2OperEntry 4 }

lSSdlcLlc2OperLanTi          OBJECT-TYPE
                             SYNTAX      INTEGER (1..50)
                             ACCESS      read-only
                             STATUS      mandatory
                             DESCRIPTION
                                 "This object defines LLC2 inactivity timer
                                  measured in units of seconds"
                             ::= { lSSdlcLlc2OperEntry 5 }

lSSdlcLlc2OperLanT1          OBJECT-TYPE
                             SYNTAX      INTEGER (1..250)
                             ACCESS      read-only
                             STATUS      mandatory
                             DESCRIPTION
                                 "This object defines LLC2 reply timer
                                  measured in units of 100 milliseconds"
                             ::= { lSSdlcLlc2OperEntry 6 }

lSSdlcLlc2OperLanT2          OBJECT-TYPE
                             SYNTAX      INTEGER (100..5000)
                             ACCESS      read-only
                             STATUS      mandatory
                             DESCRIPTION
                                 "This object defines Receiver Ack Timer
                                  measured in units of milliseconds"
                             ::= { lSSdlcLlc2OperEntry 7 }

lSSdlcLlc2OperLanN2          OBJECT-TYPE
                             SYNTAX      INTEGER (0..255)
                             ACCESS      read-only
                             STATUS      mandatory
                             DESCRIPTION
                                 "This object defines Maximum Retransmissions"
                             ::= { lSSdlcLlc2OperEntry 8 }

lSSdlcLlc2OperLanN3          OBJECT-TYPE
                             SYNTAX      INTEGER (1..127)
                             ACCESS      read-only
                             STATUS      mandatory
                             DESCRIPTION
                                 "This object defines count of I-format LPDU's
                                 before sending Ack"
                             ::= { lSSdlcLlc2OperEntry 9 }

lSSdlcLlc2OperLanTw          OBJECT-TYPE
                             SYNTAX      INTEGER (1..127)
                             ACCESS      read-only
                             STATUS      mandatory
                             DESCRIPTION
                                 "This object defines Outstanding Frames"
                             ::= { lSSdlcLlc2OperEntry 10 }

lSSdlcLlc2OperBAG            OBJECT-TYPE
                             SYNTAX      INTEGER (0..16)
                             ACCESS      read-only
                             STATUS      mandatory
                             DESCRIPTION
                                 "This object defines bandwidth allocation 
                                 group"
                             ::= { lSSdlcLlc2OperEntry 11 }

lSSdlcLlc2OperPriority       OBJECT-TYPE
                             SYNTAX      INTEGER (0..9)
                             ACCESS      read-only
                             STATUS      mandatory
                             DESCRIPTION
                                 "This object defines priority for traffic 
                                 within the node"
                             ::= { lSSdlcLlc2OperEntry 12 }

lSSdlcLlc2OperSuppressXID    OBJECT-TYPE
                             SYNTAX      INTEGER
                             {
                                 no (1),
                                 yes (2)
                             }
                             ACCESS      read-only
                             STATUS      mandatory
                             DESCRIPTION
                                 "This object prevents (if yes) the returning
                                  of an XID in response to a null XID. This
                                  might be desirable if the remote TPAD is not
                                  running PU 2.1. It should be noted that even
                                  if an XID is sent, an SNRM (Set Normal
                                  Response Mode) immediately follows, so the
                                  connection will be established."
                             ::= { lSSdlcLlc2OperEntry 13 }

portT1Group	OBJECT IDENTIFIER ::=	{ port 7 }

portT1AdminTable OBJECT-TYPE
	SYNTAX SEQUENCE OF PortT1AdminEntry
	ACCESS not-accessible
	STATUS mandatory
	DESCRIPTION "The configuration information pertaining to a T1 port.
	T1 ports can operate at full T1 bandwidth or DS0A channelized which provides
	24 separate channels."
	::= { portT1Group 1 }

portT1AdminEntry OBJECT-TYPE
	SYNTAX PortT1AdminEntry
	ACCESS not-accessible
	STATUS mandatory
	DESCRIPTION "A T1 port entry containing objects relating to T1 ports."
	INDEX { nlIfRlp, nlIfPort }
	::= { portT1AdminTable 1 }

PortT1AdminEntry ::=
	SEQUENCE {
		portT1AdminBlockedPortFlag	INTEGER,
		portT1AdminGenerateClock		INTEGER,
		portT1AdminFramingMode		INTEGER,
		portT1AdminFrameModelSelect	INTEGER,
		portT1AdminLineEncoding 		INTEGER,
		portT1AdminLineBuildOut 		INTEGER,
		portT1AdminRowStatus			RowStatus,
		portT1AdminProtocolFraming	INTEGER,
		portT1AdminNRZI				INTEGER
}

portT1AdminBlockedPortFlag OBJECT-TYPE
	SYNTAX INTEGER	{
						no(1),
						yes(2)
					}
	ACCESS read-write
	STATUS mandatory
	DESCRIPTION ""
	::= { portT1AdminEntry 1 }

portT1AdminGenerateClock OBJECT-TYPE
	SYNTAX INTEGER	{
						no(1),
						yes(2)
					}
	ACCESS read-write
	STATUS mandatory
	DESCRIPTION ""
	::= { portT1AdminEntry 2 }

portT1AdminFramingMode OBJECT-TYPE
	SYNTAX INTEGER	{
						fullT1(1),
						ds0aT1(2)
					}
	ACCESS read-write
	STATUS mandatory
	DESCRIPTION "Specifies how this T1 port is to function. ds0AT1 specifies a
	24 channelized T1."
	::= { portT1AdminEntry 3 }

portT1AdminFrameModelSelect OBJECT-TYPE
	SYNTAX INTEGER	{
						d4(1),
						esf(2)
					}
	ACCESS read-write
	STATUS mandatory
	DESCRIPTION ""
	::= { portT1AdminEntry 4 }

portT1AdminLineEncoding OBJECT-TYPE
	SYNTAX INTEGER	{
						b8zs(1),
						ami(2)
					}
	ACCESS read-write
	STATUS mandatory
	DESCRIPTION ""
	::= { portT1AdminEntry 5 }

portT1AdminLineBuildOut OBJECT-TYPE
	SYNTAX INTEGER	{
						zerodb(1),
						x133-266ft(2),
						x266-399ft(3),
						x399-533ft(4),
						x533-655ft(5),
						minus7p5db(6),
						minus15db(7),
						minus22p5db(8)
					}
	ACCESS read-write
	STATUS mandatory
	DESCRIPTION ""
	::= { portT1AdminEntry 6 }

portT1AdminRowStatus OBJECT-TYPE
	SYNTAX RowStatus	
	ACCESS read-write
	STATUS mandatory
	DESCRIPTION ""
	::= { portT1AdminEntry 7 }

portT1AdminProtocolFraming OBJECT-TYPE
	SYNTAX INTEGER	{
			sync(1),
			bisync(2)
			}
	ACCESS read-write
	STATUS mandatory
	DESCRIPTION ""
	::= { portT1AdminEntry 8 }

portT1AdminNRZI OBJECT-TYPE
	SYNTAX INTEGER	{
						no(1),
						yes(2)
					}
	ACCESS read-write
	STATUS mandatory
	DESCRIPTION ""
	::= { portT1AdminEntry 9 }

portT1OperTable OBJECT-TYPE
	SYNTAX SEQUENCE OF PortT1OperEntry
	ACCESS not-accessible
	STATUS mandatory
	DESCRIPTION "The configuration information pertaining to a T1 port.
	T1 ports can operate at full T1 bandwidth or DS0A channelized which provides
	24 separate channels."
	::= { portT1Group 2 }

portT1OperEntry OBJECT-TYPE
	SYNTAX PortT1OperEntry
	ACCESS not-accessible
	STATUS mandatory
	DESCRIPTION "A T1 port entry containing objects relating to T1 ports."
	INDEX { nlIfRlp, nlIfPort }
	::= { portT1OperTable 1 }

PortT1OperEntry ::=
	SEQUENCE {
		portT1OperBlockedPortFlag	INTEGER,
		portT1OperGenerateClock		INTEGER,
		portT1OperFramingMode		INTEGER,
		portT1OperFrameModelSelect	INTEGER,
		portT1OperLineEncoding 		INTEGER,
		portT1OperLineBuildOut 		INTEGER,
		portT1OperProtocolFraming	INTEGER,
		portT1OperNRZI				INTEGER
}

portT1OperBlockedPortFlag OBJECT-TYPE
	SYNTAX INTEGER	{
						no(1),
						yes(2)
					}
	ACCESS read-only
	STATUS mandatory
	DESCRIPTION ""
	::= { portT1OperEntry 1 }

portT1OperGenerateClock OBJECT-TYPE
	SYNTAX INTEGER	{
						no(1),
						yes(2)
					}
	ACCESS read-only
	STATUS mandatory
	DESCRIPTION ""
	::= { portT1OperEntry 2 }

portT1OperFramingMode OBJECT-TYPE
	SYNTAX INTEGER	{
						fullT1(1),
						ds0aT1(2)
					}
	ACCESS read-only
	STATUS mandatory
	DESCRIPTION "Specifies how this T1 port is to function. ds0AT1 specifies a
	24 channelized T1."
	::= { portT1OperEntry 3 }

portT1OperFrameModelSelect OBJECT-TYPE
	SYNTAX INTEGER	{
						d4(1),
						esf(2)
					}
	ACCESS read-only
	STATUS mandatory
	DESCRIPTION ""
	::= { portT1OperEntry 4 }

portT1OperLineEncoding OBJECT-TYPE
	SYNTAX INTEGER	{
						b8zs(1),
						ami(2)
					}
	ACCESS read-only
	STATUS mandatory
	DESCRIPTION ""
	::= { portT1OperEntry 5 }

portT1OperLineBuildOut OBJECT-TYPE
	SYNTAX INTEGER	{
						zerodb(1),
						x133-266ft(2),
						x266-399ft(3),
						x399-533ft(4),
						x533-655ft(5),
						minus7p5db(6),
						minus15db(7),
						minus22p5db(8)
					}
	ACCESS read-only
	STATUS mandatory
	DESCRIPTION ""
	::= { portT1OperEntry 6 }

portT1OperProtocolFraming OBJECT-TYPE
	SYNTAX INTEGER	{
			sync(1),
			bisync(2)
			}
	ACCESS read-only
	STATUS mandatory
	DESCRIPTION ""
	::= { portT1OperEntry 7 }

portT1OperNRZI OBJECT-TYPE
	SYNTAX INTEGER	{
						no(1),
						yes(2)
					}
	ACCESS read-only
	STATUS mandatory
	DESCRIPTION ""
	::= { portT1OperEntry 8 }

portVoiceGroup OBJECT IDENTIFIER ::= { port 8 }

--
-- The Voice Port Administrative table
--

portVoiceAdminTable OBJECT-TYPE
    SYNTAX  SEQUENCE OF PortVoiceAdminEntry
    ACCESS  not-accessible
    STATUS  mandatory
    DESCRIPTION
            "A list of Voice ports.  The number of entries
            will be the number of Voice ports on the node."
    ::= { portVoiceGroup 1 }

portVoiceAdminEntry OBJECT-TYPE
    SYNTAX  PortVoiceAdminEntry
    ACCESS  not-accessible
    STATUS  mandatory
    DESCRIPTION
            "A Voice Port entry containing objects relating
            to the port that are configurable by the user."
    INDEX   { portVoiceAdminRlpIndex, portVoiceAdminPortIndex }
    ::= { portVoiceAdminTable 1 }

PortVoiceAdminEntry ::=
    SEQUENCE {
        portVoiceAdminRlpIndex
            INTEGER,
        portVoiceAdminPortIndex
            INTEGER,
        portVoiceAdminBlockedFlag
            INTEGER,
        portVoiceAdminSpeed
            INTEGER,
        portVoiceAdminDTMF
            INTEGER,
        portVoiceAdminInterface
            INTEGER,
        portVoiceAdminTETimer
            INTEGER,
        portVoiceAdminLevelIn
            INTEGER,
        portVoiceAdminLevelOut
            INTEGER,
        portVoiceAdminCallTimer
            INTEGER,
        portVoiceAdminHuntGroup
            INTEGER,
        portVoiceAdminLongDialPrefix
            OCTET STRING,
        portVoiceAdminSLTTimeout
            INTEGER,
        portVoiceAdminLinkDownBusy
            INTEGER,
        portVoiceAdminFaxSupported
            INTEGER,
        portVoiceAdminTelephonyType
            INTEGER,
        portVoiceAdminJitter
            INTEGER,
        portVoiceAdminSampleDelay
            INTEGER,
        portVoiceAdminDialTimer
            INTEGER,
        portVoiceAdminAutoDial
            INTEGER,
        portVoiceAdminSuppression
            INTEGER,
        portVoiceAdminAutoDialNumber
            OCTET STRING,
        portVoiceAdminAutoPoll
            INTEGER,
        portVoiceAdminAutoPollTimer
            INTEGER,
        portVoiceAdminExtDigitsSource
            INTEGER,
        portVoiceAdminNumDigitsDelete
            INTEGER,
        portVoiceAdminForwardDelay
            INTEGER,
        portVoiceAdminForwardedType
            INTEGER,
        portVoiceAdminForwardedDigits
            INTEGER,
        portVoiceAdminMakeRatio
            INTEGER,
        portVoiceAdminBreakRatio
            INTEGER,
        portVoiceAdminDTMFOnDuration
            INTEGER,
        portVoiceAdminDTMFOffDuration
            INTEGER,
        portVoiceAdminToneType
            INTEGER,
        portVoiceAdminRowStatus
            RowStatus
    }

portVoiceAdminRlpIndex OBJECT-TYPE
    SYNTAX  INTEGER
    ACCESS  read-only
    STATUS  mandatory
    DESCRIPTION
            "The RLP number of the Voice port."
    ::= { portVoiceAdminEntry 1 }

portVoiceAdminPortIndex OBJECT-TYPE
    SYNTAX  INTEGER
    ACCESS  read-only
    STATUS  mandatory
    DESCRIPTION
            "The Port number of the Voice port."
    ::= { portVoiceAdminEntry 2 }

portVoiceAdminBlockedFlag OBJECT-TYPE
    SYNTAX  INTEGER {
                disabled (1),
                enabled (2)
                }
    ACCESS  read-write
    STATUS  mandatory
    DESCRIPTION
            "The flag which causes the port to be enabled or disabled
            at node IPL. The port will remain in that state until this
            flag is changed and the node is rebooted, or until an on-
            line enable or disable is performed."
    DEFVAL { disabled }
    ::= { portVoiceAdminEntry 3 }

portVoiceAdminSpeed OBJECT-TYPE
    SYNTAX  INTEGER {
                bps-4800 (1),
                bps-8000 (2),
                bps-32000 (3),
                bps-64000 (4)
                }
    ACCESS  read-write
    STATUS  mandatory
    DESCRIPTION
            "The speed of the port which is transmitted as part
            of a Call Setup frame. A Voice call will be established
            if there is enough bandwidth at each end to provide the
            minimum configured rate."
    DEFVAL { bps-8000 }
    ::= { portVoiceAdminEntry 4 }

portVoiceAdminDTMF OBJECT-TYPE
    SYNTAX  INTEGER (0..255)
    ACCESS  read-write
    STATUS  mandatory
    DESCRIPTION
            "The flag to enable, disable, or specify a time span
            over which DTMF (Dual Tone Multi Frequency) tones will
            be regenerated.
            0 =     pass tones transparently to the remote device.
            1 =     detect incoming tones and regenerate as received.
            2-255 = regenerate tones for the specified seconds."
    DEFVAL { 1 }
    ::= { portVoiceAdminEntry 5 }

portVoiceAdminInterface OBJECT-TYPE
    SYNTAX  INTEGER {
                em-4w (1),
                em-2w (2),
                loop-start (3),
                ac15-a (4),
                ac15-b (6),
                em-4w-te (10),
                em-2w-te (11)
                }
    ACCESS  read-write
    STATUS  mandatory
    DESCRIPTION
            "The type of interface (in conjunction with the Telephony
            Interface Type) that will be used by the Voice channel.
            This requires rebooting for the change to take effect.
            Telephony Type     Interface Type
            --------------     --------------
            OPX (FXO)          Loop Start
            SLT (FXS)          Loop Start
            E&M                4W E&M, 4W E&M TE, 2W E&M, 2W E&M TE
            AC15               AC15A, AC15C"
    DEFVAL { loop-start }
    ::= { portVoiceAdminEntry 6 }

portVoiceAdminTETimer OBJECT-TYPE
    SYNTAX  INTEGER (0..255)
    ACCESS  read-write
    STATUS  mandatory
    DESCRIPTION
            "The delay at which the E&M 'E' lead follows the 'M' lead."
    DEFVAL { 3 }
    ::= { portVoiceAdminEntry 7 }

portVoiceAdminLevelIn OBJECT-TYPE
    SYNTAX  INTEGER (-22..7)
    ACCESS  read-write
    STATUS  mandatory
    DESCRIPTION
            "The local voice level into the voice port. This adjusts
            the sensitivity of the local voice channel to the signal
            from the attached device. The purpose of this is to match
            the voice channel dB level to the input signal. A more
            negative setting produces a higher input gain. If the level
            is reduced, the voice channel will be more sensitive to the
            input. This will also cause the voice output at the remote
            device to sound louder."
    DEFVAL { 0 }
    ::= { portVoiceAdminEntry 8 }

portVoiceAdminLevelOut OBJECT-TYPE
    SYNTAX  INTEGER (-22..7)
    ACCESS  read-write
    STATUS  mandatory
    DESCRIPTION
            "The local voice level out of the voice port. A more
            positive setting produces a higher volume."
    DEFVAL { -4 }
    ::= { portVoiceAdminEntry 9 }

portVoiceAdminCallTimer OBJECT-TYPE
    SYNTAX  INTEGER (1..30)
    ACCESS  read-write
    STATUS  mandatory
    DESCRIPTION
            "The amount of time the node will wait for a response to a
            Call Connect or Call Clear request. When the node issues a
            request, it will set a timer to the value configured here.
            If that timer expires with no response from the destination,
            the node will generate a busy tone."
    DEFVAL { 5 }
    ::= { portVoiceAdminEntry 10 }

portVoiceAdminHuntGroup OBJECT-TYPE
    SYNTAX  INTEGER {
                none (1),
                a (2),
                b (3)
                }
    ACCESS  read-write
    STATUS  mandatory
    DESCRIPTION
            "The hunt group that includes the voice channel."
    DEFVAL { none }
    ::= { portVoiceAdminEntry 11 }

portVoiceAdminLongDialPrefix OBJECT-TYPE
    SYNTAX  OCTET STRING (SIZE (1))
    ACCESS  read-write
    STATUS  mandatory
    DESCRIPTION
            "The character that will be required preceeding calls using
            the long call format. When the user at an attached device
            dials a long form number, it must be preceeded by the prefix
            character specified here."
    DEFVAL { '2A'H }
    ::= { portVoiceAdminEntry 12 }

portVoiceAdminSLTTimeout OBJECT-TYPE
    SYNTAX  INTEGER (1..99)
    ACCESS  read-write
    STATUS  mandatory
    DESCRIPTION
            "The time the local port will wait before an actual fax
            transmission begins. If there is no fax tone when this
            timer expires, the connection will be terminated."
    DEFVAL { 30 }
    ::= { portVoiceAdminEntry 13 }

portVoiceAdminLinkDownBusy OBJECT-TYPE
    SYNTAX  INTEGER {
                disabled (1),
                enabled (2)
                }
    ACCESS  read-write
    STATUS  mandatory
    DESCRIPTION
            "This flag enables or disables automatic busy-out of
            channels when the link is down. When enabled, the system
            will automatically busy-out channels when the composite
            link is down. When disabled, channels remain on-hook when
            the link is down. If your application is connected to a
            PBX that can route calls to another alternate source based
            on an all busy condition, enable this so the PBX will
            recognize this condition and reroute the calls while the
            composite link is down."
    DEFVAL { enabled }
    ::= { portVoiceAdminEntry 14 }

portVoiceAdminFaxSupported OBJECT-TYPE
    SYNTAX  INTEGER {
                no (1),
                yes (2)
                }
    ACCESS  read-write
    STATUS  mandatory
    DESCRIPTION
            "The flag to indicate whether or not faxes will be
            transmitted on the port. If no, all calls will be treated
            as voice. If yes, both voice and fax will be transmitted."
    DEFVAL { yes }
    ::= { portVoiceAdminEntry 15 }

portVoiceAdminTelephonyType OBJECT-TYPE
    SYNTAX  INTEGER {
                opx (1),
                slt (2),
                em (3),
                ac15 (4)
                }
    ACCESS  read-write
    STATUS  mandatory
    DESCRIPTION
            "The type of interface (in conjunction with the
            Interface Type) that will be used by the Voice channel.
            This requires rebooting for the change to take effect.
            Telephony Type     Interface Type
            --------------     --------------
            OPX (FXO)          Loop Start
            SLT (FXS)          Loop Start
            E&M                4W E&M, 4W E&M TE, 2W E&M, 2W E&M TE
            AC15               AC15A, AC15C"
    DEFVAL { opx }
    ::= { portVoiceAdminEntry 16 }

portVoiceAdminJitter OBJECT-TYPE
    SYNTAX  INTEGER (10..255)
    ACCESS  read-write
    STATUS  mandatory
    DESCRIPTION
            "The amount of jitter delay."
    DEFVAL { 80 }
    ::= { portVoiceAdminEntry 17 }

portVoiceAdminSampleDelay OBJECT-TYPE
    SYNTAX  INTEGER (0..255)
    ACCESS  read-write
    STATUS  mandatory
    DESCRIPTION
            "The amount of sample delay."
    DEFVAL { 10 }
    ::= { portVoiceAdminEntry 18 }

portVoiceAdminDialTimer OBJECT-TYPE
    SYNTAX  INTEGER (0..10)
    ACCESS  read-write
    STATUS  mandatory
    DESCRIPTION
            "The delay the node will use to determine when variable
            length dialing is complete. (Variable length dialing allows
            the user to place a call without entering the configured
            number of digits for the speed dial number.)"
    DEFVAL { 5 }
    ::= { portVoiceAdminEntry 19 }

portVoiceAdminAutoDial OBJECT-TYPE
    SYNTAX  INTEGER {
                disabled (1),
                enabled (2)
                }
    ACCESS  read-write
    STATUS  mandatory
    DESCRIPTION
            "The flag to enable or disable the auto dial feature. Note
           that enabling this feature will disable the variable length
            dialing feature for this channel."
    DEFVAL { disabled }
    ::= { portVoiceAdminEntry 20 }

portVoiceAdminSuppression OBJECT-TYPE
    SYNTAX  INTEGER {
                very-low (1),
                low (2),
                medium (3),
                high (4),
                very-high (5)
                }
    ACCESS  read-write
    STATUS  mandatory
    DESCRIPTION
            "The silence suppression level. A larger silence suppression
            level allows more data channels to operate simultaneously
            with the voice channels."
    DEFVAL { low }
    ::= { portVoiceAdminEntry 21 }

portVoiceAdminAutoDialNumber OBJECT-TYPE
    SYNTAX  OCTET STRING (SIZE (0..4))
    ACCESS  read-write
    STATUS  mandatory
    DESCRIPTION
            "The number to which the node will attempt to connect when
            the handset attached to this port is taken off-hook. This
            is applicable only when the Auto Dial feature is enabled."
    ::= { portVoiceAdminEntry 22 }

portVoiceAdminAutoPoll OBJECT-TYPE
    SYNTAX  INTEGER {
                disabled (1),
                enabled (2)
                }
    ACCESS  read-write
    STATUS  mandatory
    DESCRIPTION
            "The flag to enable or disable auto polling. This is
            applicable only when the Auto Dial feature is enabled.
            When enabled, the node periodically polls the destination.
            If the poll is not acknowledged, the node will busy-out
            the channel. This can be useful in situations where the
            destination is an emergency number that must always be
            available. If the destination does not answer the automatic
            poll, the busy-out condition will notify an attached PBX
            that the emergency call should be routed to another call
            routing device."
    DEFVAL { disabled }
    ::= { portVoiceAdminEntry 23 }

portVoiceAdminAutoPollTimer OBJECT-TYPE
    SYNTAX  INTEGER (5..30)
    ACCESS  read-write
    STATUS  mandatory
    DESCRIPTION
            "The frequency with which an Auto Poll will be sent. This
            is applicable only when auto poll is enabled."
    DEFVAL { 10 }
    ::= { portVoiceAdminEntry 24 }

portVoiceAdminExtDigitsSource OBJECT-TYPE
    SYNTAX  INTEGER {
                map (1),
                user (2)
                }
    ACCESS  read-write
    STATUS  mandatory
    DESCRIPTION
            "The source of the extended digits when the user of
            attached equipment dials a speed dial number. This is
            applicable only when the number of extended dial digits
            is greater than zero.  When map is specified, extended
            digits are taken from the extended digits field in the
            map table.  When user is specified, extended digits are
            taken from the user of attached equipment."
    DEFVAL { map }
    ::= { portVoiceAdminEntry 25 }

portVoiceAdminNumDigitsDelete OBJECT-TYPE
    SYNTAX  INTEGER (0..4)
    ACCESS  read-write
    STATUS  mandatory
    DESCRIPTION
            "The number of leading dial digits that will be deleted
            before a dial string is forwarded. This is primarily used
            to delete leading dial digits that may be inserted by an
            attached PBX."
    DEFVAL { 0 }
    ::= { portVoiceAdminEntry 26 }

portVoiceAdminForwardDelay OBJECT-TYPE
    SYNTAX  INTEGER (0..40)
    ACCESS  read-write
    STATUS  mandatory
    DESCRIPTION
            "The length of a pause that can be inserted in an extended
            dial string that is being forwarded. This is applicable only
            when forwarded output digits is all or extended. When a comma
            is encountered in an extended digits string, the node will
            pause for the length of time specified here before additional
            extended digits are forwarded."
    DEFVAL { 2 }
    ::= { portVoiceAdminEntry 27 }

portVoiceAdminForwardedType OBJECT-TYPE
    SYNTAX  INTEGER {
                dtmf (1),
                pulse (2)
                }
    ACCESS  read-write
    STATUS  mandatory
    DESCRIPTION
            "The method how the dial digits will be forwarded. This
            is applicable only when forwarded output digits is all
            or extended."
    DEFVAL { dtmf }
    ::= { portVoiceAdminEntry 28 }

portVoiceAdminForwardedDigits OBJECT-TYPE
    SYNTAX  INTEGER {
                none (1),
                all (2),
                extended (3)
                }
    ACCESS  read-write
    STATUS  mandatory
    DESCRIPTION
            "The flag indicating which dial digits, if any, to forward.
            If none, dial digits are not forwarded to the destination
            device when a call is initiated on this channel. If all,
            the dialed speed dial number and associated extended digits
            are forwarded to the destination device. If extended, only
            the extended digit string is forwarded."
    DEFVAL { none }
    ::= { portVoiceAdminEntry 29 }

portVoiceAdminMakeRatio OBJECT-TYPE
    SYNTAX  INTEGER (20..80)
    ACCESS  read-write
    STATUS  mandatory
    DESCRIPTION
            "The make ratio of each digit pulse that is forwarded.
            This is applicable only when forwarded output digits
            is all or extended and forwarded digit type is pulse."
    DEFVAL { 34 }
    ::= { portVoiceAdminEntry 30 }

portVoiceAdminBreakRatio OBJECT-TYPE
    SYNTAX  INTEGER (20..80)
    ACCESS  read-write
    STATUS  mandatory
    DESCRIPTION
            "The break ratio of each digit pulse that is forwarded.
            This is applicable only when forwarded output digits
            is all or extended and forwarded digit type is pulse."
    DEFVAL { 66 }
    ::= { portVoiceAdminEntry 31 }

portVoiceAdminDTMFOnDuration OBJECT-TYPE
    SYNTAX  INTEGER (30..1000)
    ACCESS  read-write
    STATUS  mandatory
    DESCRIPTION
            "The length of a tone that will be used to produce a
            single DTMF digit. This is applicable only when forwarded
            output digits is all or extended and forwarded digit type
            is DTMF."
    DEFVAL { 100 }
    ::= { portVoiceAdminEntry 32 }

portVoiceAdminDTMFOffDuration OBJECT-TYPE
    SYNTAX  INTEGER (30..1000)
    ACCESS  read-write
    STATUS  mandatory
    DESCRIPTION
            "The length of silence between DTMF tones in a dial digit
            string. This is applicable only when forwarded output digits
            is all or extended and forwarded digit type is DTMF."
    DEFVAL { 100 }
    ::= { portVoiceAdminEntry 33 }

portVoiceAdminToneType OBJECT-TYPE
    SYNTAX  INTEGER {
                dtmf (1),
                mf (2)
                }
    ACCESS  read-write
    STATUS  mandatory
    DESCRIPTION
            "The tone type to detect/regenerate for forwarding DTMF/MF."
    DEFVAL { dtmf }
    ::= { portVoiceAdminEntry 34 }

portVoiceAdminRowStatus OBJECT-TYPE
    SYNTAX  RowStatus
    ACCESS  read-write
    STATUS  mandatory
    DESCRIPTION
            "This variable is used to manage the creation and deletion
            of conceptual rows in the portVoiceAdminTable and follows the
            SNMPv2 RowStatus conventions by supporting the following values:

                 - `active', which indicates that the conceptual row is
                available for use by the managed device, and which is
                supplied by a management station wishing to exercise an
                on-line update of the existing conceptual row.  For a
                management protocol set operation, a genErr response is
                returned when the row does not exist.

                 - `createAndGo', which is supplied by a management
                 station wishing to create a new instance of a
                 conceptual row and to have its status automatically set
                 to active, making it available for use by the managed
                 device.  For a management protocol set operation, a
                 genErr response is returned when the row already exists.

                 - `destroy', which is supplied by a management station
                 wishing to delete all of the instances associated with
                 an existing conceptual row.

            Note that all of the above values may be specified in a
            management protocol set operation, and only the 'active'
            value will be returned in response to a management protocol
            retrieval operation.  For a management protocol set operation,
            if other variable bindings are included in the same PDU, then
            a genErr response is returned."
    ::= { portVoiceAdminEntry 35 }

--
-- The Voice Port Operational table
--

portVoiceOperTable OBJECT-TYPE
    SYNTAX  SEQUENCE OF PortVoiceOperEntry
    ACCESS  not-accessible
    STATUS  mandatory
    DESCRIPTION
            "A list of Voice ports.  The number of entries
            will be the number of Voice ports on the node."
    ::= { portVoiceGroup 2 }

portVoiceOperEntry OBJECT-TYPE
    SYNTAX  PortVoiceOperEntry
    ACCESS  not-accessible
    STATUS  mandatory
    DESCRIPTION
            "A Voice Port entry containing objects relating
            to the port that are configurable by the user."
    INDEX   { portVoiceOperRlpIndex, portVoiceOperPortIndex }
    ::= { portVoiceOperTable 1 }

PortVoiceOperEntry ::=
    SEQUENCE {
        portVoiceOperRlpIndex
            INTEGER,
        portVoiceOperPortIndex
            INTEGER,
        portVoiceOperBlockedFlag
            INTEGER,
        portVoiceOperSpeed
            INTEGER,
        portVoiceOperDTMF
            INTEGER,
        portVoiceOperInterface
            INTEGER,
        portVoiceOperTETimer
            INTEGER,
        portVoiceOperLevelIn
            INTEGER,
        portVoiceOperLevelOut
            INTEGER,
        portVoiceOperCallTimer
            INTEGER,
        portVoiceOperHuntGroup
            INTEGER,
        portVoiceOperLongDialPrefix
            OCTET STRING,
        portVoiceOperSLTTimeout
            INTEGER,
        portVoiceOperLinkDownBusy
            INTEGER,
        portVoiceOperFaxSupported
            INTEGER,
        portVoiceOperTelephonyType
            INTEGER,
        portVoiceOperJitter
            INTEGER,
        portVoiceOperSampleDelay
            INTEGER,
        portVoiceOperDialTimer
            INTEGER,
        portVoiceOperAutoDial
            INTEGER,
        portVoiceOperSuppression
            INTEGER,
        portVoiceOperAutoDialNumber
            OCTET STRING,
        portVoiceOperAutoPoll
            INTEGER,
        portVoiceOperAutoPollTimer
            INTEGER,
        portVoiceOperExtDigitsSource
            INTEGER,
        portVoiceOperNumDigitsDelete
            INTEGER,
        portVoiceOperForwardDelay
            INTEGER,
        portVoiceOperForwardedType
            INTEGER,
        portVoiceOperForwardedDigits
            INTEGER,
        portVoiceOperMakeRatio
            INTEGER,
        portVoiceOperBreakRatio
            INTEGER,
        portVoiceOperDTMFOnDuration
            INTEGER,
        portVoiceOperDTMFOffDuration
            INTEGER,
        portVoiceOperToneType
            INTEGER
    }

portVoiceOperRlpIndex OBJECT-TYPE
    SYNTAX  INTEGER
    ACCESS  read-only
    STATUS  mandatory
    DESCRIPTION
            "The RLP number of the Voice port."
    ::= { portVoiceOperEntry 1 }

portVoiceOperPortIndex OBJECT-TYPE
    SYNTAX  INTEGER
    ACCESS  read-only
    STATUS  mandatory
    DESCRIPTION
            "The Port number of the Voice port."
    ::= { portVoiceOperEntry 2 }

portVoiceOperBlockedFlag OBJECT-TYPE
    SYNTAX  INTEGER {
                disabled (1),
                enabled (2)
                }
    ACCESS  read-only
    STATUS  mandatory
    DESCRIPTION
            "The flag which causes the port to be enabled or disabled
            at node IPL. The port will remain in that state until this
            flag is changed and the node is rebooted, or until an on-
            line enable or disable is performed."
    ::= { portVoiceOperEntry 3 }

portVoiceOperSpeed OBJECT-TYPE
    SYNTAX  INTEGER {
                bps-4800 (1),
                bps-8000 (2),
                bps-32000 (3),
                bps-64000 (4)
                }
    ACCESS  read-only
    STATUS  mandatory
    DESCRIPTION
            "The speed of the port which is transmitted as part
            of a Call Setup frame. A Voice call will be established
            if there is enough bandwidth at each end to provide the
            minimum configured rate."
    ::= { portVoiceOperEntry 4 }

portVoiceOperDTMF OBJECT-TYPE
    SYNTAX  INTEGER (0..255)
    ACCESS  read-only
    STATUS  mandatory
    DESCRIPTION
            "The flag to enable, disable, or specify a time span
            over which DTMF (Dual Tone Multi Frequency) tones will
            be regenerated.
            0 =     pass tones transparently to the remote device.
            1 =     detect incoming tones and regenerate as received.
            2-255 = regenerate tones for the specified seconds."
    ::= { portVoiceOperEntry 5 }

portVoiceOperInterface OBJECT-TYPE
    SYNTAX  INTEGER {
                em-4w (1),
                em-2w (2),
                loop-start (3),
                ac15-a (4),
                ac15-b (6),
                em-4w-te (10),
                em-2w-te (11)
                }
    ACCESS  read-only
    STATUS  mandatory
    DESCRIPTION
            "The type of interface (in conjunction with the Telephony
            Interface Type) that will be used by the Voice channel.
            This requires rebooting for the change to take effect.
            Telephony Type     Interface Type
            --------------     --------------
            OPX (FXO)          Loop Start
            SLT (FXS)          Loop Start
            E&M                4W E&M, 4W E&M TE, 2W E&M, 2W E&M TE
            AC15               AC15A, AC15C"
    ::= { portVoiceOperEntry 6 }

portVoiceOperTETimer OBJECT-TYPE
    SYNTAX  INTEGER (0..255)
    ACCESS  read-only
    STATUS  mandatory
    DESCRIPTION
            "The delay at which the E&M 'E' lead follows the 'M' lead."
    ::= { portVoiceOperEntry 7 }

portVoiceOperLevelIn OBJECT-TYPE
    SYNTAX  INTEGER (-22..7)
    ACCESS  read-only
    STATUS  mandatory
    DESCRIPTION
            "The local voice level into the voice port. This adjusts
            the sensitivity of the local voice channel to the signal
            from the attached device. The purpose of this is to match
            the voice channel dB level to the input signal. A more
            negative setting produces a higher input gain. If the level
            is reduced, the voice channel will be more sensitive to the
            input. This will also cause the voice output at the remote
            device to sound louder."
    ::= { portVoiceOperEntry 8 }

portVoiceOperLevelOut OBJECT-TYPE
    SYNTAX  INTEGER (-22..7)
    ACCESS  read-only
    STATUS  mandatory
    DESCRIPTION
            "The local voice level out of the voice port. A more
            positive setting produces a higher volume."
    ::= { portVoiceOperEntry 9 }

portVoiceOperCallTimer OBJECT-TYPE
    SYNTAX  INTEGER (1..30)
    ACCESS  read-only
    STATUS  mandatory
    DESCRIPTION
            "The amount of time the node will wait for a response to a
            Call Connect or Call Clear request. When the node issues a
            request, it will set a timer to the value configured here.
            If that timer expires with no response from the destination,
            the node will generate a busy tone."
    ::= { portVoiceOperEntry 10 }

portVoiceOperHuntGroup OBJECT-TYPE
    SYNTAX  INTEGER {
                none (1),
                a (2),
                b (3)
                }
    ACCESS  read-only
    STATUS  mandatory
    DESCRIPTION
            "The hunt group that includes the voice channel."
    ::= { portVoiceOperEntry 11 }

portVoiceOperLongDialPrefix OBJECT-TYPE
    SYNTAX  OCTET STRING (SIZE (1))
    ACCESS  read-only
    STATUS  mandatory
    DESCRIPTION
            "The character that will be required preceeding calls using
            the long call format. When the user at an attached device
            dials a long form number, it must be preceeded by the prefix
            character specified here."
    ::= { portVoiceOperEntry 12 }

portVoiceOperSLTTimeout OBJECT-TYPE
    SYNTAX  INTEGER (1..99)
    ACCESS  read-only
    STATUS  mandatory
    DESCRIPTION
            "The time the local port will wait before an actual fax
            transmission begins. If there is no fax tone when this
            timer expires, the connection will be terminated."
    ::= { portVoiceOperEntry 13 }

portVoiceOperLinkDownBusy OBJECT-TYPE
    SYNTAX  INTEGER {
                disabled (1),
                enabled (2)
                }
    ACCESS  read-only
    STATUS  mandatory
    DESCRIPTION
            "This flag enables or disables automatic busy-out of
            channels when the link is down. When enabled, the system
            will automatically busy-out channels when the composite
            link is down. When disabled, channels remain on-hook when
            the link is down. If your application is connected to a
            PBX that can route calls to another alternate source based
            on an all busy condition, enable this so the PBX will
            recognize this condition and reroute the calls while the
            composite link is down."
    ::= { portVoiceOperEntry 14 }

portVoiceOperFaxSupported OBJECT-TYPE
    SYNTAX  INTEGER {
                no (1),
                yes (2)
                }
    ACCESS  read-only
    STATUS  mandatory
    DESCRIPTION
            "The flag to indicate whether or not faxes will be
            transmitted on the port. If no, all calls will be treated
            as voice. If yes, both voice and fax will be transmitted."
    ::= { portVoiceOperEntry 15 }

portVoiceOperTelephonyType OBJECT-TYPE
    SYNTAX  INTEGER {
                opx (1),
                slt (2),
                em (3),
                ac15 (4)
                }
    ACCESS  read-only
    STATUS  mandatory
    DESCRIPTION
            "The type of interface (in conjunction with the
            Interface Type) that will be used by the Voice channel.
            This requires rebooting for the change to take effect.
            Telephony Type     Interface Type
            --------------     --------------
            OPX (FXO)          Loop Start
            SLT (FXS)          Loop Start
            E&M                4W E&M, 4W E&M TE, 2W E&M, 2W E&M TE
            AC15               AC15A, AC15C"
    ::= { portVoiceOperEntry 16 }

portVoiceOperJitter OBJECT-TYPE
    SYNTAX  INTEGER (10..255)
    ACCESS  read-only
    STATUS  mandatory
    DESCRIPTION
            "The amount of jitter delay."
    ::= { portVoiceOperEntry 17 }

portVoiceOperSampleDelay OBJECT-TYPE
    SYNTAX  INTEGER (0..255)
    ACCESS  read-only
    STATUS  mandatory
    DESCRIPTION
            "The amount of sample delay."
    ::= { portVoiceOperEntry 18 }

portVoiceOperDialTimer OBJECT-TYPE
    SYNTAX  INTEGER (0..10)
    ACCESS  read-only
    STATUS  mandatory
    DESCRIPTION
            "The delay the node will use to determine when variable
            length dialing is complete. (Variable length dialing allows
            the user to place a call without entering the configured
            number of digits for the speed dial number.)"
    ::= { portVoiceOperEntry 19 }

portVoiceOperAutoDial OBJECT-TYPE
    SYNTAX  INTEGER {
                disabled (1),
                enabled (2)
                }
    ACCESS  read-only
    STATUS  mandatory
    DESCRIPTION
            "The flag to enable or disable the auto dial feature. Note
            that enabling this feature will disable the variable length
            dialing feature for this channel."
    ::= { portVoiceOperEntry 20 }

portVoiceOperSuppression OBJECT-TYPE
    SYNTAX  INTEGER {
                very-low (1),
                low (2),
                medium (3),
                high (4),
                very-high (5)
                }
    ACCESS  read-only
    STATUS  mandatory
    DESCRIPTION
            "The silence suppression level. A larger silence suppression
            level allows more data channels to operate simultaneously
            with the voice channels."
    ::= { portVoiceOperEntry 21 }

portVoiceOperAutoDialNumber OBJECT-TYPE
    SYNTAX  OCTET STRING (SIZE (0..4))
    ACCESS  read-only
    STATUS  mandatory
    DESCRIPTION
            "The number to which the node will attempt to connect when
            the handset attached to this port is taken off-hook. This
            is applicable only when the Auto Dial feature is enabled."
    ::= { portVoiceOperEntry 22 }

portVoiceOperAutoPoll OBJECT-TYPE
    SYNTAX  INTEGER {
                disabled (1),
                enabled (2)
                }
    ACCESS  read-only
    STATUS  mandatory
    DESCRIPTION
            "The flag to enable or disable auto polling. This is
            applicable only when the Auto Dial feature is enabled.
            When enabled, the node periodically polls the destination.
            If the poll is not acknowledged, the node will busy-out
            the channel. This can be useful in situations where the
            destination is an emergency number that must always be
            available. If the destination does not answer the automatic
            poll, the busy-out condition will notify an attached PBX
            that the emergency call should be routed to another call
            routing device."
    ::= { portVoiceOperEntry 23 }

portVoiceOperAutoPollTimer OBJECT-TYPE
    SYNTAX  INTEGER (5..30)
    ACCESS  read-only
    STATUS  mandatory
    DESCRIPTION
            "The frequency with which an Auto Poll will be sent. This
            is applicable only when auto poll is enabled."
    ::= { portVoiceOperEntry 24 }

portVoiceOperExtDigitsSource OBJECT-TYPE
    SYNTAX  INTEGER {
                map (1),
                user (2)
                }
    ACCESS  read-only
    STATUS  mandatory
    DESCRIPTION
            "The source of the extended digits when the user of
            attached equipment dials a speed dial number. This is
            applicable only when the number of extended dial digits
            is greater than zero.  When map is specified, extended
            digits are taken from the extended digits field in the
            map table.  When user is specified, extended digits are
            taken from the user of attached equipment."
    ::= { portVoiceOperEntry 25 }

portVoiceOperNumDigitsDelete OBJECT-TYPE
    SYNTAX  INTEGER (0..4)
    ACCESS  read-only
    STATUS  mandatory
    DESCRIPTION
            "The number of leading dial digits that will be deleted
            before a dial string is forwarded. This is primarily used
            to delete leading dial digits that may be inserted by an
            attached PBX."
    ::= { portVoiceOperEntry 26 }

portVoiceOperForwardDelay OBJECT-TYPE
    SYNTAX  INTEGER (0..40)
    ACCESS  read-only
    STATUS  mandatory
    DESCRIPTION
            "The length of a pause that can be inserted in an extended
            dial string that is being forwarded. This is applicable only
            when forwarded output digits is all or extended. When a comma
            is encountered in an extended digits string, the node will
            pause for the length of time specified here before additional
            extended digits are forwarded."
    ::= { portVoiceOperEntry 27 }

portVoiceOperForwardedType OBJECT-TYPE
    SYNTAX  INTEGER {
                dtmf (1),
                pulse (2)
                }
    ACCESS  read-only
    STATUS  mandatory
    DESCRIPTION
            "The method how the dial digits will be forwarded. This
            is applicable only when forwarded output digits is all
            or extended."
    ::= { portVoiceOperEntry 28 }

portVoiceOperForwardedDigits OBJECT-TYPE
    SYNTAX  INTEGER {
                none (1),
                all (2),
                extended (3)
                }
    ACCESS  read-only
    STATUS  mandatory
    DESCRIPTION
            "The flag indicating which dial digits, if any, to forward.
            If none, dial digits are not forwarded to the destination
            device when a call is initiated on this channel. If all,
            the dialed speed dial number and associated extended digits
            are forwarded to the destination device. If extended, only
            the extended digit string is forwarded."
    ::= { portVoiceOperEntry 29 }

portVoiceOperMakeRatio OBJECT-TYPE
    SYNTAX  INTEGER (20..80)
    ACCESS  read-only
    STATUS  mandatory
    DESCRIPTION
            "The make ratio of each digit pulse that is forwarded.
            This is applicable only when forwarded output digits
            is all or extended and forwarded digit type is pulse."
    ::= { portVoiceOperEntry 30 }

portVoiceOperBreakRatio OBJECT-TYPE
    SYNTAX  INTEGER (20..80)
    ACCESS  read-only
    STATUS  mandatory
    DESCRIPTION
            "The break ratio of each digit pulse that is forwarded.
            This is applicable only when forwarded output digits
            is all or extended and forwarded digit type is pulse."
    ::= { portVoiceOperEntry 31 }

portVoiceOperDTMFOnDuration OBJECT-TYPE
    SYNTAX  INTEGER (30..1000)
    ACCESS  read-only
    STATUS  mandatory
    DESCRIPTION
            "The length of a tone that will be used to produce a
            single DTMF digit. This is applicable only when forwarded
            output digits is all or extended and forwarded digit type
            is DTMF."
    ::= { portVoiceOperEntry 32 }

portVoiceOperDTMFOffDuration OBJECT-TYPE
    SYNTAX  INTEGER (30..1000)
    ACCESS  read-only
    STATUS  mandatory
    DESCRIPTION
            "The length of silence between DTMF tones in a dial digit
            string. This is applicable only when forwarded output digits
            is all or extended and forwarded digit type is DTMF."
    ::= { portVoiceOperEntry 33 }

portVoiceOperToneType OBJECT-TYPE
    SYNTAX  INTEGER {
                dtmf (1),
                mf (2)
                }
    ACCESS  read-only
    STATUS  mandatory
    DESCRIPTION
            "The tone type to detect/regenerate for forwarding DTMF/MF."
    ::= { portVoiceOperEntry 34 }

-- **********************************
-- *  THE NETLINK INTERFACES GROUP  *
-- **********************************

nlInterfaces OBJECT IDENTIFIER ::=  { local 4 }

--  The nlIinterfaces group is a netlink table which contains all interfaces
--  indexed by RLP and port

--
--  The Netlink If Table
--
-- This table is used to correlate an RLP and Port number to a MIB-II
-- Interface Table entry and a Netlink Interface Table entry. The table
-- is indexed by RLP and port number. 
-- The range of RLP numbers can be:
--     1-8 = RLP cards
--     250 = IP Interfaces
--     251 = IPX Interfaces
--     252 = LLC2 Interfaces
-- The range of port numbers can be:
-- For RLP cards (RLP 1-8) :
--     1-8 = Physical Port
--     9-64 = Logical Port
-- For IP Interfaces (RLP 250) :
--     1-257 = the interface number - FRX4000/FRX6000 version 3.4
--     1-129 = the interface number - other FRX4000/FRX6000 and FRX7000
-- For IPX Interfaces (RLP 251) :
--     1-64 = the interface number
-- For LLC2 Interfaces (RLP 252) :
--     1-96  = the interface number - FRX4000/FRX6000
--     1-251 = the interface number - FRX7000

nlIfTable OBJECT-TYPE
	SYNTAX SEQUENCE OF NlIfEntry
	ACCESS not-accessible
	STATUS mandatory
	DESCRIPTION "A Table to describe each interface on a node.
	This table is indexed by RLP and Port number and can be used to 
	identify the corresponding MIB-II ifIndex of a Port as well as
	additional port information maintained by Netlink."
	::= { nlInterfaces 1 }

nlIfEntry OBJECT-TYPE
	SYNTAX NlIfEntry
	ACCESS not-accessible
	STATUS mandatory
	DESCRIPTION "An Interface entry containing objects relating to interfaces."
	INDEX { nlIfRlp, nlIfPort }
	::= { nlIfTable 1 }

NlIfEntry ::=
	SEQUENCE {
		nlIfRlp
			INTEGER,
		nlIfPort
			INTEGER,
		nlIfType
			INTEGER,
		nlIfIndex
			INTEGER,
		nlIfTableIndex
			INTEGER,
		nlIfTableOid
			OBJECT IDENTIFIER,
		nlIfConnectorType
			INTEGER,
		nlIfPortStatus
			INTEGER,
		nlIfPhyPort
			INTEGER
	}

nlIfRlp OBJECT-TYPE
	SYNTAX INTEGER
	ACCESS read-only
	STATUS mandatory
	DESCRIPTION "The RLP number on the node. RLP numbers 1-8 are Physical
	RLP cards, and RLP number 250, 251 and 252 define IP, IPX and LLC2
	interfaces respectively."
	::= { nlIfEntry 1 }

nlIfPort OBJECT-TYPE
	SYNTAX INTEGER
	ACCESS read-only
	STATUS mandatory
	DESCRIPTION "The Port number on the RLP. Port numbers 1-8 are
	known to be physical ports, and 9-64 are logical ports. If the 
	RLP number identifies an IP, IPX or LLC2 interface, then the port 
	number can be 1-257 (IP), 1-64 (IPX), or 1-96 (LLC2)."
	::= { nlIfEntry 2 }

nlIfType OBJECT-TYPE
   SYNTAX  INTEGER {
			   other(1),          -- none of the following
			   regular1822(2),
			   hdh1822(3),
			   ddnX25(4),
			   rfc877x25(5),
			   ethernetCsmacd(6),
			   iso88023Csmacd(7),
			   iso88024TokenBus(8),
			   iso88025TokenRing(9),
			   iso88026Man(10),
			   starLan(11),
			   proteon10Mbit(12),
			   proteon80Mbit(13),
			   hyperchannel(14),
			   fddi(15),
			   lapb(16),
			   sdlc(17),
			   ds1(18),           -- DS1/E1 (RFC 1406)
			   e1(19),            -- obsolete
			   basicISDN(20),
			   primaryISDN(21),
			   propPointToPointSerial(22), -- proprietary serial
			   ppp(23),
			   softwareLoopback(24),
			   eon(25),            -- CLNP over IP (RFC 1070)
			   ethernet3Mbit(26),
			   nsip(27),           -- XNS over IP
			   slip(28),           -- generic SLIP
			   ultra(29),          -- ULTRA technologies
			   ds3(30),            -- T-3
			   sip(31),            -- SMDS
			   frameRelay(32),    -- DTE only
			   rs232(33),
			   para(34),           -- parallel-port
			   arcnet(35),         -- arcnet
			   arcnetPlus(36),     -- arcnet plus
			   atm(37),            -- ATM cells
			   miox25(38),
			   sonet(39),          -- SONET or SDH
			   x25ple(40),
			   iso88022llc(41),
			   localTalk(42),
			   smdsDxi(43),
			   frameRelayService(44),  -- Frame relay DCE
			   v35(45),
			   hssi(46),
			   hippi(47),
			   modem(48),          -- Generic modem
			   aal5(49),           -- AAL5 over ATM
			   sonetPath(50),
			   sonetVT(51),
			   smdsIcip(52),       -- SMDS InterCarrier Interface
			   propVirtual(53),    -- proprietary virtual/internal
			   propMultiplexor(54), -- proprietary multiplexing
			   trunk(200),			-- NETLINK: Trunk port
			   async(201),			-- NETLINK: Async port
			   bsci(202),			-- NETLINK: Bsci port
			   logicalPort(203),     -- NETLINK: Logical port
			   t1(204),    			 -- NETLINK: T1 port
			   ip(205),             -- NETLINK: IP interface
			   ipx(206),             -- NETLINK: IPX interface
			   llc2(207),            -- NETLINK: LLC2 interface
			   voice(208) 
		   }
	ACCESS read-only
	STATUS mandatory
	DESCRIPTION "The type of interface"
	::= { nlIfEntry 3 }

nlIfIndex OBJECT-TYPE
	SYNTAX INTEGER
	ACCESS read-only
	STATUS mandatory
	DESCRIPTION "The associated index into the MIB-II ifTable for this
	port"
	::= { nlIfEntry 4 }

nlIfTableIndex OBJECT-TYPE
	SYNTAX INTEGER
	ACCESS read-only
	STATUS mandatory
	DESCRIPTION "The associated index into an enterprise table used to
	describe additional information for this port. See nlIfTableOid as the 
	pointer to the actual table."
	::= { nlIfEntry 5 }

nlIfTableOid OBJECT-TYPE
	SYNTAX OBJECT IDENTIFIER
	ACCESS read-only
	STATUS mandatory
	DESCRIPTION "The OID of the table Entry that contains additional
	information about this port. The OID will point to a specific table
	depending on the type of port."
	::= { nlIfEntry 6 }

nlIfConnectorType OBJECT-TYPE
	SYNTAX INTEGER { none(2),
					 rs232(3),
					 v25bis-dial(4),
					 v35(5),
					 rs449(6),
					 rs530(7),
					 x21(8),	
					 csudsu(9),
					 t1(10),
					 e1(11),
					 voice(13) 
					}

	ACCESS read-only
	STATUS mandatory
	DESCRIPTION "The physical connector type used for this port. Valid
	for ports 1-8 only."
	::= { nlIfEntry 7 }

nlIfPortStatus OBJECT-TYPE
	SYNTAX INTEGER { linkUp(1),
					 restarting(2),
					 operational(3),
					 disabled(4),
					 disconnect(5),
					 configured(6),
					 dialReady(7),
					 quiesced(8),
					 failed(9),
					 hardwareFault(10),
					 other(11),
					 ipl(12),
					 na(13),
					 remoteLoopback(14),
					 blueAlarm(15),
					 yellowAlarm(16),
					 redAlarm(17),
					 onHook(18),
					 offHook(19),
					 dialing(20),
					 activeVoiceCall(21),
					 onHookPending(22) 
				   }
	ACCESS read-only
	STATUS mandatory
	DESCRIPTION "The status of this port state. Valid for ports 1-64 only."
	::= { nlIfEntry 8 }

nlIfPhyPort OBJECT-TYPE
	SYNTAX INTEGER
	ACCESS read-only
	STATUS mandatory
	DESCRIPTION "The Underlying Physical Port number on the RLP of this
	logical port. Port numbers 1-8 are valid, but this field is only
	applicable if the nlIfPort field is 9-64."
	::= { nlIfEntry 9 }

nlIfLlc2Interfaces OBJECT IDENTIFIER ::= { nlInterfaces 2}

--
--  The Netlink LLC2 Interface Tables
--

nlIfLlc2LANTable OBJECT-TYPE
	SYNTAX SEQUENCE OF NlIfLlc2LANEntry
	ACCESS not-accessible
	STATUS mandatory
	DESCRIPTION "A Table to define LLC2 interfaces over LAN."
	::= { nlIfLlc2Interfaces 1 }

nlIfLlc2LANEntry OBJECT-TYPE
	SYNTAX NlIfLlc2LANEntry
	ACCESS not-accessible
	STATUS mandatory
	DESCRIPTION "An LLC2 LAN Interface entry containing objects relating
	to LLC2 LAN interfaces."
	INDEX { nlIfLlc2LANRlp, nlIfLlc2LANPort }
	::= { nlIfLlc2LANTable 1 }

NlIfLlc2LANEntry ::=
	SEQUENCE {
		nlIfLlc2LANRlp				INTEGER,
		nlIfLlc2LANPort				INTEGER,
		nlIfLlc2LANType				INTEGER,
		nlIfLlc2LANCard				INTEGER,	
		nlIfLlc2LANID				INTEGER,
		nlIfLlc2LANInterface			INTEGER,
		nlIfLlc2LANRowStatus			RowStatus,
		nlIfLlc2LANPriority                     INTEGER,
        nlIfLlc2LANBlockedPortFlag              INTEGER
	}

nlIfLlc2LANRlp   OBJECT-TYPE
		SYNTAX INTEGER
		ACCESS read-only
		STATUS mandatory
		DESCRIPTION "The RLP number on the node. For LLC2 LAN interfaces,
		this must be 252."
		::= { nlIfLlc2LANEntry 1 }

nlIfLlc2LANPort OBJECT-TYPE
		SYNTAX INTEGER
		ACCESS read-only
		STATUS mandatory
		DESCRIPTION "The Port number on the RLP. For LLC2 LAN interfaces,
		this corresponds to the LAN card number."
		::= { nlIfLlc2LANEntry 2 }

nlIfLlc2LANType OBJECT-TYPE
		SYNTAX INTEGER {
			ethernet (1),
			token-ring (2)
		}
		ACCESS read-write
		STATUS mandatory
		DESCRIPTION "The type of the LLC2 interface- either ethernet or
		token ring."
		DEFVAL { ethernet }
		::= { nlIfLlc2LANEntry 3 }

nlIfLlc2LANCard OBJECT-TYPE
		SYNTAX INTEGER (1..2)
		ACCESS read-only
		STATUS mandatory
		DESCRIPTION "The LAN card that the LLC2 interface is running on."
		::= { nlIfLlc2LANEntry 4 }

nlIfLlc2LANID 	OBJECT-TYPE
		SYNTAX INTEGER (0..4095)
		ACCESS read-write
		STATUS mandatory
		DESCRIPTION "Valid only if the type of the LLC2 LAN interface is
		token ring.  Identifies the token ring adapter to the network."
		DEFVAL { 4095 }
		::= { nlIfLlc2LANEntry 5 }

nlIfLlc2LANInterface OBJECT-TYPE
		     SYNTAX INTEGER (1..2)
		     ACCESS read-only
		     STATUS mandatory
		     DESCRIPTION "The LLC2 interface number."
		     ::= { nlIfLlc2LANEntry 6 }

nlIfLlc2LANRowStatus 	OBJECT-TYPE
                        SYNTAX      RowStatus
                        ACCESS      read-write
                        STATUS      mandatory
                        DESCRIPTION
            "This variable is used to manage the creation and deletion
            of conceptual rows in the nlIfLlc2LANTable and follows the
            SNMPv2 RowStatus conventions by supporting the following values:

                 - `active', which indicates that the conceptual row is
                available for use by the managed device.  For a management
                protocol set operation, a genErr response is returned when
                the row does not exist.

                 - `createAndGo', which is supplied by a management
                 station wishing to create a new instance of a
                 conceptual row and to have its status automatically set
                 to active, making it available for use by the managed
                 device.  For a management protocol set operation, a
                 genErr response is returned when the row already exists.

                 - `destroy', which is supplied by a management station
                 wishing to delete all of the instances associated with
                 an existing conceptual row.

            Note that all of the above values may be specified in a
            management protocol set operation, and only the 'active'
            value will be returned in response to a management protocol
            retrieval operation.  For a management protocol set operation,
            if other variable bindings are included in the same PDU, then
            a genErr response is returned."
			::= { nlIfLlc2LANEntry 7 }

nlIfLlc2LANPriority 	OBJECT-TYPE
			SYNTAX INTEGER (0..9)
  		   	ACCESS read-write
		   	STATUS mandatory
		   	DESCRIPTION "Interface priority- allows setting a priority for traffic
		   	within the node.  The higher the number, the higher the priority relative
		   	to other intra-nodal traffic."
			DEFVAL { 0 }
		   	::= {nlIfLlc2LANEntry 8}

nlIfLlc2LANBlockedPortFlag 	OBJECT-TYPE
				SYNTAX  INTEGER {
						no(1),
						yes(2)
				}
        	                ACCESS      read-write
                	        STATUS      mandatory
                        	DESCRIPTION
                        		"The blocked port flag."
				DEFVAL { no }
				::= { nlIfLlc2LANEntry 9 }

nlIfLlc2FrTable OBJECT-TYPE
	SYNTAX SEQUENCE OF NlIfLlc2FrEntry
	ACCESS not-accessible
	STATUS mandatory
	DESCRIPTION "A Table to define LLC2 interfaces over Frame Relay."
	::= { nlIfLlc2Interfaces 2 }

nlIfLlc2FrEntry OBJECT-TYPE
	SYNTAX NlIfLlc2FrEntry
	ACCESS not-accessible
	STATUS mandatory
	DESCRIPTION "An LLC2 FR Interface entry containing objects relating
	to LLC2 FR interfaces."
	INDEX { nlIfLlc2FrRlp, nlIfLlc2FrPort, nlIfLlc2FrDLCI, nlIfLlc2FrFormat }
	::= { nlIfLlc2FrTable 1 }

NlIfLlc2FrEntry ::=
	SEQUENCE {
		nlIfLlc2FrRlp				INTEGER,
		nlIfLlc2FrPort				INTEGER,
		nlIfLlc2FrDLCI				INTEGER,
		nlIfLlc2FrFormat			INTEGER,	
		nlIfLlc2FrPriority			INTEGER,
		nlIfLlc2FrBAG				INTEGER,
		nlIfLlc2FrHostMACAddress		MacAddress,
		nlIfLlc2FrSessionType			INTEGER,
		nlIfLlc2FrLANID				INTEGER,
		nlIfLlc2FrInterface                     INTEGER,
		nlIfLlc2FrRowStatus 			RowStatus,
		nlIfLlc2FrBlockedPortFlag               INTEGER
	}

nlIfLlc2FrRlp   OBJECT-TYPE
		SYNTAX INTEGER (1..8)
		ACCESS read-only
		STATUS mandatory
		DESCRIPTION "The RLP number on the node."
		::= { nlIfLlc2FrEntry 1 }

nlIfLlc2FrPort  OBJECT-TYPE
		SYNTAX INTEGER (1..255)
		ACCESS read-only
		STATUS mandatory
		DESCRIPTION "The Port number on the RLP. Port numbers 1-8 are
		known to be physical ports, and channels are 193-241."
		::= { nlIfLlc2FrEntry 2 }

nlIfLlc2FrDLCI  OBJECT-TYPE
		SYNTAX INTEGER (16..991)
		ACCESS read-only
		STATUS mandatory
		DESCRIPTION "The DLCI number used to identify the entry in the table. 
		The range is 16-991. "
		::= { nlIfLlc2FrEntry 3 }

nlIfLlc2FrFormat OBJECT-TYPE
		 SYNTAX INTEGER {
			native-llc2 (1),
			tb-8023 (2),
			srb-8025 (3)
		 }
		 ACCESS read-only
		 STATUS mandatory
		 DESCRIPTION "The RFC1490 encapsulation method used for LLC2 traffic."
		 ::= {nlIfLlc2FrEntry 4}

nlIfLlc2FrPriority OBJECT-TYPE
		   SYNTAX INTEGER (0..9)
  		   ACCESS read-write
		   STATUS mandatory
		   DESCRIPTION "Interface priority- allows setting a priority for traffic
		   within the node.  The higher the number, the higher the priority relative
		   to other intra-nodal traffic."
		   DEFVAL { 0 }
		   ::= {nlIfLlc2FrEntry 5}

nlIfLlc2FrBAG OBJECT-TYPE
	      SYNTAX INTEGER (1..16)
  	      ACCESS read-write
	      STATUS mandatory
	      DESCRIPTION "Assigns the interface to one of sixteen groups whose parameters
	      regulate bandwidth usage."
	      DEFVAL { 1 }
	      ::= {nlIfLlc2FrEntry 6}

nlIfLlc2FrHostMACAddress OBJECT-TYPE
			 SYNTAX MacAddress
			 ACCESS read-write
			 STATUS mandatory
			 DESCRIPTION "The MAC address of the host or workstation to which 
			 the remote device needs to connect.  Valid only if the format is
			 native-llc2."
		  	 DEFVAL { '400000000001'H }    -- 40:00:00:00:00:01
			 ::= {nlIfLlc2FrEntry 7}

nlIfLlc2FrSessionType	OBJECT-TYPE
			SYNTAX INTEGER {
				terminated (1),
				originated (2),
				not-applicable (3)
			}				
			ACCESS read-write
			STATUS mandatory
			DESCRIPTION "If originated, means that LLC2 connects from the configured
			Host MAC address can use this interface.  If terminated, connections to
			the configured address can use this interface.  Valid only if the
			format is native-llc2."
			DEFVAL { originated }
			::= {nlIfLlc2FrEntry 8}

nlIfLlc2FrLANID 	OBJECT-TYPE
			SYNTAX INTEGER (0..4095)
			ACCESS read-write
			STATUS mandatory
			DESCRIPTION "Identifies the ring number used by a frame relay-compliant
			source-route bridge at the other end of this PVC.  Valid only if the
			format is srb-8025."
			DEFVAL { 4095 }
			::= { nlIfLlc2FrEntry 9 }

nlIfLlc2FrInterface 	OBJECT-TYPE
			SYNTAX INTEGER 
			ACCESS read-only
			STATUS mandatory
			DESCRIPTION "LLC2 interface number."
			::= { nlIfLlc2FrEntry 10 }

nlIfLlc2FrRowStatus 	OBJECT-TYPE
                        SYNTAX      RowStatus
                        ACCESS      read-write
                        STATUS      mandatory
                        DESCRIPTION
            "This variable is used to manage the creation and deletion
            of conceptual rows in the nlIfLlc2FrTable and follows the
            SNMPv2 RowStatus conventions by supporting the following values:

                 - `active', which indicates that the conceptual row is
                available for use by the managed device.  For a management
                protocol set operation, a genErr response is returned when
                the row does not exist.

                 - `createAndGo', which is supplied by a management
                 station wishing to create a new instance of a
                 conceptual row and to have its status automatically set
                 to active, making it available for use by the managed
                 device.  For a management protocol set operation, a
                 genErr response is returned when the row already exists.

                 - `destroy', which is supplied by a management station
                 wishing to delete all of the instances associated with
                 an existing conceptual row.

            Note that all of the above values may be specified in a
            management protocol set operation, and only the 'active'
            value will be returned in response to a management protocol
            retrieval operation.  For a management protocol set operation,
            if other variable bindings are included in the same PDU, then
            a genErr response is returned."
			::= { nlIfLlc2FrEntry 11 }

nlIfLlc2FrBlockedPortFlag 	OBJECT-TYPE
				SYNTAX  INTEGER {
						no(1),
						yes(2)
				}
        	                ACCESS      read-write
                	        STATUS      mandatory
                        	DESCRIPTION
                        		"The blocked port flag."
				DEFVAL { no }
				::= { nlIfLlc2FrEntry 12 }	

ipxConfig OBJECT IDENTIFIER ::=    { nlInterfaces 3 }
ipxConfigRouting OBJECT IDENTIFIER ::= { ipxConfig 1 }

-- Routing Group

-- Static Route Config Table
--  The static route config table contains an entry for each static route entry
--  in the system 

ipxStaticRouteConfigTable OBJECT-TYPE
	SYNTAX	SEQUENCE OF IPXStaticRouteConfigEntry
	ACCESS  not-accessible
	STATUS	mandatory
	DESCRIPTION	"The IPX Static Route Configuration Table"
	::= {ipxConfigRouting 1}

ipxStaticRouteConfigEntry OBJECT-TYPE
	SYNTAX	IPXStaticRouteConfigEntry
	ACCESS	not-accessible
	STATUS	mandatory
	DESCRIPTION	"Each entry corresponds to one instance of IPX Static Routing on the system"
	INDEX	{ipxStaticRouteConfigCircIndex,
			 ipxStaticRouteConfigNetNum
			}

	::= {ipxStaticRouteConfigTable 1}

IPXStaticRouteConfigEntry ::= SEQUENCE {
			ipxStaticRouteConfigCircIndex
				INTEGER,
			ipxStaticRouteConfigNetNum
				OCTET STRING,
			ipxStaticRouteConfigRouter
				OCTET STRING,
			ipxStaticRouteConfigRowStatus
				RowStatus
}

ipxStaticRouteConfigCircIndex OBJECT-TYPE 
	SYNTAX	INTEGER (1..65535)
	ACCESS	read-only 
	STATUS	mandatory
	DESCRIPTION	"The unique identifier of the circuit used to reach the
				first hop in the static route"
	::= {ipxStaticRouteConfigEntry 1}

ipxStaticRouteConfigNetNum OBJECT-TYPE 
	SYNTAX	OCTET STRING (SIZE(4))    
	ACCESS	read-only 
	STATUS	mandatory
	DESCRIPTION	"The IPX network number of the route's destination"
	::= {ipxStaticRouteConfigEntry 2}

ipxStaticRouteConfigRouter OBJECT-TYPE
	SYNTAX	OCTET STRING (SIZE(6)) 
	ACCESS	read-write
	STATUS	mandatory
	DESCRIPTION	"The hex value of the node address of the router that will forward a packet when this route is used. 
				 If Novell's IPXWAN is used on the interface, this field will be ignored "
	::= {ipxStaticRouteConfigEntry 3}

ipxStaticRouteConfigRowStatus OBJECT-TYPE 
	SYNTAX	RowStatus
	ACCESS	read-write
	STATUS	mandatory
    DESCRIPTION
            "This variable is used to manage the creation and deletion
            of conceptual rows in the ipxStaticRouteTable  and follows the
            SNMPv2 RowStatus conventions by supporting the following values:

                 - `active', which indicates that the conceptual row is
                available for use by the managed device.  For a management
                protocol set operation, a genErr response is returned when
                the row does not exist.

                 - `createAndGo', which is supplied by a management
                 station wishing to create a new instance of a
                 conceptual row and to have its status automatically set
                 to active, making it available for use by the managed
                 device.  For a management protocol set operation, a
                 genErr response is returned when the row already exists.

                 - `destroy', which is supplied by a management station
                 wishing to delete all of the instances associated with
                 an existing conceptual row.

            Note that all of the above values may be specified in a
            management protocol set operation, and only the 'active'
            value will be returned in response to a management protocol
            retrieval operation.  For a management protocol set operation,
            if other variable bindings are included in the same PDU, then
            a genErr response is returned."
	::= {ipxStaticRouteConfigEntry 4}

-- Static SAP Config Table
--  The static SAP config table contains an entry for each SAP route entry
--  in the system 

ipxServConfigTable OBJECT-TYPE
	SYNTAX	SEQUENCE OF IPXServConfigEntry
	ACCESS  not-accessible
	STATUS	mandatory
	DESCRIPTION	"The IPX Static Route Configuration Table"
	::= {ipxConfigRouting 2}

ipxServConfigEntry OBJECT-TYPE
	SYNTAX	IPXServConfigEntry
	ACCESS	not-accessible
	STATUS	mandatory
	DESCRIPTION	"Each entry corresponds to one instance of IPX Static Routing on the system"
	INDEX	{ipxServConfigServiceType,
			 ipxServConfigServName
			}

	::= {ipxServConfigTable 1}

IPXServConfigEntry ::= SEQUENCE {
			ipxServConfigServiceType
				INTEGER,
			ipxServConfigServName
				OCTET STRING,
			ipxServConfigServNetworkAddress
				INTEGER, 
			ipxServConfigServNodeAddress 
				OCTET STRING, 
			ipxServConfigServSocketNumber 
				INTEGER, 
			ipxServConfigInterveningNetworks 
				INTEGER,
			ipxServConfigGatewayAddress 
				OCTET STRING, 
			ipxServConfigInterface 
				INTEGER,
			ipxServConfigRowStatus
				RowStatus
}

ipxServConfigServiceType  OBJECT-TYPE 
	SYNTAX	INTEGER (1..65535) 
	ACCESS	read-only 
	STATUS	mandatory
	DESCRIPTION	"The Service Type, a SAP service code "
	::= {ipxServConfigEntry 1}

ipxServConfigServName  OBJECT-TYPE 
	SYNTAX	OCTET STRING (SIZE(1..48)) 
	ACCESS	read-only 
	STATUS	mandatory
	DESCRIPTION	"The Sercice Name, identifies a specific server in the IPX network. "
	::= {ipxServConfigEntry 2}

ipxServConfigServNetworkAddress OBJECT-TYPE 
	SYNTAX	INTEGER  
	ACCESS	read-write
	STATUS	mandatory
	DESCRIPTION	"The IPX network number portion of the IPX address of the server identified by ServName "
	DEFVAL { 1 } 
	::= {ipxServConfigEntry 3}

ipxServConfigServNodeAddress OBJECT-TYPE 
	SYNTAX	OCTET STRING (SIZE(6))
	ACCESS	read-write
	STATUS	mandatory
	DESCRIPTION	"The  node portion of the IPX address of the service"
	::= {ipxServConfigEntry 4}

ipxServConfigServSocketNumber OBJECT-TYPE 
	SYNTAX	INTEGER (0..65535)
	ACCESS	read-write
	STATUS	mandatory
	DESCRIPTION	"The socket portion of the IPX address of the service"
	DEFVAL { 0 } 
	::= {ipxServConfigEntry 5}

ipxServConfigInterveningNetworks OBJECT-TYPE 
	SYNTAX	INTEGER (1..65535)
	ACCESS	read-write
	STATUS	mandatory
	DESCRIPTION	"The number of routers that a packet must pass through t reach the server"
	DEFVAL { 1 } 
	::= {ipxServConfigEntry 6}

ipxServConfigGatewayAddress  OBJECT-TYPE 
	SYNTAX	OCTET STRING (SIZE(6))
	ACCESS	read-write
	STATUS	mandatory
	DESCRIPTION	"The node address of the router thar will forward a packet"
	::= {ipxServConfigEntry 7}

ipxServConfigInterface  OBJECT-TYPE 
	SYNTAX	INTEGER (0..65535) 
	ACCESS	read-write
	STATUS	mandatory
	DESCRIPTION	"The IPX network number assigned to the interface used to send packets that are destined for this server"
	DEFVAL { 0 } 
	::= {ipxServConfigEntry 8}

ipxServConfigRowStatus OBJECT-TYPE
	SYNTAX RowStatus
	ACCESS read-write
	STATUS mandatory
    DESCRIPTION
            "This variable is used to manage the creation and deletion
            of conceptual rows in the ipxServTable  and follows the
            SNMPv2 RowStatus conventions by supporting the following values:

                 - `active', which indicates that the conceptual row is
                available for use by the managed device.  For a management
                protocol set operation, a genErr response is returned when
                the row does not exist.

                 - `createAndGo', which is supplied by a management
                 station wishing to create a new instance of a
                 conceptual row and to have its status automatically set
                 to active, making it available for use by the managed
                 device.  For a management protocol set operation, a
                 genErr response is returned when the row already exists.

                 - `destroy', which is supplied by a management station
                 wishing to delete all of the instances associated with
                 an existing conceptual row.

            Note that all of the above values may be specified in a
            management protocol set operation, and only the 'active'
            value will be returned in response to a management protocol
            retrieval operation.  For a management protocol set operation,
            if other variable bindings are included in the same PDU, then
            a genErr response is returned."
	::= {ipxServConfigEntry 9}

ipxConfigInterface OBJECT IDENTIFIER ::= { ipxConfig 2 }

-- Interface Group

-- Interface Table

ipxInterfaceTable OBJECT-TYPE
	SYNTAX SEQUENCE OF IPXInterfaceEntry 
	ACCESS	not-accessible
	STATUS	mandatory 
	DESCRIPTION "The IPX Interface Table"
	::= {ipxConfigInterface 6} 

ipxInterfaceEntry OBJECT-TYPE
	SYNTAX	IPXInterfaceEntry 
	ACCESS	not-accessible 
	STATUS	mandatory 
	DESCRIPTION ""
	INDEX	{ipxInterfaceNumber 
			} 

	::= {ipxInterfaceTable 1} 

IPXInterfaceEntry ::= SEQUENCE {
	ipxInterfaceNumber INTEGER,
	ipxInterfaceBlockedPortFlag INTEGER,
	ipxInterfaceType INTEGER,
	ipxInterfaceFrameType INTEGER, 
	ipxInterfaceMaxTransUnit INTEGER, 
	ipxInterfaceNetworkAddress INTEGER, 
	ipxInterfaceBandwidthAllocGroup INTEGER, 
	ipxInterfacePortDiagEnabled INTEGER, 
	ipxInterfaceNetBIOSEnabled INTEGER, 
	ipxInterfaceNetBIOSHops INTEGER, 
	ipxInterfacePeriodicRIPEnabled INTEGER, 
	ipxInterfacePeriodicRIPTimer INTEGER, 
	ipxInterfacePeriodicSAPEnabled INTEGER, 
	ipxInterfacePeriodicSAPTimer INTEGER, 
	ipxInterfaceRIPEnabled INTEGER, 
	ipxInterfaceRIPAgeTimer INTEGER, 
	ipxInterfaceRIPMaxSize INTEGER, 
	ipxInterfaceSAPEnabled INTEGER, 
	ipxInterfaceSAPAgeTimer INTEGER, 
	ipxInterfaceTransportTime INTEGER, 
	ipxInterfaceSerializationEnabled INTEGER, 
	ipxInterfaceWatchdogSpoofingEnabled INTEGER, 
	ipxInterfaceLanCardNumber INTEGER, 
	ipxInterfaceWanEnabled INTEGER,
	ipxInterfaceSourceSubscriber OCTET STRING,
	ipxInterfaceDestinationSubscriber OCTET STRING,
	ipxInterfaceSVCRetryTimer INTEGER,
	ipxInterfaceSVCIdleTimer  INTEGER,
	ipxInterfaceMaxVC INTEGER,
	ipxInterfacePVCConnection INTEGER,
	ipxInterfaceSourceCard INTEGER,
	ipxInterfaceSourcePort INTEGER,
	ipxInterfaceSourceDLCI INTEGER, 
	ipxInterfaceRowStatus RowStatus 
}

ipxInterfaceNumber OBJECT-TYPE 
	SYNTAX INTEGER (1..64) 
	ACCESS read-only 
	STATUS mandatory
	DESCRIPTION "The Interface Number, a sequential number to identify the interface"
	::= {ipxInterfaceEntry 1}

ipxInterfaceBlockedPortFlag OBJECT-TYPE 
	SYNTAX INTEGER 
			{ no(1),
			  yes(2)
			}

	ACCESS read-write
	STATUS mandatory
	DESCRIPTION "This flag causes the IPX interface to be enabled (N) or disabled (Y) at node IPL. The port
				 will remain in that state until this parameter is changed"
	::= {ipxInterfaceEntry 2}

ipxInterfaceType OBJECT-TYPE 
	SYNTAX INTEGER
			{ ethernet(1),
			  eight025(2),
			  x25(3),
			  frl(4)
			}

	ACCESS read-write
	STATUS mandatory
	DESCRIPTION "The interface type. 802.5 is not valid on FRX4000"
	::= {ipxInterfaceEntry 3}

ipxInterfaceFrameType OBJECT-TYPE 
	SYNTAX INTEGER
			{ typeII(1),
			  raw(2),
			  llc(3),
			  snap(4)
			}
	ACCESS read-write
	STATUS mandatory
	DESCRIPTION "The frame type - depends on the interfece type. Valid combinations are: 
				 Ethernet, 802.5  - typeII, raw, llc, snap
				 Frame relay, X25 - typeII"
	DEFVAL { typeII }
	::= {ipxInterfaceEntry 4}

ipxInterfaceMaxTransUnit OBJECT-TYPE 
	SYNTAX INTEGER 
	ACCESS read-write
	STATUS mandatory
	DESCRIPTION "Maximum frame size that can be transmitted or received over the IPX interface.: Valid ranges are:
				 Ethernet		  - (45-1518)
				 802.5			  - (48-4096)
				 Frame relay, X25 - (31-4096) "
	DEFVAL { 4096 }
	::= {ipxInterfaceEntry 5}

ipxInterfaceNetworkAddress OBJECT-TYPE 
	SYNTAX INTEGER 
	ACCESS read-write
	STATUS mandatory
	DESCRIPTION "Identifies the local interface to the Novell Network"
	DEFVAL { 0 }
	::= {ipxInterfaceEntry 6}

ipxInterfaceBandwidthAllocGroup OBJECT-TYPE 
	SYNTAX INTEGER (1..16)  
	ACCESS read-write
	STATUS mandatory
	DESCRIPTION "Assigns the IPX interface to one of sixteen groups whose parameters regulate bandwidth usage"
	DEFVAL { 1 }
	::= {ipxInterfaceEntry 7}

ipxInterfacePortDiagEnabled OBJECT-TYPE 
	SYNTAX INTEGER
			{ no(1),
			  yes(2)
			} 
	ACCESS read-write
	STATUS mandatory
	DESCRIPTION "Enables/Disables the IPX interface's ability to handle Novell diagonistics packets"
	DEFVAL { no }
	::= {ipxInterfaceEntry 8}

ipxInterfaceNetBIOSEnabled OBJECT-TYPE 
	SYNTAX INTEGER
			{ no(1),
			  yes(2)
			} 
	ACCESS read-write
	STATUS mandatory
	DESCRIPTION "Determines whether Novell-encapsulated NetBIOS 
				 frames received on the interface will be processed"
	DEFVAL { no }
	::= {ipxInterfaceEntry 9}

ipxInterfaceNetBIOSHops OBJECT-TYPE 
	SYNTAX INTEGER (0..255)  
	ACCESS read-write
	STATUS mandatory
	DESCRIPTION "Maximum number of hops allowed for routing a Novell-encapsulated NetBIOS frame"
	DEFVAL { 8 }
	::= {ipxInterfaceEntry 10}

ipxInterfacePeriodicRIPEnabled OBJECT-TYPE 
	SYNTAX INTEGER  
			{ no(1),
			  yes(2)
			} 
	ACCESS read-write
	STATUS mandatory
	DESCRIPTION "Determines whether the node will originate periodic IPX Routing Information Protocol messages
				 from this interface to inform the network that the route through this interface is viable"
	DEFVAL { no }
	::= {ipxInterfaceEntry 11}

ipxInterfacePeriodicRIPTimer OBJECT-TYPE 
	SYNTAX INTEGER (1..65535)  
	ACCESS read-write
	STATUS mandatory
	DESCRIPTION "This is the interval between the periodic IPX RIP broadcasts from this interface"
	DEFVAL { 60 }
	::= {ipxInterfaceEntry 12}

ipxInterfacePeriodicSAPEnabled OBJECT-TYPE 
	SYNTAX INTEGER  {
						no(1),
						yes(2)
					} 
	ACCESS read-write
	STATUS mandatory
	DESCRIPTION "Determines whether the node will originate periodic IPX SAP messages
				 from this interface to inform the network which SAP entries in the routing table are viable"
	DEFVAL { no }
	::= {ipxInterfaceEntry 13}

ipxInterfacePeriodicSAPTimer OBJECT-TYPE 
	SYNTAX INTEGER (1..65535)  
	ACCESS read-write
	STATUS mandatory
	DESCRIPTION "The interval between the periodic SAP broadcasts from this interface"
	DEFVAL { 60 }
	::= {ipxInterfaceEntry 14}

ipxInterfaceRIPEnabled OBJECT-TYPE 
	SYNTAX INTEGER  
			{ no(1),
			  yes(2)
			} 
	ACCESS read-write
	STATUS mandatory
	DESCRIPTION "Datermines whether this interface will support RIP proceswsing "
	DEFVAL { no }
	::= {ipxInterfaceEntry 15}

ipxInterfaceRIPAgeTimer OBJECT-TYPE 
	SYNTAX INTEGER (0..65535) 
	ACCESS read-write
	STATUS mandatory
	DESCRIPTION "This is used to delete route entries in the routing information table. The timer starts/restarts
				 each time an entry is created/updated. If the timer expires, the router will assume that the entry is no
				 longer valid and the entry will be deleteda from the table "
	DEFVAL { 180 }
	::= {ipxInterfaceEntry 16}

ipxInterfaceRIPMaxSize OBJECT-TYPE 
	SYNTAX INTEGER  (54..446) 
	ACCESS read-write
	STATUS mandatory
	DESCRIPTION "Maximum possible RIP packet size "
	DEFVAL { 446 }
	::= {ipxInterfaceEntry 17}

ipxInterfaceSAPEnabled OBJECT-TYPE 
	SYNTAX INTEGER 
			{ no(1),
			  yes(2)
			} 
	ACCESS read-write
	STATUS mandatory
	DESCRIPTION "Determines whether the interface will support SAP or not "
	DEFVAL { no }
	::= {ipxInterfaceEntry 18}

ipxInterfaceSAPAgeTimer OBJECT-TYPE 
	SYNTAX INTEGER (0..65535) 
	ACCESS read-write
	STATUS mandatory
	DESCRIPTION "This is used to delete route entries from the router information table. The timer starts/restars
				 each time an entry is created/updated. If the timer expires, the router will assume that the entry is no
				 longer valid and the entry will be deleted from the table "
	DEFVAL { 180 }
	::= {ipxInterfaceEntry 19}

ipxInterfaceTransportTime OBJECT-TYPE 
	SYNTAX INTEGER (1..255) 
	ACCESS read-write
	STATUS mandatory
	DESCRIPTION "is the time (in 55 milliseconds unit) that will normally take to forward frames out of interface.
				 Recommmended values are 1 for LAN interfaces and 30 for WAN interfaces. A value of 0 indicates that the
				 back to back frame forwarding is acceptable. This time is used to calculate the least cost path during
				 routing. If IPXWAMN is (Y), Transport time will be overridden by the value calculated by IPXWAN "
	DEFVAL { 1 }
	::= {ipxInterfaceEntry 20}

ipxInterfaceSerializationEnabled OBJECT-TYPE 
	SYNTAX INTEGER 
			{ no(1),
			  yes(2)
			} 
	ACCESS read-write
	STATUS mandatory
	DESCRIPTION "Determines whether NetWare file server serialization security frames will be 
				 forwarded on the interface. These broadcasts frames are used by Novell to hold informations regarding the
				 licensing of the file server executables "
	DEFVAL { no }
	::= {ipxInterfaceEntry 21}

ipxInterfaceWatchdogSpoofingEnabled OBJECT-TYPE 
	SYNTAX INTEGER 
			{ no(1),
			  yes(2)
			} 
	ACCESS read-write
	STATUS mandatory
	DESCRIPTION "Determines whether this interface will be used by the local node to respond to (keep alive) messages on
				 behalf of the client workstations. Novell servers periodically issue these messages to all clients
				 to determine whether each client is still alive "
	DEFVAL { no }
	::= {ipxInterfaceEntry 22}

ipxInterfaceLanCardNumber OBJECT-TYPE
	SYNTAX INTEGER (0..1)  
	ACCESS read-write
	STATUS mandatory
	DESCRIPTION "The card number installed in an FRX6000. The first or only LAN card installed is always 0,
				 and the second is card 1" 
	DEFVAL { 0 }
	::= {ipxInterfaceEntry 23}

ipxInterfaceWanEnabled OBJECT-TYPE
	SYNTAX INTEGER
			{ no(1),
			  yes(2),
			  not-applicable(3) 
			} 
	ACCESS read-write
	STATUS mandatory
	DESCRIPTION "Determines whether Novell's IPXWAN protocol will be used on the interface. IPXWAN specifies a method 
				 for IPX routers to communicate across WAN links. FRX6000 and FRX4000 implement IPXWAN running over RFC 
				 1490-complaint frame relay and RFC1356-complaint X.25" 
	DEFVAL { no }
	::= {ipxInterfaceEntry 24}

ipxInterfaceSourceSubscriber OBJECT-TYPE
	SYNTAX OCTET STRING (SIZE(0..15)) 
	ACCESS read-write
	STATUS mandatory
	DESCRIPTION "Subscruber id that defines an IPX interface in the node, by associating itself with port 66 (a
				 number reserved for the IPXinterface) on the RLP that has an IPX installed on it. 
				 .. Valid only for type X.25 " 
	::= {ipxInterfaceEntry 25}

ipxInterfaceDestinationSubscriber OBJECT-TYPE
	SYNTAX OCTET STRING (SIZE(0..15)) 
	ACCESS read-write
	STATUS mandatory
	DESCRIPTION "Subscriber ID associated with the physical X.25 port that will be used for the IPX interface .
				 .. Valid only for type X.25 " 
	::= {ipxInterfaceEntry 26}

ipxInterfaceSVCRetryTimer OBJECT-TYPE
	SYNTAX INTEGER (5..60) 
	ACCESS read-write
	STATUS mandatory
	DESCRIPTION "The frequency with which calls will be placed to try to establish a connection 
				 .. Valid only for type X.25 " 
	DEFVAL { 20 }
	::= {ipxInterfaceEntry 27}

ipxInterfaceSVCIdleTimer OBJECT-TYPE
	SYNTAX INTEGER (0..5) 
	ACCESS read-write
	STATUS mandatory
	DESCRIPTION "is a period that an IPX connection can remain active with no traffic before the connection is cleared.
				 .. Valid only for type X.25 " 
	DEFVAL { 1 }
	::= {ipxInterfaceEntry 28}

ipxInterfaceMaxVC OBJECT-TYPE
	SYNTAX INTEGER (1..8) 
	ACCESS read-write
	STATUS mandatory
	DESCRIPTION "This specifies a number of virtual circuits over which IPX traffic will be transmitted in parallel.  
				 .. Valid only for type X.25 " 
	DEFVAL { 1 }
	::= {ipxInterfaceEntry 29 }

ipxInterfacePVCConnection OBJECT-TYPE
	SYNTAX INTEGER 
			{ no(1),
			  yes(2), 
			  not-applicable(3) 
			} 
	ACCESS read-write
	STATUS mandatory
	DESCRIPTION "Identifies this interface as one of a PVC.  
				 .. Valid only for type X.25 " 
	DEFVAL { no }
	::= {ipxInterfaceEntry 30}

ipxInterfaceSourceCard OBJECT-TYPE
	SYNTAX INTEGER (0..7) 
	ACCESS read-write
	STATUS mandatory
	DESCRIPTION "Identifies the location of this end of the frame relay IPX interface.
				 .. Valid only for frame relay " 
	DEFVAL { 0 }
	::= {ipxInterfaceEntry 31}

ipxInterfaceSourcePort OBJECT-TYPE
	SYNTAX INTEGER (0..7) 
	ACCESS read-write
	STATUS mandatory
	DESCRIPTION "Identifies the location of this end of the frame relay IPX interface.
				 .. Valid only for frame relay " 
	DEFVAL { 0 }
	::= {ipxInterfaceEntry 32}

ipxInterfaceSourceDLCI OBJECT-TYPE
	SYNTAX INTEGER (16..991)  
	ACCESS read-write
	STATUS mandatory
	DESCRIPTION "Identifies the location of this end of the frame relay IPX interface.
				 .. Valid only for frame relay " 
	DEFVAL { 16 }
	::= {ipxInterfaceEntry 33}

ipxInterfaceRowStatus OBJECT-TYPE 
	SYNTAX RowStatus  
	ACCESS read-write
	STATUS mandatory
    DESCRIPTION
            "This variable is used to manage the creation and deletion
            of conceptual rows in the ipxInterfaceTable and follows the
            SNMPv2 RowStatus conventions by supporting the following values:

                 - `active', which indicates that the conceptual row is
                available for use by the managed device.  For a management
                protocol set operation, a genErr response is returned when
                the row does not exist.

                 - `createAndGo', which is supplied by a management
                 station wishing to create a new instance of a
                 conceptual row and to have its status automatically set
                 to active, making it available for use by the managed
                 device.  For a management protocol set operation, a
                 genErr response is returned when the row already exists.

                 - `destroy', which is supplied by a management station
                 wishing to delete all of the instances associated with
                 an existing conceptual row.

            Note that all of the above values may be specified in a
            management protocol set operation, and only the 'active'
            value will be returned in response to a management protocol
            retrieval operation.  For a management protocol set operation,
            if other variable bindings are included in the same PDU, then
            a genErr response is returned."
	::= {ipxInterfaceEntry 34}

-- The Node Default Group 

ipxConfigNodeDefault OBJECT IDENTIFIER ::= {ipxConfig 3}

ipxNodeDefaultConfigNetworkAddress OBJECT-TYPE 
    SYNTAX	INTEGER  
	ACCESS  read-write
	STATUS  mandatory
	DESCRIPTION "Identifies the node to the IPX network" 
	::= {ipxConfigNodeDefault 1}

ipxNodeDefaultConfigRIPSAPGap OBJECT-TYPE
    SYNTAX 	INTEGER (0..100) 
	ACCESS  read-write
	STATUS  mandatory
	DESCRIPTION "The minimum delay between consecutive RIP and SAP transmissions"
	::= {ipxConfigNodeDefault 2}

ipxNodeDefaultConfigRouterName OBJECT-TYPE
    SYNTAX  OCTET STRING (SIZE(1..48))
	ACCESS  read-write
	STATUS  mandatory
	DESCRIPTION "An unique identifier within the IPX network" 
	::= {ipxConfigNodeDefault 3}

--
--  The Netlink IP Interface Table
--

nlIfIpInterfaces OBJECT IDENTIFIER ::= { nlInterfaces 4}

nlIfIpTable OBJECT-TYPE
	SYNTAX SEQUENCE OF NlIfIpEntry
	ACCESS not-accessible
	STATUS mandatory
	DESCRIPTION "A Table to define IP interfaces over frame relay,
				X.25, or LAN (ethernet, 802.3, 802.5)."
	::= { nlIfIpInterfaces 1 }

nlIfIpEntry OBJECT-TYPE
	SYNTAX NlIfIpEntry
	ACCESS not-accessible
	STATUS mandatory
	DESCRIPTION "An IP Interface entry containing objects relating
	to IP interfaces."
	INDEX { nlIfIpInterface }
	::= { nlIfIpTable 1 }

NlIfIpEntry ::=
	SEQUENCE {
		nlIfIpInterface			INTEGER,
		nlIfIpMtu				INTEGER,
		nlIfIpNetworkMask		IpAddress,
		nlIfIpRouteMetric		INTEGER,
		nlIfIpICMPAddRoutes		INTEGER,
		nlIfIpRIPDeltaUpdates	INTEGER,
		nlIfIpRIPFullUpdates	INTEGER,
		nlIfIpPriority			INTEGER,
		nlIfIpBAG				INTEGER,
		nlIfIpType				INTEGER,
		nlIfIpSourceAddress		IpAddress,
		nlIfIpDestAddress		IpAddress,
		nlIfIpBroadcastAddress	IpAddress,
		nlIfIpLANCard			INTEGER,
		nlIfIpSourceSub			NlSubscriberAddress,
		nlIfIpDestSub			NlSubscriberAddress,
		nlIfIpSVCRetryTimer		INTEGER,
		nlIfIpSVCIdleTimer		INTEGER,
		nlIfIpMaxSVC			INTEGER,
		nlIfIpPVCConnection		INTEGER,
		nlIfIpSourceRlp			INTEGER,
		nlIfIpSourcePort		INTEGER,
		nlIfIpSourceDLCI		INTEGER,
		nlIfIpRIPSupport		INTEGER,
		nlIfIpInverseARP		INTEGER,
		nlIfIpProxyARP			INTEGER,
		nlIfIpUnnumberedIf		INTEGER,
		nlIfIpRowStatus			RowStatus
	}

nlIfIpInterface OBJECT-TYPE
	SYNTAX INTEGER (1..257)
	ACCESS read-only
	STATUS mandatory
	DESCRIPTION "The interface number which uniquely identifies the
				interface to which this entry is applicable. The
				interface identified by a particular value of this
				number is NOT the same interface as defined by the
				same value of ifIndex."
	::= { nlIfIpEntry 1 }

nlIfIpMtu OBJECT-TYPE
	SYNTAX INTEGER (1..4096)
	ACCESS read-write
	STATUS mandatory
	DESCRIPTION "The maximum size (in bytes) of the data field that can
				be used to encapsulate an IP datagram for transmission
				over the interface. If the interface type is LAN based,
				then the maximum size value cannot exceed 1500."
	DEFVAL { 4096 }
	::= { nlIfIpEntry 2 }

nlIfIpNetworkMask OBJECT-TYPE
	SYNTAX IpAddress
	ACCESS read-write
	STATUS mandatory
	DESCRIPTION "The mask used during routing to determine the portion
				of the address associated with the network."
	DEFVAL { 'FF000000'H }    -- 255.0.0.0
	::= { nlIfIpEntry 3 }

nlIfIpRouteMetric OBJECT-TYPE
	SYNTAX INTEGER (0..255)
	ACCESS read-write
	STATUS mandatory
	DESCRIPTION "The number of network hops (network gateways in the
				overall path over the internet) associated with this
				interface."
	DEFVAL { 0 }
	::= { nlIfIpEntry 4 }

nlIfIpICMPAddRoutes OBJECT-TYPE
	SYNTAX INTEGER {
		no(1),
		yes(2)
	}
	ACCESS read-write
	STATUS mandatory
	DESCRIPTION "The flag which indicates whether IP may add routes
				obtained by ICMP, whose error and control function
				is used to send re-direction options back to the
				source if problems are discovered."
	DEFVAL { yes }
	::= { nlIfIpEntry 5 }

nlIfIpRIPDeltaUpdates OBJECT-TYPE
	SYNTAX INTEGER (10..300)
	ACCESS read-write
	STATUS mandatory
	DESCRIPTION "The frequency with which RIP messages will be sent to
				every neighbor node, containing any changes to the
				routing table that occurred since the last full update."
	DEFVAL { 30 }
	::= { nlIfIpEntry 6 }

nlIfIpRIPFullUpdates OBJECT-TYPE
	SYNTAX INTEGER (10..300)
	ACCESS read-write
	STATUS mandatory
	DESCRIPTION "The frequency with which updates of the entire routing
				table will be sent to every neighbor node, via one or
				more RIP messages."
	DEFVAL { 60 }
	::= { nlIfIpEntry 7 }

nlIfIpPriority OBJECT-TYPE
	SYNTAX INTEGER (0..9)
	ACCESS read-write
	STATUS mandatory
	DESCRIPTION "The priority setting for traffic within the node. The
				higher the number, the higher the priority relative to
				other intra-nodal traffic."
	DEFVAL { 5 }
	::= { nlIfIpEntry 8 }

nlIfIpBAG OBJECT-TYPE
	SYNTAX INTEGER (1..16)
	ACCESS read-write
	STATUS mandatory
	DESCRIPTION "The bandwidth allocation group to which this interface
				is assigned to. This object is only valid when the
				interface type is frame relay or proprietary virtual."
	DEFVAL { 1 }
	::= { nlIfIpEntry 9 }

nlIfIpType OBJECT-TYPE
	SYNTAX INTEGER {
		other(1),		-- none of the following
		rfc877x25(5),
		ethernetCsmacd(6),
		iso88023Csmacd(7),
		iso88025TokenRing(9),
		frameRelay(32),		-- DTE only
		propVirtual(53)		-- proprietary virtual/internal
	}
	ACCESS read-write
	STATUS mandatory
	DESCRIPTION "The type of IP interface."
	DEFVAL { rfc877x25 }
	::= { nlIfIpEntry 10 }

nlIfIpSourceAddress OBJECT-TYPE
	SYNTAX IpAddress
	ACCESS read-write
	STATUS mandatory
	DESCRIPTION "The IP address of the end-to-end sender."
	DEFVAL { '00000000'H }    -- 0.0.0.0
	::= { nlIfIpEntry 11 }

nlIfIpDestAddress OBJECT-TYPE
	SYNTAX IpAddress
	ACCESS read-write
	STATUS mandatory
	DESCRIPTION "The IP address of the end-to-end receiver. This object
				is only valid when the interface type is X.25 or proprietary
				virtual, or when the interface type is frame relay and the
				inverse ARP flag indicates disabled."
	DEFVAL { '00000000'H }    -- 0.0.0.0
	::= { nlIfIpEntry 12 }

nlIfIpBroadcastAddress OBJECT-TYPE
	SYNTAX IpAddress
	ACCESS read-write
	STATUS mandatory
	DESCRIPTION "The IP address that is used to send to all LAN hosts
				on the network. This object is only valid when the
				interface type is LAN based."
	DEFVAL { '00000000'H }    -- 0.0.0.0
	::= { nlIfIpEntry 13 }

nlIfIpLANCard OBJECT-TYPE
	SYNTAX INTEGER (0..1)
	ACCESS read-write
	STATUS mandatory
	DESCRIPTION "The LAN card that contains the interface. This object
				is only valid when the interface type is LAN based."
	DEFVAL { 0 }
	::= { nlIfIpEntry 14 }

nlIfIpSourceSub OBJECT-TYPE
	SYNTAX NlSubscriberAddress
	ACCESS read-write
	STATUS mandatory
	DESCRIPTION "The subscriber ID associated with the source IP
				interface port. This object is only valid when the
				interface type is X.25."
	::= { nlIfIpEntry 15 }

nlIfIpDestSub OBJECT-TYPE
	SYNTAX NlSubscriberAddress
	ACCESS read-write
	STATUS mandatory
	DESCRIPTION "The subscriber ID associated with the destination IP
				interface port. This object is only valid when the
				interface type is X.25."
	::= { nlIfIpEntry 16 }

nlIfIpSVCRetryTimer OBJECT-TYPE
	SYNTAX INTEGER (5..60)
	ACCESS read-write
	STATUS mandatory
	DESCRIPTION "The frequency with which calls will be placed to try
				to establish a connection. This object is only valid
				when the interface type is X.25."
	DEFVAL { 20 }
	::= { nlIfIpEntry 17 }

nlIfIpSVCIdleTimer OBJECT-TYPE
	SYNTAX INTEGER (0..5)
	ACCESS read-write
	STATUS mandatory
	DESCRIPTION "The period that an IP connection remains active with
				no traffic before the connection is cleared. This object
				is only valid when the interface type is X.25."
	DEFVAL { 1 }
	::= { nlIfIpEntry 18 }

nlIfIpMaxSVC OBJECT-TYPE
	SYNTAX INTEGER (1..8)
	ACCESS read-write
	STATUS mandatory
	DESCRIPTION "The number of virtual circuits over which IP traffic
				will be transmitted in parallel. This object is only
				valid when the interface type is X.25."
	DEFVAL { 1 }
	::= { nlIfIpEntry 19 }

nlIfIpPVCConnection OBJECT-TYPE
	SYNTAX INTEGER {
		no(1),
		yes(2)
	}
	ACCESS read-write
	STATUS mandatory
	DESCRIPTION "The flag which indicates whether this interface is a
				PVC. This object is only valid when the interface type
				is X.25."
	DEFVAL { no }
	::= { nlIfIpEntry 20 }

nlIfIpSourceRlp OBJECT-TYPE
	SYNTAX INTEGER (1..8)
	ACCESS read-write
	STATUS mandatory
	DESCRIPTION "The RLP of the logical interface of this end of the frame
				relay link. This object is only valid when the interface
				type is frame relay."
	DEFVAL { 1 }
	::= { nlIfIpEntry 21 }

nlIfIpSourcePort OBJECT-TYPE
	SYNTAX INTEGER (1..8)
	ACCESS read-write
	STATUS mandatory
	DESCRIPTION "The port of the logical interface of this end of the frame
				relay link. This object is only valid when the interface
				type is frame relay."
	DEFVAL { 1 }
	::= { nlIfIpEntry 22 }

nlIfIpSourceDLCI OBJECT-TYPE
	SYNTAX INTEGER (16..991)
	ACCESS read-write
	STATUS mandatory
	DESCRIPTION "The DLCI of the logical interface of this end of the frame
				relay link. This object is only valid when the interface
				type is frame relay."
	DEFVAL { 16 }
	::= { nlIfIpEntry 23 }

nlIfIpRIPSupport OBJECT-TYPE
	SYNTAX INTEGER {
		disabled(1),
		enabled(2),
		receive-only(3)
	}
	ACCESS read-write
	STATUS mandatory
	DESCRIPTION "The RIP support that is being run on the interface."
	DEFVAL { enabled }
	::= { nlIfIpEntry 24 }

nlIfIpInverseARP OBJECT-TYPE
	SYNTAX INTEGER {
		disabled(1),
		enabled(2)
	}
	ACCESS read-write
	STATUS mandatory
	DESCRIPTION "The flag which indicates whether inverse ARP is enabled
				or disabled. This object is only valid when the interface
				type is frame relay."
	DEFVAL { disabled }
	::= { nlIfIpEntry 25 }

nlIfIpProxyARP OBJECT-TYPE
	SYNTAX INTEGER {
		disabled(1),
		enabled(2)
	}
	ACCESS read-write
	STATUS mandatory
	DESCRIPTION "The flag which indicates whether proxy ARP is enabled
				or disabled. This object is only valid when the interface
				type is LAN based."
	DEFVAL { disabled }
	::= { nlIfIpEntry 26 }

nlIfIpUnnumberedIf OBJECT-TYPE
	SYNTAX INTEGER {
		no(1),
		yes(2)
	}
	ACCESS read-write
	STATUS mandatory
	DESCRIPTION "The flag which indicates whether this interface is an
				unnumbered interface (i.e., does not require a specific
				source IP address). This object is only valid when the
				interface type is frame relay or X.25."
	DEFVAL { yes }
	::= { nlIfIpEntry 27 }

nlIfIpRowStatus OBJECT-TYPE
	SYNTAX RowStatus
	ACCESS read-write
	STATUS mandatory
    DESCRIPTION
            "This variable is used to manage the creation and deletion
            of conceptual rows in the nlIfIpTable and follows the SNMPv2
            RowStatus conventions by supporting the following values:

                 - `active', which indicates that the conceptual row is
                available for use by the managed device.  For a management
                protocol set operation, a genErr response is returned when
                the row does not exist.

                 - `createAndGo', which is supplied by a management
                 station wishing to create a new instance of a
                 conceptual row and to have its status automatically set
                 to active, making it available for use by the managed
                 device.  For a management protocol set operation, a
                 genErr response is returned when the row already exists.

                 - `destroy', which is supplied by a management station
                 wishing to delete all of the instances associated with
                 an existing conceptual row.

            Note that all of the above values may be specified in a
            management protocol set operation, and only the 'active'
            value will be returned in response to a management protocol
            retrieval operation.  For a management protocol set operation,
            if other variable bindings are included in the same PDU, then
            a genErr response is returned."
	::= { nlIfIpEntry 28 }

--
--  The Netlink IP Interface Secondary Addresses Table
--

nlIfIpSecondaryAddrTable OBJECT-TYPE
	SYNTAX SEQUENCE OF NlIfIpSecondaryAddrEntry
	ACCESS not-accessible
	STATUS mandatory
	DESCRIPTION "A Table to define secondary IP interfaces on a
				LAN (ethernet, 802.3, 802.5) interface."
	::= { nlIfIpInterfaces 2 }

nlIfIpSecondaryAddrEntry OBJECT-TYPE
	SYNTAX NlIfIpSecondaryAddrEntry
	ACCESS not-accessible
	STATUS mandatory
	DESCRIPTION "An IP Secondary Address entry containing objects relating
	to IP secondary addresses."
	INDEX { nlIfIpInterface, nlIfIpSecondaryAddrSequence }
	::= { nlIfIpSecondaryAddrTable 1 }

NlIfIpSecondaryAddrEntry ::=
	SEQUENCE {
		nlIfIpSecondaryAddrSequence				INTEGER,
		nlIfIpSecondaryAddrNetworkMask			IpAddress,
		nlIfIpSecondaryAddrRouteMetric			INTEGER,
		nlIfIpSecondaryAddrSourceAddress		IpAddress,
		nlIfIpSecondaryAddrBroadcastAddress		IpAddress,
		nlIfIpSecondaryAddrRIPSupport			INTEGER,
		nlIfIpSecondaryAddrRowStatus			RowStatus
	}

nlIfIpSecondaryAddrSequence OBJECT-TYPE
	SYNTAX INTEGER (1..15)
	ACCESS read-write
	STATUS mandatory
	DESCRIPTION "The maximum number of secondary IP addresses that may
				be configured on an interface."
	::= { nlIfIpSecondaryAddrEntry 1 }

nlIfIpSecondaryAddrNetworkMask OBJECT-TYPE
	SYNTAX IpAddress
	ACCESS read-write
	STATUS mandatory
	DESCRIPTION "The mask used during routing to determine the portion
				of the address associated with the network."
	DEFVAL { '00000000'H }    -- 0.0.0.0
	::= { nlIfIpSecondaryAddrEntry 2 }

nlIfIpSecondaryAddrRouteMetric OBJECT-TYPE
	SYNTAX INTEGER (0..255)
	ACCESS read-write
	STATUS mandatory
	DESCRIPTION "The number of network hops (network gateways in the
				overall path over the internet) associated with this
				interface."
	DEFVAL { 0 }
	::= { nlIfIpSecondaryAddrEntry 3 }

nlIfIpSecondaryAddrSourceAddress OBJECT-TYPE
	SYNTAX IpAddress
	ACCESS read-write
	STATUS mandatory
	DESCRIPTION "The IP address of the end-to-end sender."
	DEFVAL { '00000000'H }    -- 0.0.0.0
	::= { nlIfIpSecondaryAddrEntry 4 }

nlIfIpSecondaryAddrBroadcastAddress OBJECT-TYPE
	SYNTAX IpAddress
	ACCESS read-write
	STATUS mandatory
	DESCRIPTION "The IP address that is used to send to all LAN hosts
				on the network."
	DEFVAL { '00000000'H }    -- 0.0.0.0
	::= { nlIfIpSecondaryAddrEntry 5 }

nlIfIpSecondaryAddrRIPSupport OBJECT-TYPE
	SYNTAX INTEGER {
		disabled(1),
		enabled(2),
		receive-only(3)
	}
	ACCESS read-write
	STATUS mandatory
	DESCRIPTION "The RIP support that is being run on the interface."
	DEFVAL { enabled }
	::= { nlIfIpSecondaryAddrEntry 6 }

nlIfIpSecondaryAddrRowStatus OBJECT-TYPE
	SYNTAX RowStatus
	ACCESS read-write
	STATUS mandatory
    DESCRIPTION
            "This variable is used to manage the creation and deletion of
            conceptual rows in the nlIfIpSecondaryAddrTable and follows the
            SNMPv2 RowStatus conventions by supporting the following values:

                 - `active', which indicates that the conceptual row is
                available for use by the managed device.  For a management
                protocol set operation, a genErr response is returned when
                the row does not exist.

                 - `createAndGo', which is supplied by a management
                 station wishing to create a new instance of a
                 conceptual row and to have its status automatically set
                 to active, making it available for use by the managed
                 device.  For a management protocol set operation, a
                 genErr response is returned when the row already exists.

                 - `destroy', which is supplied by a management station
                 wishing to delete all of the instances associated with
                 an existing conceptual row.

            Note that all of the above values may be specified in a
            management protocol set operation, and only the 'active'
            value will be returned in response to a management protocol
            retrieval operation.  For a management protocol set operation,
            if other variable bindings are included in the same PDU, then
            a genErr response is returned."
	::= { nlIfIpSecondaryAddrEntry 7 }

nlIfVoiceInterfaces OBJECT IDENTIFIER ::= { nlInterfaces 5}

--
--  The Netlink Voice Interface Table
--

nlIfVoiceTable OBJECT-TYPE
    SYNTAX SEQUENCE OF NlIfVoiceEntry
    ACCESS not-accessible
    STATUS mandatory
    DESCRIPTION "A Table to define Voice interfaces over frame relay."
    ::= { nlIfVoiceInterfaces 1 }

nlIfVoiceEntry OBJECT-TYPE
    SYNTAX NlIfVoiceEntry
    ACCESS not-accessible
    STATUS mandatory
    DESCRIPTION
            "A Voice Interface entry containing objects relating
            to the interface that are configurable by the user."
    INDEX { nlIfVoiceInterface }
    ::= { nlIfVoiceTable 1 }

NlIfVoiceEntry ::=
    SEQUENCE {
        nlIfVoiceInterface          INTEGER,
        nlIfVoicePeerNodeType       INTEGER,
        nlIfVoicePeerNodeNumber     INTEGER,
        nlIfVoicePeerNodePort       INTEGER,
        nlIfVoiceLocalNodeNumber    INTEGER,
        nlIfVoiceLocalNodePort      INTEGER,
        nlIfVoiceFrameRelayRlp      INTEGER,
        nlIfVoiceFrameRelayPort     INTEGER,
        nlIfVoiceFrameRelayDLCI     INTEGER,
        nlIfVoiceEnableFragment     INTEGER,
        nlIfVoiceRowStatus          RowStatus
    }

nlIfVoiceInterface OBJECT-TYPE
    SYNTAX INTEGER (1..129)
    ACCESS read-only
    STATUS mandatory
    DESCRIPTION "The interface number which uniquely identifies the
                interface to which this entry is applicable. The
                interface identified by a particular value of this
                number is NOT the same interface as defined by the
                same value of ifIndex."
    ::= { nlIfVoiceEntry 1 }

nlIfVoicePeerNodeType OBJECT-TYPE
    SYNTAX INTEGER {
                netlink (1),
                act (2)
                }
    ACCESS read-write
    STATUS mandatory
    DESCRIPTION "The node type for the node at the remote end of the
                frame relay connection."
    DEFVAL { act }
    ::= { nlIfVoiceEntry 2 }

nlIfVoicePeerNodeNumber OBJECT-TYPE
    SYNTAX INTEGER (1..61)
    ACCESS read-write
    STATUS mandatory
    DESCRIPTION "The node number of the remote device."
    DEFVAL { 1 }
    ::= { nlIfVoiceEntry 3 }

nlIfVoicePeerNodePort OBJECT-TYPE
    SYNTAX INTEGER (1..17)
    ACCESS read-write
    STATUS mandatory
    DESCRIPTION "The voice port on the remote device."
    DEFVAL { 1 }
    ::= { nlIfVoiceEntry 4 }

nlIfVoiceLocalNodeNumber OBJECT-TYPE
    SYNTAX INTEGER (1..61)
    ACCESS read-write
    STATUS mandatory
    DESCRIPTION "The node number of the local device."
    DEFVAL { 1 }
    ::= { nlIfVoiceEntry 5 }

nlIfVoiceLocalNodePort OBJECT-TYPE
    SYNTAX INTEGER (1..17)
    ACCESS read-write
    STATUS mandatory
    DESCRIPTION "The voice port on the local device."
    DEFVAL { 1 }
    ::= { nlIfVoiceEntry 6 }

nlIfVoiceFrameRelayRlp OBJECT-TYPE
    SYNTAX INTEGER (1..8)
    ACCESS read-write
    STATUS mandatory
    DESCRIPTION "The RLP of the logical interface of this end of the frame
                relay link."
    DEFVAL { 1 }
    ::= { nlIfVoiceEntry 7 }

nlIfVoiceFrameRelayPort OBJECT-TYPE
    SYNTAX INTEGER (1..8)
    ACCESS read-write
    STATUS mandatory
    DESCRIPTION "The port of the logical interface of this end of the frame
                relay link."
    DEFVAL { 1 }
    ::= { nlIfVoiceEntry 8 }

nlIfVoiceFrameRelayDLCI OBJECT-TYPE
    SYNTAX INTEGER (16..991)
    ACCESS read-write
    STATUS mandatory
    DESCRIPTION "The DLCI of the logical interface of this end of the frame
                relay link."
    DEFVAL { 16 }
    ::= { nlIfVoiceEntry 9 }

nlIfVoiceEnableFragment OBJECT-TYPE
    SYNTAX  INTEGER {
                no (1),
                yes (2)
                }
    ACCESS  read-write
    STATUS  mandatory
    DESCRIPTION ""
    DEFVAL { no }
    ::= { nlIfVoiceEntry 10 }

nlIfVoiceRowStatus OBJECT-TYPE
    SYNTAX  RowStatus
    ACCESS  read-write
    STATUS  mandatory
    DESCRIPTION
            "This variable is used to manage the creation and deletion
            of conceptual rows in the noIfVoiceTable and follows the
            SNMPv2 RowStatus conventions by supporting the following values:

                 - `active', which indicates that the conceptual row is
                available for use by the managed device.  For a management
                protocol set operation, a genErr response is returned when
                the row does not exist.

                 - `createAndGo', which is supplied by a management
                 station wishing to create a new instance of a
                 conceptual row and to have its status automatically set
                 to active, making it available for use by the managed
                 device.  For a management protocol set operation, a
                 genErr response is returned when the row already exists.

                 - `destroy', which is supplied by a management station
                 wishing to delete all of the instances associated with
                 an existing conceptual row.

            Note that all of the above values may be specified in a
            management protocol set operation, and only the 'active'
            value will be returned in response to a management protocol
            retrieval operation.  For a management protocol set operation,
            if other variable bindings are included in the same PDU, then
            a genErr response is returned."
    ::= { nlIfVoiceEntry 11 }

-- **************************
-- *  THE SUBSCRIBER GROUP  *
-- **************************

subscriber OBJECT IDENTIFIER ::=    { local 5 }

--
--  The Netlink Local Subscriber Table
--

nlLocalSubscriberTable OBJECT-TYPE
	SYNTAX SEQUENCE OF NlLocalSubscriberEntry
	ACCESS not-accessible
	STATUS mandatory
	DESCRIPTION "A Table to define each local subscriber."
	::= { subscriber 1 }

nlLocalSubscriberEntry OBJECT-TYPE
	SYNTAX NlLocalSubscriberEntry
	ACCESS not-accessible
	STATUS mandatory
	DESCRIPTION "A Local Subscriber entry containing objects relating
	to local subscribers."
	INDEX { nlLocalSubscriberId }
	::= { nlLocalSubscriberTable 1 }

NlLocalSubscriberEntry ::=
	SEQUENCE {
		nlLocalSubscriberId					NlSubscriberAddress,
		nlLocalSubscriberName				DisplayString,
		nlLocalSubscriberAlgorithm			INTEGER,
		nlLocalSubscriberSystematicRedirect	INTEGER,
		nlLocalSubscriberRedirectBusy		INTEGER,
		nlLocalSubscriberRedirectOO			INTEGER,
		nlLocalSubscriberPriority			INTEGER,
		nlLocalSubscriberRowStatus			RowStatus
	}

nlLocalSubscriberId OBJECT-TYPE
	SYNTAX 	NlSubscriberAddress
	ACCESS read-only
	STATUS mandatory
	DESCRIPTION "The Subscriber ID.  A valid subscriber ID is a string of
		numeric digits represented by their ASCII equivalents.  The
		ASCII equivalents of the wildcard characters '*' and '?' are 
		also allowed.  A '*' is a wildcard that matches any number of 
		digits, including zero.	A '?' is a wildcard that matches any single digit."
	::= { nlLocalSubscriberEntry 1 }

nlLocalSubscriberName OBJECT-TYPE
	SYNTAX DisplayString (SIZE (0..31))
	ACCESS read-only
	STATUS mandatory
	DESCRIPTION "The Subscriber name.  The subscriber name is not accessible from 
		     SNMP, and a blank string is always returned."
	::= { nlLocalSubscriberEntry 2 }

nlLocalSubscriberAlgorithm OBJECT-TYPE
	SYNTAX INTEGER {
		round-robin(1),
		line-failed(2),
		line-busy(3),
		least-lcn(4)
		}
	ACCESS read-write
	STATUS mandatory
	DESCRIPTION "The Subscriber routing algorithm.
			The following 4 types of routing algorithms are supported.
			1 - round robin selects ports specified cyclicly in numerical
			order according to the list of Redirection addresses. If the port
			is unreachable or congested, the call request is sent to the next
			port.
			2. Alternate Route on Line Failure - selects the first port
			 not in a failed state. If a connection is not made, the call
			will be cleared even if other ports are available.
			3. Alternate Route on Line Busy - selects the first port
			that has LCN's available (not busy). If a port has failed,
			the next available port is selected.
			4. Least LCN with throughput selects the line with the minumum
			loading, calculated by weight and number of LCN's in use.

			If use of a routing algorithm is not desired, accept the default
			and specify only one routing path."
	DEFVAL { round-robin }
	::= { nlLocalSubscriberEntry 3 }

nlLocalSubscriberSystematicRedirect OBJECT-TYPE
	SYNTAX INTEGER {
		no(1),
		yes(2)
	}
	ACCESS read-write
	STATUS mandatory
	DESCRIPTION "Systematic Redirection."
    DEFVAL { no }	
	::= { nlLocalSubscriberEntry 4 }

nlLocalSubscriberRedirectBusy OBJECT-TYPE
	SYNTAX INTEGER {
		no(1),
		yes(2)
	}
	ACCESS read-write
	STATUS mandatory
	DESCRIPTION "Redirect calls according to Redirection Addresses if the
		primary subscriber device is busy."
    DEFVAL { no }	
	::= { nlLocalSubscriberEntry 5 }

nlLocalSubscriberRedirectOO OBJECT-TYPE
	SYNTAX INTEGER {
		no(1),
		yes(2)
	}
	ACCESS read-write
	STATUS mandatory
	DESCRIPTION "Redirect calls according to Redirection Addresses if the
		primary subscriber device is out of order."
    DEFVAL { no }	
	::= { nlLocalSubscriberEntry 6 }

nlLocalSubscriberPriority OBJECT-TYPE
	SYNTAX INTEGER (0..9)
	ACCESS read-write
	STATUS mandatory
	DESCRIPTION "Allows setting a priority for traffic within the node."
    DEFVAL { 0 }	
	::= { nlLocalSubscriberEntry 7 }

nlLocalSubscriberRowStatus OBJECT-TYPE
	SYNTAX      RowStatus
	ACCESS read-write
	STATUS mandatory
	DESCRIPTION 
            "This variable is used to manage the creation and deletion
            of conceptual rows in the nlLocalSubscriberTable and follows the
            SNMPv2 RowStatus conventions by supporting the following values:

                 - `active', which indicates that the conceptual row is
                available for use by the managed device.  For a management
                protocol set operation, a genErr response is returned when
                the row does not exist.

                 - `createAndGo', which is supplied by a management
                 station wishing to create a new instance of a
                 conceptual row and to have its status automatically set
                 to active, making it available for use by the managed
                 device.  For a management protocol set operation, a
                 genErr response is returned when the row already exists.

                 - `destroy', which is supplied by a management station
                 wishing to delete all of the instances associated with
                 an existing conceptual row.

            Note that all of the above values may be specified in a
            management protocol set operation, and only the 'active'
            value will be returned in response to a management protocol
            retrieval operation.  For a management protocol set operation,
            if other variable bindings are included in the same PDU, then
            a genErr response is returned."

	::= { nlLocalSubscriberEntry 8 }

-- Routing Paths Table.

nlLocalSubscriberRouteTable OBJECT-TYPE
	SYNTAX SEQUENCE OF NlLocalSubscriberRouteEntry
	ACCESS not-accessible
	STATUS mandatory
	DESCRIPTION "A Table to define local subscriber route paths."
	::= { subscriber 2 }

nlLocalSubscriberRouteEntry OBJECT-TYPE
	SYNTAX NlLocalSubscriberRouteEntry
	ACCESS not-accessible
	STATUS mandatory
	DESCRIPTION "A Local Subscriber Route entry containing objects relating
	to local subscriber routes."
	INDEX { nlLocalSubscriberId, nlLocalSubscriberRouteIndex}
	::= { nlLocalSubscriberRouteTable 1 }

NlLocalSubscriberRouteEntry ::=
	SEQUENCE {
		nlLocalSubscriberRouteIndex		INTEGER,
		nlLocalSubscriberRouteConf		INTEGER,
		nlLocalSubscriberRouteLP		INTEGER,
		nlLocalSubscriberRoutePort		INTEGER,
		nlLocalSubscriberRouteRowStatus	RowStatus
	}

nlLocalSubscriberRouteIndex OBJECT-TYPE
	SYNTAX INTEGER (1..8)
	ACCESS read-only
	STATUS mandatory
	DESCRIPTION "Route path index for a specific subscriber route path."
	::= { nlLocalSubscriberRouteEntry 1 }

nlLocalSubscriberRouteConf OBJECT-TYPE
	SYNTAX INTEGER  {
		no(1),
		yes(2)
	}
	ACCESS read-only
	STATUS mandatory
	DESCRIPTION "Flag to indicate if the LP/port routing path to the
		subscriber device is configured or not. This object is read-
		only. The route is always configured for an entry in the table."
	::= { nlLocalSubscriberRouteEntry 2 }

nlLocalSubscriberRouteLP OBJECT-TYPE
	SYNTAX INTEGER  
	ACCESS read-write
	STATUS mandatory
	DESCRIPTION "Instance of the LP that makes up the routing path"
	::= { nlLocalSubscriberRouteEntry 3 }

nlLocalSubscriberRoutePort OBJECT-TYPE
	SYNTAX INTEGER  
	ACCESS read-write
	STATUS mandatory
	DESCRIPTION "Instance of the port that makes up the routing path"
	::= { nlLocalSubscriberRouteEntry 4 }

nlLocalSubscriberRouteRowStatus OBJECT-TYPE
	SYNTAX      RowStatus
	ACCESS read-write
	STATUS mandatory
	DESCRIPTION 
            "This variable is used to manage the creation and deletion
            of conceptual rows in the nlLocalSubscriberRouteTable and follows the
            SNMPv2 RowStatus conventions by supporting the following values:

                 - `active', which indicates that the conceptual row is
                available for use by the managed device.  For a management
                protocol set operation, a genErr response is returned when
                the row does not exist.

                 - `createAndGo', which is supplied by a management
                 station wishing to create a new instance of a
                 conceptual row and to have its status automatically set
                 to active, making it available for use by the managed
                 device.  For a management protocol set operation, a
                 genErr response is returned when the row already exists.

                 - `destroy', which is supplied by a management station
                 wishing to delete all of the instances associated with
                 an existing conceptual row.

            Note that all of the above values may be specified in a
            management protocol set operation, and only the 'active'
            value will be returned in response to a management protocol
            retrieval operation.  For a management protocol set operation,
            if other variable bindings are included in the same PDU, then
            a genErr response is returned."

	::= { nlLocalSubscriberRouteEntry 5 }

--- Redirection Address table.

nlLocalSubscriberRedirTable OBJECT-TYPE
	SYNTAX SEQUENCE OF NlLocalSubscriberRedirEntry
	ACCESS not-accessible
	STATUS mandatory
	DESCRIPTION "A Table to list local subscriber redirection addresses."
	::= { subscriber 3 }

nlLocalSubscriberRedirEntry OBJECT-TYPE
	SYNTAX NlLocalSubscriberRedirEntry
	ACCESS not-accessible
	STATUS mandatory
	DESCRIPTION "A Local Subscriber Redirection Address entry containing
	objects relating to local subscriber redirection addresses."
	INDEX { nlLocalSubscriberId, nlLocalSubscriberRedirIndex }
	::= { nlLocalSubscriberRedirTable 1 }

NlLocalSubscriberRedirEntry ::=
	SEQUENCE {
		nlLocalSubscriberRedirIndex		INTEGER,
		nlLocalSubscriberRedirAddr		NlSubscriberAddress,
		nlLocalSubscriberRedirRowStatus	RowStatus
	}

nlLocalSubscriberRedirIndex OBJECT-TYPE
	SYNTAX INTEGER (1..5)
	ACCESS read-only
	STATUS mandatory
	DESCRIPTION "Redirection entry index for a local subscriber."
	::= { nlLocalSubscriberRedirEntry 1 }

nlLocalSubscriberRedirAddr OBJECT-TYPE
	SYNTAX NlSubscriberAddress
	ACCESS read-write
	STATUS mandatory
	DESCRIPTION "Subscriber redirection address."
	::= { nlLocalSubscriberRedirEntry 2 }

nlLocalSubscriberRedirRowStatus OBJECT-TYPE
	SYNTAX      RowStatus
	ACCESS read-write
	STATUS mandatory
	DESCRIPTION 
            "This variable is used to manage the creation and deletion
            of conceptual rows in the nlLocalSubscriberRedirTable and follows the
            SNMPv2 RowStatus conventions by supporting the following values:

                 - `active', which indicates that the conceptual row is
                available for use by the managed device.  For a management
                protocol set operation, a genErr response is returned when
                the row does not exist.

                 - `createAndGo', which is supplied by a management
                 station wishing to create a new instance of a
                 conceptual row and to have its status automatically set
                 to active, making it available for use by the managed
                 device.  For a management protocol set operation, a
                 genErr response is returned when the row already exists.

                 - `destroy', which is supplied by a management station
                 wishing to delete all of the instances associated with
                 an existing conceptual row.

            Note that all of the above values may be specified in a
            management protocol set operation, and only the 'active'
            value will be returned in response to a management protocol
            retrieval operation.  For a management protocol set operation,
            if other variable bindings are included in the same PDU, then
            a genErr response is returned."
	::= { nlLocalSubscriberRedirEntry 3 }

-- ********************
-- *  THE LLC2 GROUP  *
-- ********************

llc2 OBJECT IDENTIFIER ::=    { local 6 }

--
--  The Netlink LLC2 Host Table
--

nlLlc2HostTable OBJECT-TYPE
	SYNTAX SEQUENCE OF NlLlc2HostEntry
	ACCESS not-accessible
	STATUS mandatory
	DESCRIPTION "A Table to define LLC2 host entries."
	::= { llc2 1 }

nlLlc2HostEntry OBJECT-TYPE
	SYNTAX NlLlc2HostEntry
	ACCESS not-accessible
	STATUS mandatory
	DESCRIPTION "An LLC2 Host entry containing objects relating to
	LLC2 hosts."
	INDEX { nlLlc2HostGroup, nlLlc2HostIndex }
	::= { nlLlc2HostTable 1 }

NlLlc2HostEntry ::=
	SEQUENCE {
		nlLlc2HostIndex					INTEGER,
		nlLlc2HostMACAddress			MacAddress,
		nlLlc2HostSessionType			INTEGER,
		nlLlc2HostT1ReplyTimer			TimeInterval,
		nlLlc2HostT2RecvAckTimer		TimeInterval,
		nlLlc2HostTiInactivityTimer		TimeInterval,
		nlLlc2HostN3NumberLPDUs			INTEGER,
		nlLlc2HostTwNumberOutstanding	INTEGER,
		nlLlc2HostN2ExpiredT1LPDUCount	INTEGER,
		nlLlc2HostPriority				INTEGER,
		nlLlc2HostBAG					INTEGER,
		nlLlc2HostRoutingSubscriberId	NlSubscriberAddress,
		nlLlc2HostSrcMACAddressMask		MacAddress,
		nlLlc2HostAccess				INTEGER,
		nlLlc2HostRowStatus				RowStatus,
		nlLlc2HostInterface				INTEGER,
		nlLlc2HostGroup				INTEGER
	}

nlLlc2HostIndex OBJECT-TYPE
	SYNTAX INTEGER	(1..251)
	ACCESS read-only
	STATUS mandatory
	DESCRIPTION "LLC2 Host Index"
	::= { nlLlc2HostEntry 1 }

nlLlc2HostMACAddress OBJECT-TYPE
	SYNTAX MacAddress
	ACCESS read-write
	STATUS mandatory
	DESCRIPTION "The LLC2 Host MAC Address."
	DEFVAL { '400000000001'H }    -- 40:00:00:00:00:01
	::= { nlLlc2HostEntry 2 }

nlLlc2HostSessionType OBJECT-TYPE
	SYNTAX INTEGER {
		originated(1),
		terminated(2)
		}
	ACCESS read-write
	STATUS mandatory
	DESCRIPTION "The mode in which the Host is operating"
	DEFVAL { terminated }
	::= { nlLlc2HostEntry 3 }

nlLlc2HostT1ReplyTimer OBJECT-TYPE
	SYNTAX TimeInterval (1..250)
	ACCESS read-write
	STATUS mandatory
	DESCRIPTION "Reply Timer used to detect a failure of the Remote node."
	DEFVAL { 10 }
	::= { nlLlc2HostEntry 4 }

nlLlc2HostT2RecvAckTimer OBJECT-TYPE
	SYNTAX TimeInterval (100..5000)
	ACCESS read-write
	STATUS mandatory
	DESCRIPTION "Receive Ack Timer used to delay sending an
		acknowledgement of a received information LPDU."
	DEFVAL { 100 }
	::= { nlLlc2HostEntry 5 }

nlLlc2HostTiInactivityTimer OBJECT-TYPE
	SYNTAX TimeInterval (1..50)
	ACCESS read-write
	STATUS mandatory
	DESCRIPTION "Timer used to detect inoperative condition of the
		remote link station or transmission medium."
	DEFVAL { 30 }
	::= { nlLlc2HostEntry 6 }

nlLlc2HostN3NumberLPDUs OBJECT-TYPE
	SYNTAX INTEGER (1..127)
	ACCESS read-write
	STATUS mandatory
	DESCRIPTION "The number of Information LPDUs that need to be received
		before an acknowledgement is sent."
	DEFVAL { 3 }
	::= { nlLlc2HostEntry 7 }

nlLlc2HostTwNumberOutstanding OBJECT-TYPE
	SYNTAX INTEGER (1..127)
	ACCESS read-write
	STATUS mandatory
	DESCRIPTION "Maximum number of sequentially numbered information
		LPDUs that can be outstanding at any time."
	DEFVAL { 7 }
	::= { nlLlc2HostEntry 8 }

nlLlc2HostN2ExpiredT1LPDUCount OBJECT-TYPE
	SYNTAX INTEGER (0..255)
	ACCESS read-write
	STATUS mandatory
	DESCRIPTION "Maximum number of LPDU retransmissions occur following
		the expiration of Timer T1."
	DEFVAL { 8 }
	::= { nlLlc2HostEntry 9 }

nlLlc2HostPriority OBJECT-TYPE
	SYNTAX INTEGER (0..9)
	ACCESS read-write
	STATUS mandatory
	DESCRIPTION "Traffic priorities within the node."
	DEFVAL { 0 }
	::= { nlLlc2HostEntry 10 }

nlLlc2HostBAG OBJECT-TYPE
	SYNTAX INTEGER (1..16)
	ACCESS read-only
	STATUS mandatory
	DESCRIPTION "Bandwidth Allocation group to which the LLC2 Host belongs.
		This object is read-only. Bandwidth allocation groups do not apply
		to LLC2 hosts."
	DEFVAL { 1 }
	::= { nlLlc2HostEntry 11 }

nlLlc2HostRoutingSubscriberId OBJECT-TYPE
	SYNTAX NlSubscriberAddress
	ACCESS read-write
	STATUS mandatory
	DESCRIPTION "LLC2 hosts Routing Subscriber Id"
	::= { nlLlc2HostEntry 12 }

nlLlc2HostSrcMACAddressMask OBJECT-TYPE
	SYNTAX MacAddress
	ACCESS read-write
	STATUS mandatory
	DESCRIPTION "LLC2 Host's Source MAC Address Mask"
	DEFVAL { '000000000000'H }    -- 00:00:00:00:00:00
	::= { nlLlc2HostEntry 13 }

nlLlc2HostAccess OBJECT-TYPE
	SYNTAX INTEGER {
	 lan(1),
	 frameRelay(2),
	 tokenRing(3),
	 ethernet(4),
	 all(5),
	 not-applicable(6)
	}
	ACCESS read-only
	STATUS mandatory
	DESCRIPTION "Specifies different type(s) of interface(s) that can be
		used for connections to a terminated host session."
	DEFVAL { not-applicable }
	::= { nlLlc2HostEntry 14 }

nlLlc2HostRowStatus OBJECT-TYPE
	SYNTAX RowStatus
	ACCESS read-write
	STATUS mandatory
	DESCRIPTION "Row status convention for LLC2 Host entry."
	::= { nlLlc2HostEntry 15 }

nlLlc2HostInterface OBJECT-TYPE
	SYNTAX INTEGER
	ACCESS read-only
	STATUS mandatory
	DESCRIPTION "LLC2 interface number associated with this host entry, always
	300 for non-FRX7000."
	DEFVAL { 300 }
	::= { nlLlc2HostEntry 16 }

nlLlc2HostGroup OBJECT-TYPE
	SYNTAX INTEGER (1..4)
	ACCESS read-only
	STATUS mandatory
	DESCRIPTION "Traffic group associated with LLC2 interface, always 1 for
	non-FRX7000."
	::= { nlLlc2HostEntry 17 }

-- LLC2 Terminated Host Connection Table.
--
nlLlc2TermConnectionTable OBJECT-TYPE
        SYNTAX SEQUENCE OF NlLlc2TermConnectionEntry
        ACCESS not-accessible
        STATUS mandatory
        DESCRIPTION "A Table to describe LLC2 Terminated Host Connections."
        ::= { llc2 2 }

nlLlc2TermConnectionEntry OBJECT-TYPE
	SYNTAX NlLlc2TermConnectionEntry
        ACCESS not-accessible
        STATUS mandatory
	DESCRIPTION "An LLC2 Terminated Host Connection entry containing
	objects relating to LLC2 terminated host connections."
        INDEX { nlLlc2HostGroup, nlLlc2HostIndex, nlLlc2TermConnectionSequence }
        ::= { nlLlc2TermConnectionTable 1 }

NlLlc2TermConnectionEntry ::=
	SEQUENCE {
		nlLlc2TermConnectionSequence			INTEGER,
		nlLlc2TermConnectionHSAP				INTEGER,
		nlLlc2TermConnectionLocalSubscriberId	NlSubscriberAddress,
		nlLlc2TermConnectionRemoteSubscriberId	NlSubscriberAddress,
		nlLlc2TermConnectionRowStatus			RowStatus
	}

nlLlc2TermConnectionSequence OBJECT-TYPE
	SYNTAX INTEGER (1..16)
	ACCESS read-only
	STATUS mandatory
	DESCRIPTION "LLC2 Host connection Sequence number"
	::= { nlLlc2TermConnectionEntry 1 }

nlLlc2TermConnectionHSAP OBJECT-TYPE
	SYNTAX INTEGER (4..254)
	ACCESS read-write
	STATUS mandatory
	DESCRIPTION "Service Access point used to connect to the Host"
	DEFVAL { 4 }
	::= { nlLlc2TermConnectionEntry 2 }

nlLlc2TermConnectionLocalSubscriberId OBJECT-TYPE
	SYNTAX NlSubscriberAddress
	ACCESS read-write
	STATUS mandatory
	DESCRIPTION "LLC2 Host Connection's Local Subscriber Id"
	::= { nlLlc2TermConnectionEntry 3 }

nlLlc2TermConnectionRemoteSubscriberId OBJECT-TYPE
	SYNTAX NlSubscriberAddress
	ACCESS read-write
	STATUS mandatory
	DESCRIPTION "LLC2 Host Connection's Remote Subscriber Id"
	::= { nlLlc2TermConnectionEntry 4 }

nlLlc2TermConnectionRowStatus OBJECT-TYPE
	SYNTAX RowStatus
	ACCESS read-write
	STATUS mandatory
	DESCRIPTION 
            "This variable is used to manage the creation and deletion
            of conceptual rows in the nlLlc2TermConnectionTable and follows the
            SNMPv2 RowStatus conventions by supporting the following values:

                 - `active', which indicates that the conceptual row is
                available for use by the managed device.  For a management
                protocol set operation, a genErr response is returned when
                the row does not exist.

                 - `createAndGo', which is supplied by a management
                 station wishing to create a new instance of a
                 conceptual row and to have its status automatically set
                 to active, making it available for use by the managed
                 device.  For a management protocol set operation, a
                 genErr response is returned when the row already exists.

                 - `destroy', which is supplied by a management station
                 wishing to delete all of the instances associated with
                 an existing conceptual row.

            Note that all of the above values may be specified in a
            management protocol set operation, and only the 'active'
            value will be returned in response to a management protocol
            retrieval operation.  For a management protocol set operation,
            if other variable bindings are included in the same PDU, then
            a genErr response is returned."
	::= { nlLlc2TermConnectionEntry 5 }

-- LLC2 Originated Host Connection Table.
--
nlLlc2OrigConnectionTable OBJECT-TYPE
        SYNTAX SEQUENCE OF NlLlc2OrigConnectionEntry
        ACCESS not-accessible
        STATUS mandatory
        DESCRIPTION "A Table to describe LLC2 Originated Host Connections."
        ::= { llc2 3 }

nlLlc2OrigConnectionEntry OBJECT-TYPE
	SYNTAX NlLlc2OrigConnectionEntry
        ACCESS not-accessible
        STATUS mandatory
	DESCRIPTION "An LLC2 Originated Host Connection entry containing
	objects relating to LLC2 originated host connections."
        INDEX { nlLlc2HostGroup, nlLlc2HostIndex, nlLlc2OrigConnectionSequence }
        ::= { nlLlc2OrigConnectionTable 1 }

NlLlc2OrigConnectionEntry ::=
	SEQUENCE {
		nlLlc2OrigConnectionSequence			INTEGER,
		nlLlc2OrigConnectionHSAP				INTEGER,
		nlLlc2OrigConnectionType				INTEGER,
		nlLlc2OrigConnectionLocalSubscriberId	NlSubscriberAddress,
		nlLlc2OrigConnectionRemoteSubscriberId	NlSubscriberAddress,
		nlLlc2OrigConnectionIDBLK				INTEGER,
		nlLlc2OrigConnectionIDNUM				INTEGER,
		nlLlc2OrigConnectionMAXDATA				INTEGER,
		nlLlc2OrigConnectionMAXIN				INTEGER,
		nlLlc2OrigConnectionRowStatus			RowStatus
	}

nlLlc2OrigConnectionSequence OBJECT-TYPE
	SYNTAX INTEGER (1..16)
	ACCESS read-only
	STATUS mandatory
	DESCRIPTION "LLC2 Host connection Sequence number"
	::= { nlLlc2OrigConnectionEntry 1 }

nlLlc2OrigConnectionHSAP OBJECT-TYPE
	SYNTAX INTEGER (4..254)
	ACCESS read-write
	STATUS mandatory
	DESCRIPTION "Service Access point used to connect to the Host"
	DEFVAL { 4 }
	::= { nlLlc2OrigConnectionEntry 2 }

nlLlc2OrigConnectionType OBJECT-TYPE
	SYNTAX INTEGER {
		sdlc(1),
		llc2(2)
		} 
	ACCESS read-write
	STATUS mandatory
	DESCRIPTION "Specifies Remote subscriber device type"
	DEFVAL { llc2 }
	::= { nlLlc2OrigConnectionEntry 3 }

nlLlc2OrigConnectionLocalSubscriberId OBJECT-TYPE
	SYNTAX NlSubscriberAddress
	ACCESS read-write
	STATUS mandatory
	DESCRIPTION "LLC2 Host Connection's Local Subscriber Id"
	::= { nlLlc2OrigConnectionEntry 4 }

nlLlc2OrigConnectionRemoteSubscriberId OBJECT-TYPE
	SYNTAX NlSubscriberAddress
	ACCESS read-write
	STATUS mandatory
	DESCRIPTION "LLC2 Host Connection's Remote Subscriber Id"
	::= { nlLlc2OrigConnectionEntry 5 }

nlLlc2OrigConnectionIDBLK OBJECT-TYPE
	SYNTAX INTEGER 
	ACCESS read-only
	STATUS mandatory
	DESCRIPTION "This field is obsolete"
	DEFVAL { 0 }
	::= { nlLlc2OrigConnectionEntry 6 }

nlLlc2OrigConnectionIDNUM OBJECT-TYPE
	SYNTAX INTEGER 
	ACCESS read-only
	STATUS mandatory
	DESCRIPTION "This field is obsolete"
	DEFVAL { 0 }
	::= { nlLlc2OrigConnectionEntry 7 }

nlLlc2OrigConnectionMAXDATA OBJECT-TYPE
	SYNTAX INTEGER 
	ACCESS read-only
	STATUS mandatory
	DESCRIPTION "This field is obsolete"
	DEFVAL { 0 }
	::= { nlLlc2OrigConnectionEntry 8 }

nlLlc2OrigConnectionMAXIN OBJECT-TYPE
	SYNTAX INTEGER 
	ACCESS read-only
	STATUS mandatory
	DESCRIPTION "This field is obsolete"
	DEFVAL { 0 }
	::= { nlLlc2OrigConnectionEntry 9 }

nlLlc2OrigConnectionRowStatus OBJECT-TYPE
	SYNTAX RowStatus
	ACCESS read-write
	STATUS mandatory
	DESCRIPTION 
            "This variable is used to manage the creation and deletion
            of conceptual rows in the nlLlc2OrigConnectionTable and follows the
            SNMPv2 RowStatus conventions by supporting the following values:

                 - `active', which indicates that the conceptual row is
                available for use by the managed device.  For a management
                protocol set operation, a genErr response is returned when
                the row does not exist.

                 - `createAndGo', which is supplied by a management
                 station wishing to create a new instance of a
                 conceptual row and to have its status automatically set
                 to active, making it available for use by the managed
                 device.  For a management protocol set operation, a
                 genErr response is returned when the row already exists.

                 - `destroy', which is supplied by a management station
                 wishing to delete all of the instances associated with
                 an existing conceptual row.

            Note that all of the above values may be specified in a
            management protocol set operation, and only the 'active'
            value will be returned in response to a management protocol
            retrieval operation.  For a management protocol set operation,
            if other variable bindings are included in the same PDU, then
            a genErr response is returned."
	::= { nlLlc2OrigConnectionEntry 10 }

nlLlc2NextHostNumber OBJECT-TYPE
        SYNTAX INTEGER
        ACCESS read-only
        STATUS mandatory
        DESCRIPTION "The host number to be used for the next created
	host record, always 1 on non-FRX7000."
	    DEFVAL { 1 }
        ::= { llc2 4 }

-- **********************
-- *  THE STATUS GROUP  *
-- **********************

status  OBJECT IDENTIFIER ::= 	{ local 7 }

--
--  The Port Pin Status Table
--

pinStatusTable OBJECT-TYPE
	SYNTAX SEQUENCE OF PortPinEntry
	ACCESS not-accessible
	STATUS mandatory
	DESCRIPTION "A Table to describe the status of each pin on a 
	physical port. This table is indexed by RLP and Port"
	::= { status 4 }

portPinEntry OBJECT-TYPE
	SYNTAX PortPinEntry
	ACCESS not-accessible
	STATUS mandatory
	DESCRIPTION "A port pin entry containing objects relating to ports."
	INDEX { portPinRlp,portPinPort }
	::= { pinStatusTable 1 }

PortPinEntry ::=
	SEQUENCE {
		portPinRlp
			INTEGER,
		portPinPort
			INTEGER,
		portPinStatus
			OCTET STRING
	}

portPinRlp OBJECT-TYPE
	SYNTAX INTEGER
	ACCESS read-only
	STATUS mandatory
	DESCRIPTION "The RLP number on the node"
	::= { portPinEntry 1 }

portPinPort OBJECT-TYPE
	SYNTAX INTEGER
	ACCESS read-only
	STATUS mandatory
	DESCRIPTION "The Port number on the RLP. Port numbers 0-7 are
	known to be physical ports."
	::= { portPinEntry 2 }

portPinStatus OBJECT-TYPE
	SYNTAX OCTET STRING
	ACCESS read-only
	STATUS mandatory
	DESCRIPTION "The status of all pins for this physical port. There
	is one octet value for each of the pins. Each octet value is defined
	as follows:
		00 = unknown
		01 = active
		02 = inactive
		03 = unused "
	::= { portPinEntry 3 }

-- **************************
-- *  THE STATISTICS GROUP  *
-- **************************

statistics OBJECT IDENTIFIER ::= 	{ local 8 }
statGroup OBJECT IDENTIFIER ::=   	{ statistics 1 }

--
-- The RLP Statistics group define the RLPStats Table
--

rlpStatsTable OBJECT-TYPE
	SYNTAX SEQUENCE OF RlpStatsEntry
	ACCESS not-accessible
	STATUS mandatory
	DESCRIPTION "A Table to describe Statistics on each RLP"
	::= { statGroup 2 }

rlpStatsEntry OBJECT-TYPE
	SYNTAX RlpStatsEntry
	ACCESS not-accessible
	STATUS mandatory
	DESCRIPTION "An RLP statistics entry containing objects relating
	to RLP statistics."
	INDEX { rlpStatsIndex }
	::= { rlpStatsTable 1 }

RlpStatsEntry ::=
	SEQUENCE {
		rlpStatsIndex
			INTEGER,
		rlpStatsUsedBuffers
			Counter,
		rlpStatsQMessages
			Counter,
		rlpStatsInFrames
			Counter,
		rlpStatsOutFrames
			Counter,
		rlpStatsFrameRejects
			Counter,
		rlpStatsFrameRetransmits
			Counter
	}
rlpStatsIndex OBJECT-TYPE
	SYNTAX INTEGER
	ACCESS read-only
	STATUS mandatory
	DESCRIPTION "The RLP number"
	::= { rlpStatsEntry 1 }

rlpStatsQMessages OBJECT-TYPE
	SYNTAX Counter
	ACCESS read-only
	STATUS mandatory
	DESCRIPTION "The number of frames queued on the RLP"
	::= { rlpStatsEntry 2 }

rlpStatsUsedBuffers OBJECT-TYPE
	SYNTAX Counter
	ACCESS read-only
	STATUS mandatory
	DESCRIPTION "The percentage of total buffers available being used at
	the moment of inquiry"
	::= { rlpStatsEntry 3 }

rlpStatsInFrames OBJECT-TYPE
	SYNTAX Counter
	ACCESS read-only
	STATUS mandatory
	DESCRIPTION "The number of frames received."
	::= { rlpStatsEntry 4 }

rlpStatsOutFrames OBJECT-TYPE
	SYNTAX Counter
	ACCESS read-only
	STATUS mandatory
	DESCRIPTION "The number of frames transmitted."
	::= { rlpStatsEntry 5 }

rlpStatsFrameRejects OBJECT-TYPE
	SYNTAX Counter
	ACCESS read-only
	STATUS mandatory
	DESCRIPTION "The number of frames rejected."
	::= { rlpStatsEntry 6 }

rlpStatsFrameRetransmits OBJECT-TYPE
	SYNTAX Counter
	ACCESS read-only
	STATUS mandatory
	DESCRIPTION "The number of frames retransmitted . If
	this value is consistently greater than zero and there are no other
	problems, then increase the retransmission parameter."
	::= { rlpStatsEntry 7 }

--
-- The Port Statistics group define the portStats Table
--

portStatsTable OBJECT-TYPE
	SYNTAX SEQUENCE OF PortStatsEntry
	ACCESS not-accessible
	STATUS mandatory
	DESCRIPTION "A Table to describe Statistics on each RLP"
	::= { statGroup 3 }

portStatsEntry OBJECT-TYPE
	SYNTAX PortStatsEntry
	ACCESS not-accessible
	STATUS mandatory
	DESCRIPTION "A port statistics entry containing objects relating
	to port statistics."
	INDEX { portStatsRlpIndex, portStatsIndex }
	::= { portStatsTable 1 }

PortStatsEntry ::=
	SEQUENCE {
		portStatsRlpIndex
			INTEGER,
		portStatsIndex
			INTEGER,
		portStatsInFrames
			Counter,
		portStatsOutFrames
			Counter,
		portStatsFrameRetrans
			Counter,
		portStatsFCSErrors
			Counter,
		portStatsLogicalRejects
			Counter,
		portStatsInPercentUtils
			Counter,
		portStatsOutPercentUtils
			Counter
	}

portStatsRlpIndex OBJECT-TYPE
	SYNTAX INTEGER
	ACCESS read-only
	STATUS mandatory
	DESCRIPTION "The RLP number"
	::= { portStatsEntry 1 }

portStatsIndex OBJECT-TYPE
	SYNTAX INTEGER
	ACCESS read-only
	STATUS mandatory
	DESCRIPTION "The Port number"
	::= { portStatsEntry 2 }

portStatsInFrames OBJECT-TYPE
	SYNTAX Counter
	ACCESS read-only
	STATUS mandatory
	DESCRIPTION "The number of frames received."
	::= { portStatsEntry 3 }

portStatsOutFrames OBJECT-TYPE
	SYNTAX Counter
	ACCESS read-only
	STATUS mandatory
	DESCRIPTION "The number of frames transmitted."
	::= { portStatsEntry 4 }

portStatsFrameRetrans OBJECT-TYPE
	SYNTAX Counter
	ACCESS read-only
	STATUS mandatory
	DESCRIPTION "The number of frames retransmitted."
	::= { portStatsEntry 5 }

portStatsFCSErrors OBJECT-TYPE
	SYNTAX Counter
	ACCESS read-only
	STATUS mandatory
	DESCRIPTION "The number of Frame Check Sequence (FCS) errors.
	A value consistently greater than zero indicates line probelms."
	::= { portStatsEntry 6 }

portStatsLogicalRejects OBJECT-TYPE
	SYNTAX Counter
	ACCESS read-only
	STATUS mandatory
	DESCRIPTION "The sum of Rejects and Frame Rejects. 
	A value consistently greater than zero indicates line probelms."
	::= { portStatsEntry 7 }

portStatsInPercentUtils OBJECT-TYPE
	SYNTAX Counter
	ACCESS read-only
	STATUS mandatory
	DESCRIPTION "The ratio of non-flag characters to total characters
	being received by the port."
	::= { portStatsEntry 8 }

portStatsOutPercentUtils OBJECT-TYPE
	SYNTAX Counter
	ACCESS read-only
	STATUS mandatory
	DESCRIPTION "The ration of non-flag characters to total characters
	being transmitted by the port."
	::= { portStatsEntry 9 }

statFrame OBJECT IDENTIFIER ::= 		{ statGroup 4 }

--
-- The Frame Relay Frame Level Statistics group defines the FlvFRStats Table
--

frStatsTable OBJECT-TYPE
	SYNTAX SEQUENCE OF FrStatsEntry
	ACCESS not-accessible
	STATUS mandatory
	DESCRIPTION "A Table to describe Frame Relay Frame Level Statistics on each Port"
	::= { statFrame 1}

frStatsEntry OBJECT-TYPE
	SYNTAX FrStatsEntry
	ACCESS not-accessible
	STATUS mandatory
	DESCRIPTION "A frame relay port statistics entry containing objects
	relating to frame relay port statistics."
	INDEX { frStatsRlpIndex, frStatsPortIndex }
	::= { frStatsTable 1 }

FrStatsEntry ::=
	SEQUENCE {
		frStatsRlpIndex
			INTEGER,
		frStatsPortIndex
			INTEGER,
		frStatsRxDEFrames
			Counter,
		frStatsTxDEFrames
			Counter,
		frStatsTxFECNFrames
			Counter,
		frStatsRxFECNFrames
			Counter,
		frStatsTxBECNFrames
			Counter,
		frStatsRxBECNFrames
			Counter,
		frStatsTxLMIFrames
			Counter,
		frStatsRxLMIFrames
			Counter,
		frStatsTxANXDFrames
			Counter,
		frStatsRxANXDFrames
			Counter,
		frStatsTotDiscFrames
			Counter
-- For the current time, we don't separate Discarded Frames
--		frStatsTxDiscFrames
--			Counter,
--		frStatsRxDiscFrames
--			Counter
}
frStatsRlpIndex OBJECT-TYPE
	SYNTAX INTEGER
	ACCESS read-only
	STATUS mandatory
	DESCRIPTION "The RLP Number."
	::= { frStatsEntry 1 }

frStatsPortIndex OBJECT-TYPE
	SYNTAX INTEGER
	ACCESS read-only
	STATUS mandatory
	DESCRIPTION "The Port number."
	::= { frStatsEntry 2 }

frStatsTxDEFrames OBJECT-TYPE
	SYNTAX Counter
	ACCESS read-only
	STATUS mandatory
	DESCRIPTION "The number of frames transmitted on the port with the
                 Discard Eligibility bit set."
	::= { frStatsEntry 3 }

frStatsRxDEFrames OBJECT-TYPE
	SYNTAX Counter
	ACCESS read-only
	STATUS mandatory
	DESCRIPTION "The number of frames received on the port with the discard
				 eligibility bit set."
	::= { frStatsEntry 4 }

frStatsTxFECNFrames OBJECT-TYPE
	SYNTAX Counter
	ACCESS read-only
	STATUS mandatory
	DESCRIPTION "The of number of frames transmitted on the port with FECN."
	::= { frStatsEntry 5 }

frStatsRxFECNFrames OBJECT-TYPE
	SYNTAX Counter
	ACCESS read-only
	STATUS mandatory
	DESCRIPTION "The number of frames received on the port with FECN."
	::= { frStatsEntry 6 }

frStatsTxBECNFrames OBJECT-TYPE
	SYNTAX Counter
	ACCESS read-only
	STATUS mandatory
	DESCRIPTION "The number of frames transmitted on the port with BECN."
	::= { frStatsEntry 7 }

frStatsRxBECNFrames OBJECT-TYPE
	SYNTAX Counter
	ACCESS read-only
	STATUS mandatory
	DESCRIPTION "The number of frames received on the port with BECN."
	::= { frStatsEntry 8 }

frStatsTxLMIFrames OBJECT-TYPE
	SYNTAX Counter
	ACCESS read-only
	STATUS mandatory
	DESCRIPTION "The number of LMI frames transmitted on the port."
	::= { frStatsEntry 9 }

frStatsRxLMIFrames OBJECT-TYPE
	SYNTAX Counter
	ACCESS read-only
	STATUS mandatory
	DESCRIPTION "The number of LMI frames received on the port."
	::= { frStatsEntry 10 }

frStatsTxANXDFrames OBJECT-TYPE
	SYNTAX Counter
	ACCESS read-only
	STATUS mandatory
	DESCRIPTION "The number of AnnexD frames transmitted on the port"
	::= { frStatsEntry 11 }
--
frStatsRxANXDFrames OBJECT-TYPE
	SYNTAX Counter
	ACCESS read-only
	STATUS mandatory
	DESCRIPTION "The number of AnnexD frames received on the port"
	::= { frStatsEntry 12 }
--
frStatsTotDiscFrames OBJECT-TYPE
	SYNTAX Counter
	ACCESS read-only
	STATUS mandatory
	DESCRIPTION "The total number of discarded frames on the port."
	::= { frStatsEntry 13 }
--
-- frStatsRxDiscFrames OBJECT-TYPE
-- 	SYNTAX Counter
-- 	ACCESS read-only
-- 	STATUS mandatory
-- 	DESCRIPTION "The number of INFO Frames transmitted on the port"
-- 	::= { frStatsEntry 14 }
--
-- The X25 Frame Level Tx Statistics group define the FlvX25TxStats Table
--

x25TxStatsTable OBJECT-TYPE
	SYNTAX SEQUENCE OF X25TxStatsEntry
	ACCESS not-accessible
	STATUS mandatory
	DESCRIPTION "A Table to describe X25 Frame Level Txmit Statistics on each Port"
	::= { statFrame 2 }

x25TxStatsEntry OBJECT-TYPE
	SYNTAX X25TxStatsEntry
	ACCESS not-accessible
	STATUS mandatory
	DESCRIPTION "An X25 frame level transmit statistics entry containing
	objects relating to x25 frame level transmit statistics."
	INDEX { x25TxRlpIndex, x25TxPortIndex }
	::= { x25TxStatsTable 1 }

X25TxStatsEntry ::=
	SEQUENCE {
		x25TxRlpIndex
			INTEGER,
		x25TxPortIndex
			INTEGER,
		x25TxSABMFrames
			Counter,
		x25TxUAFrames
			Counter,
		x25TxDISCFrames
			Counter,
		x25TxDMFrames
			Counter,
		x25TxFRMRFrames
			Counter,
		x25TxREJFrames
			Counter,
		x25TxRRFrames
			Counter,
		x25TxRNRFrames
			Counter,
		x25TxINFOFrames
			Counter
}
x25TxRlpIndex OBJECT-TYPE
	SYNTAX INTEGER
	ACCESS read-only
	STATUS mandatory
	DESCRIPTION "The RLP Number."
	::= { x25TxStatsEntry 1 }

x25TxPortIndex OBJECT-TYPE
	SYNTAX INTEGER
	ACCESS read-only
	STATUS mandatory
	DESCRIPTION "The Port number."
	::= { x25TxStatsEntry 2 }

x25TxSABMFrames OBJECT-TYPE
	SYNTAX Counter
	ACCESS read-only
	STATUS mandatory
	DESCRIPTION "The number of SABM's transmitted on the port."
	::= { x25TxStatsEntry 3 }

x25TxUAFrames OBJECT-TYPE
	SYNTAX Counter
	ACCESS read-only
	STATUS mandatory
	DESCRIPTION "The number of UA Frames transmitted on the port."
	::= { x25TxStatsEntry 4 }

x25TxDISCFrames OBJECT-TYPE
	SYNTAX Counter
	ACCESS read-only
	STATUS mandatory
	DESCRIPTION "The number of DISC Frames transmitted on the port."
	::= { x25TxStatsEntry 5 }

x25TxDMFrames OBJECT-TYPE
	SYNTAX Counter
	ACCESS read-only
	STATUS mandatory
	DESCRIPTION "The number of DM frames transmitted on the port."
	::= { x25TxStatsEntry 6 }

x25TxFRMRFrames OBJECT-TYPE
	SYNTAX Counter
	ACCESS read-only
	STATUS mandatory
	DESCRIPTION "The of Number of FRMR frames transmitted on the port."
	::= { x25TxStatsEntry 7 }

x25TxREJFrames OBJECT-TYPE
	SYNTAX Counter
	ACCESS read-only
	STATUS mandatory
	DESCRIPTION "The number of Reject Frames transmitted on the port."
	::= { x25TxStatsEntry 8 }

x25TxRRFrames OBJECT-TYPE
	SYNTAX Counter
	ACCESS read-only
	STATUS mandatory
	DESCRIPTION "The number of RR frames transmitted on the port."
	::= { x25TxStatsEntry 9 }

x25TxRNRFrames OBJECT-TYPE
	SYNTAX Counter
	ACCESS read-only
	STATUS mandatory
	DESCRIPTION "The number of RNR Frames transmitted on the port."
	::= { x25TxStatsEntry 10 }

x25TxINFOFrames OBJECT-TYPE
	SYNTAX Counter
	ACCESS read-only
	STATUS mandatory
	DESCRIPTION "The number of INFO Frames transmitted on the port"
	::= { x25TxStatsEntry 11 }
--
-- The X25 Frame Level Rx Statistics group define the FlvX25RxStats Table
--

x25RxStatsTable OBJECT-TYPE
	SYNTAX SEQUENCE OF X25RxStatsEntry
	ACCESS not-accessible
	STATUS mandatory
	DESCRIPTION "A Table to describe X25 Frame Level Rxmit Statistics on each Port"
	::= { statFrame 3 }

x25RxStatsEntry OBJECT-TYPE
	SYNTAX X25RxStatsEntry
	ACCESS not-accessible
	STATUS mandatory
	DESCRIPTION "An X25 frame level receive statistics entry containing
	objects relating to x25 frame level receive statistics."
	INDEX { x25RxRlpIndex, x25RxPortIndex }
	::= { x25RxStatsTable 1 }

X25RxStatsEntry ::=
	SEQUENCE {
		x25RxRlpIndex
			INTEGER,
		x25RxPortIndex
			INTEGER,
		x25RxSABMFrames
			Counter,
		x25RxUAFrames
			Counter,
		x25RxDISCFrames
			Counter,
		x25RxDMFrames
			Counter,
		x25RxFRMRFrames
			Counter,
		x25RxREJFrames
			Counter,
		x25RxRRFrames
			Counter,
		x25RxRNRFrames
			Counter,
		x25RxINFOFrames
			Counter
}
x25RxRlpIndex OBJECT-TYPE
	SYNTAX INTEGER
	ACCESS read-only
	STATUS mandatory
	DESCRIPTION "The RLP Number."
	::= { x25RxStatsEntry 1 }

x25RxPortIndex OBJECT-TYPE
	SYNTAX INTEGER
	ACCESS read-only
	STATUS mandatory
	DESCRIPTION "The Port number."
	::= { x25RxStatsEntry 2 }

x25RxSABMFrames OBJECT-TYPE
	SYNTAX Counter
	ACCESS read-only
	STATUS mandatory
	DESCRIPTION "The number of SABM's received on the port."
	::= { x25RxStatsEntry 3 }

x25RxUAFrames OBJECT-TYPE
	SYNTAX Counter
	ACCESS read-only
	STATUS mandatory
	DESCRIPTION "The number of UA Frames received on the port."
	::= { x25RxStatsEntry 4 }

x25RxDISCFrames OBJECT-TYPE
	SYNTAX Counter
	ACCESS read-only
	STATUS mandatory
	DESCRIPTION "The number of DISC Frames received on the port."
	::= { x25RxStatsEntry 5 }

x25RxDMFrames OBJECT-TYPE
	SYNTAX Counter
	ACCESS read-only
	STATUS mandatory
	DESCRIPTION "The number of DM frames received on the port."
	::= { x25RxStatsEntry 6 }

x25RxFRMRFrames OBJECT-TYPE
	SYNTAX Counter
	ACCESS read-only
	STATUS mandatory
	DESCRIPTION "The of Number of FRMR frames received on the port."
	::= { x25RxStatsEntry 7 }

x25RxREJFrames OBJECT-TYPE
	SYNTAX Counter
	ACCESS read-only
	STATUS mandatory
	DESCRIPTION "The number of Reject Frames received on the port."
	::= { x25RxStatsEntry 8 }

x25RxRRFrames OBJECT-TYPE
	SYNTAX Counter
	ACCESS read-only
	STATUS mandatory
	DESCRIPTION "The number of RR frames received on the port."
	::= { x25RxStatsEntry 9 }

x25RxRNRFrames OBJECT-TYPE
	SYNTAX Counter
	ACCESS read-only
	STATUS mandatory
	DESCRIPTION "The number of RNR Frames received on the port."
	::= { x25RxStatsEntry 10 }

x25RxINFOFrames OBJECT-TYPE
	SYNTAX Counter
	ACCESS read-only
	STATUS mandatory
	DESCRIPTION "The number of INFO Frames received on the port"
	::= { x25RxStatsEntry 11 }

statBag OBJECT IDENTIFIER ::= 		{ statGroup 5 }
statIp OBJECT IDENTIFIER ::= 			{ statGroup 6 }
statT1  OBJECT IDENTIFIER ::=                   { statGroup 7 }

-- The statistics group for T1 Channels.

t1StatsTable OBJECT-TYPE
	SYNTAX SEQUENCE OF T1StatsEntry
	ACCESS not-accessible
	STATUS mandatory
	DESCRIPTION "A Table to describe T1 Statistics."
	::= { statT1 1}

t1StatsEntry OBJECT-TYPE
	SYNTAX T1StatsEntry
	ACCESS not-accessible
	STATUS mandatory
	DESCRIPTION "A T1 port statistics entry containing objects relating
	to T1 port statistics."
	INDEX { t1StatsRlpIndex, t1StatsPortIndex }
	::= { t1StatsTable 1 }

T1StatsEntry ::=
	SEQUENCE {
		t1StatsRlpIndex
			INTEGER,
		t1StatsPortIndex
			INTEGER,
		t1StatsRcvFrames
			Counter,
		t1StatsXmitFrames
			Counter,
		t1StatsLCVCnt
			Counter,
		t1StatsPCVRErrs
			Counter,
		t1StatsOOSCnt
			Counter,
		t1StatsBlueAlarms
			Counter,
		t1StatsYellowAlarms
			Counter,
		t1StatsRedAlarms
			Counter,
		t1StatsRcvUsage
			Counter,
		t1StatsXmitUsage
			Counter,
		t1StatsXmitAbortFrames
			Counter,
		t1StatsRcvAbortFrames
			Counter,
		t1StatsRcvOverruns
			Counter,
		t1StatsRcvErrors
			Counter,
		t1StatsRcvChannelErrors
			Counter
}

t1StatsRlpIndex OBJECT-TYPE
	SYNTAX INTEGER
	ACCESS read-only
	STATUS mandatory
	DESCRIPTION "The RLP Number."
	::= { t1StatsEntry 1 }

t1StatsPortIndex OBJECT-TYPE
	SYNTAX INTEGER
	ACCESS read-only
	STATUS mandatory
	DESCRIPTION "The Port Number."
	::= { t1StatsEntry 2 }

t1StatsRcvFrames OBJECT-TYPE
	SYNTAX Counter
	ACCESS read-only
	STATUS mandatory
	DESCRIPTION "Total received frames."
	::= { t1StatsEntry 3 }

t1StatsXmitFrames OBJECT-TYPE
	SYNTAX Counter
	ACCESS read-only
	STATUS mandatory
	DESCRIPTION "Total transmitted frames."
	::= { t1StatsEntry 4 }

t1StatsLCVCnt OBJECT-TYPE
	SYNTAX Counter
	ACCESS read-only
	STATUS mandatory
	DESCRIPTION "Line code violation count."
	::= { t1StatsEntry 5 }

t1StatsPCVRErrs OBJECT-TYPE
	SYNTAX Counter
	ACCESS read-only
	STATUS mandatory
	DESCRIPTION "PCVR Bit error count."
	::= { t1StatsEntry 6 }

t1StatsOOSCnt OBJECT-TYPE
	SYNTAX Counter
	ACCESS read-only
	STATUS mandatory
	DESCRIPTION "Multiframe out of sync count."
	::= { t1StatsEntry 7 }

t1StatsBlueAlarms OBJECT-TYPE
	SYNTAX Counter
	ACCESS read-only
	STATUS mandatory
	DESCRIPTION "Blue alarm count."
	::= { t1StatsEntry 8 }

t1StatsYellowAlarms OBJECT-TYPE
	SYNTAX Counter
	ACCESS read-only
	STATUS mandatory
	DESCRIPTION "Yellow alarm count."
	::= { t1StatsEntry 9 }

t1StatsRedAlarms OBJECT-TYPE
	SYNTAX Counter
	ACCESS read-only
	STATUS mandatory
	DESCRIPTION "Red alarm count."
	::= { t1StatsEntry 10 }

t1StatsRcvUsage OBJECT-TYPE
	SYNTAX Counter
	ACCESS read-only
	STATUS mandatory
	DESCRIPTION "Receive port utilization."
	::= { t1StatsEntry 11 }

t1StatsXmitUsage OBJECT-TYPE
	SYNTAX Counter
	ACCESS read-only
	STATUS mandatory
	DESCRIPTION "Transmit port utilization."
	::= { t1StatsEntry 12 }

t1StatsXmitAbortFrames OBJECT-TYPE
	SYNTAX Counter
	ACCESS read-only
	STATUS mandatory
	DESCRIPTION "Total aborted transmit frames."
	::= { t1StatsEntry 13 }

t1StatsRcvAbortFrames OBJECT-TYPE
	SYNTAX Counter
	ACCESS read-only
	STATUS mandatory
	DESCRIPTION "Total aborted receive frames."
	::= { t1StatsEntry 14 }

t1StatsRcvOverruns OBJECT-TYPE
	SYNTAX Counter
	ACCESS read-only
	STATUS mandatory
	DESCRIPTION "Total receive overruns."
	::= { t1StatsEntry 15 }

t1StatsRcvErrors OBJECT-TYPE
	SYNTAX Counter
	ACCESS read-only
	STATUS mandatory
	DESCRIPTION "Total bad receives."
	::= { t1StatsEntry 16 }

t1StatsRcvChannelErrors OBJECT-TYPE
	SYNTAX Counter
	ACCESS read-only
	STATUS mandatory
	DESCRIPTION "Total bad receives."
	::= { t1StatsEntry 17 }

-- The statistics group for DS0A.

statDS0A  OBJECT IDENTIFIER ::=                 { statGroup 8 }

ds0aStatsTable OBJECT-TYPE
	SYNTAX SEQUENCE OF DS0AStatsEntry
	ACCESS not-accessible
	STATUS mandatory
	DESCRIPTION "A Table to describe DS0A Statistics."
	::= { statDS0A 1}

ds0aStatsEntry OBJECT-TYPE
	SYNTAX DS0AStatsEntry
	ACCESS not-accessible
	STATUS mandatory
	DESCRIPTION "A DS0A port statistics entry containing objects relating
	to DS0A port statistics."
	INDEX { ds0aStatsRlpIndex, ds0aStatsPortIndex, ds0aStatsChannelIndex }
	::= { ds0aStatsTable 1 }

DS0AStatsEntry ::=
	SEQUENCE {
		ds0aStatsRlpIndex
			INTEGER,
		ds0aStatsPortIndex
			INTEGER,
		ds0aStatsChannelIndex
			INTEGER,
		ds0aStatsXmitFrames
			Counter,
		ds0aStatsRcvFrames
			Counter,
		ds0aStatsRcvAbortFrames
			Counter,
		ds0aStatsRcvOverruns
			Counter,
		ds0aStatsRcvErrors
			Counter
}

ds0aStatsRlpIndex OBJECT-TYPE
	SYNTAX INTEGER
	ACCESS read-only
	STATUS mandatory
	DESCRIPTION "The RLP Number."
	::= { ds0aStatsEntry 1 }

ds0aStatsPortIndex OBJECT-TYPE
	SYNTAX INTEGER
	ACCESS read-only
	STATUS mandatory
	DESCRIPTION "The Port Number."
	::= { ds0aStatsEntry 2 }

ds0aStatsChannelIndex OBJECT-TYPE
	SYNTAX INTEGER
	ACCESS read-only
	STATUS mandatory
	DESCRIPTION "The Channel Number."
	::= { ds0aStatsEntry 3 }

ds0aStatsXmitFrames OBJECT-TYPE
	SYNTAX Counter
	ACCESS read-only
	STATUS mandatory
	DESCRIPTION "Total transmitted frames."
	::= { ds0aStatsEntry 4 }

ds0aStatsRcvFrames OBJECT-TYPE
	SYNTAX Counter
	ACCESS read-only
	STATUS mandatory
	DESCRIPTION "Total received frames."
	::= { ds0aStatsEntry 5 }

ds0aStatsRcvAbortFrames OBJECT-TYPE
	SYNTAX Counter
	ACCESS read-only
	STATUS mandatory
	DESCRIPTION "Total receive aborted frames."
	::= { ds0aStatsEntry 6 }

ds0aStatsRcvOverruns OBJECT-TYPE
	SYNTAX Counter
	ACCESS read-only
	STATUS mandatory
	DESCRIPTION "Total receive overruns."
	::= { ds0aStatsEntry 7 }

ds0aStatsRcvErrors OBJECT-TYPE
	SYNTAX Counter
	ACCESS read-only
	STATUS mandatory
	DESCRIPTION "Total receive errors."
	::= { ds0aStatsEntry 8 }

-- The statistics group for Voice.
statVoice  OBJECT IDENTIFIER ::={ statGroup 9 }

--
-- The Voice Statistics Table
--

voiceStatsTable OBJECT-TYPE
    SYNTAX SEQUENCE OF VoiceStatsEntry
    ACCESS not-accessible
    STATUS mandatory
    DESCRIPTION "A Table to describe Voice over Frame Relay Statistics."
    ::= { statVoice 1}

voiceStatsEntry OBJECT-TYPE
    SYNTAX VoiceStatsEntry
    ACCESS not-accessible
    STATUS mandatory
    DESCRIPTION "A voice port statistics entry containing objects relating
    to voice port statistics."
    INDEX {voiceStatsRlpIndex, voiceStatsPortIndex }

    ::= { voiceStatsTable 1 }

VoiceStatsEntry ::=
    SEQUENCE {
        voiceStatsRlpIndex
            INTEGER,
        voiceStatsPortIndex
            INTEGER,
        voiceStatsRxCalls
            Counter,
        voiceStatsTxCalls
            Counter,
        voiceStatsRxCallsAccepts
            Counter,
        voiceStatsTxCallsAccepts
            Counter,
        voiceStatsRxClears
            Counter,
        voiceStatsTxClears
            Counter,
        voiceStatsBusyCalls
            Counter,
        voiceStatsCallTimeouts
            Counter,
        voiceStatsRxCongestions
            Counter,
        voiceStatsTxCongestions
            Counter
}

voiceStatsRlpIndex OBJECT-TYPE
    SYNTAX INTEGER
    ACCESS read-only
    STATUS mandatory
    DESCRIPTION "The RLP Number."
    ::= { voiceStatsEntry 1 }

voiceStatsPortIndex OBJECT-TYPE
    SYNTAX INTEGER
    ACCESS read-only
    STATUS mandatory
    DESCRIPTION "The Port Number."
    ::= { voiceStatsEntry 2 }

voiceStatsRxCalls OBJECT-TYPE
    SYNTAX Counter
    ACCESS read-only
    STATUS mandatory
    DESCRIPTION "The Number of Calls Received from the Network."
    ::= { voiceStatsEntry 3 }

voiceStatsTxCalls OBJECT-TYPE
    SYNTAX Counter
    ACCESS read-only
    STATUS mandatory
    DESCRIPTION "The Number of Calls Transmitted to the Network."
    ::= { voiceStatsEntry 4 }

voiceStatsRxCallsAccepts OBJECT-TYPE
    SYNTAX Counter
    ACCESS read-only
    STATUS mandatory
    DESCRIPTION "The Number of Call Accepts Received from the Network."
    ::= { voiceStatsEntry 5 }

voiceStatsTxCallsAccepts OBJECT-TYPE
    SYNTAX Counter
    ACCESS read-only
    STATUS mandatory
    DESCRIPTION "The Number of Call Accepts Transmitted to the Network."
    ::= { voiceStatsEntry 6 }

voiceStatsRxClears OBJECT-TYPE
    SYNTAX Counter
    ACCESS read-only
    STATUS mandatory
    DESCRIPTION "The Number of Call Receives cleared."
    ::= { voiceStatsEntry 7 }

voiceStatsTxClears OBJECT-TYPE
    SYNTAX Counter
    ACCESS read-only
    STATUS mandatory
    DESCRIPTION "The Number of Call Transmitts cleared."
    ::= { voiceStatsEntry 8 }

voiceStatsBusyCalls OBJECT-TYPE
    SYNTAX Counter
    ACCESS read-only
    STATUS mandatory
    DESCRIPTION "The Number of calls which received Busy indication."
    ::= { voiceStatsEntry 9 }

voiceStatsCallTimeouts OBJECT-TYPE
    SYNTAX Counter
    ACCESS read-only
    STATUS mandatory
    DESCRIPTION "The Number of calls which transmitted time-out to the network."
    ::= { voiceStatsEntry 10 }

voiceStatsRxCongestions OBJECT-TYPE
    SYNTAX Counter
    ACCESS read-only
    STATUS mandatory
    DESCRIPTION "The number of congestion management frames Received."
    ::= { voiceStatsEntry 11 }

voiceStatsTxCongestions OBJECT-TYPE
    SYNTAX Counter
    ACCESS read-only
    STATUS mandatory
    DESCRIPTION "The number of congestion management frames Transmitted."
    ::= { voiceStatsEntry 12 }

statThresh OBJECT IDENTIFIER ::= 	{ statistics 2 }

--
-- The Statistic Threshold group for RLPs defines the RlpThresh Table
--

rlpThreshTable OBJECT-TYPE
	SYNTAX SEQUENCE OF RlpThreshEntry
	ACCESS not-accessible
	STATUS mandatory
	DESCRIPTION "A Table to describe Statistic thresholds on each RLP"
	::= { statThresh 1 }

rlpThreshEntry OBJECT-TYPE
	SYNTAX RlpThreshEntry
	ACCESS not-accessible
	STATUS mandatory
	DESCRIPTION "An RLP statistics threshold entry containing objects
	relating to RLP statistics thresholds."
	INDEX { rlpThreshRlpIndex }
	::= { rlpThreshTable 1 }

RlpThreshEntry ::=
	SEQUENCE {
		rlpThreshRlpIndex
			INTEGER,
		rlpThreshPercntBufInUse
			INTEGER,
		rlpThreshMsgQueueLen
			INTEGER,
		rlpThreshRxFramesPerSec
			INTEGER,
		rlpThreshTxFramesPerSec
			INTEGER,
		rlpThreshRejFramesPerSec
			INTEGER,
		rlpThreshRtxFramesPerSec
			INTEGER
}
rlpThreshRlpIndex OBJECT-TYPE
	SYNTAX INTEGER
	ACCESS read-only
	STATUS mandatory
	DESCRIPTION "The RLP Number."
	::= { rlpThreshEntry 1 }

rlpThreshPercntBufInUse OBJECT-TYPE
	SYNTAX INTEGER
	ACCESS read-only
	STATUS mandatory
	DESCRIPTION "The threshold for Percent of Buffers in use on the RLP"
	::= { rlpThreshEntry 2 }

rlpThreshMsgQueueLen OBJECT-TYPE
	SYNTAX INTEGER
	ACCESS read-only
	STATUS mandatory
	DESCRIPTION "The threshold for Percent of Buffers in use on the RLP"
	::= { rlpThreshEntry 3 }

rlpThreshRxFramesPerSec OBJECT-TYPE
	SYNTAX INTEGER
	ACCESS read-only
	STATUS mandatory
	DESCRIPTION "The threshold for Rcvd frames per second on the RLP"
	::= { rlpThreshEntry 4 }

rlpThreshTxFramesPerSec OBJECT-TYPE
	SYNTAX INTEGER
	ACCESS read-only
	STATUS mandatory
	DESCRIPTION "The threshold for Txmitted frames per second on the RLP"
	::= { rlpThreshEntry 5 }

rlpThreshRejFramesPerSec OBJECT-TYPE
	SYNTAX INTEGER
	ACCESS read-only
	STATUS mandatory
	DESCRIPTION "The threshold for Rejected Frames per second on the RLP"
	::= { rlpThreshEntry 6 }

rlpThreshRtxFramesPerSec OBJECT-TYPE
	SYNTAX INTEGER
	ACCESS read-only
	STATUS mandatory
	DESCRIPTION "The threshold for Retransmitted frames per second on the RLP"
	::= { rlpThreshEntry 7 }

--
-- The Statistic Threshold group for Ports defines the PortThresh Table
--

portThreshTable OBJECT-TYPE
	SYNTAX SEQUENCE OF PortThreshEntry
	ACCESS not-accessible
	STATUS mandatory
	DESCRIPTION "A Table to describe Statistic thresholds on each port"
	::= { statThresh 2  }

portThreshEntry OBJECT-TYPE
	SYNTAX PortThreshEntry
	ACCESS not-accessible
	STATUS mandatory
	DESCRIPTION "A port statistics threshold entry containing objects
	relating to port statistics thresholds."
	INDEX { portThreshRlpIndex, portThreshIndex }
	::= { portThreshTable 1 }

PortThreshEntry ::=
	SEQUENCE {
		portThreshRlpIndex
			INTEGER,
		portThreshIndex
			INTEGER,
		portThreshRxFramesPerSec
			INTEGER,
		portThreshTxFramesPerSec
			INTEGER,
		portThreshRtxFramesPerSec
			INTEGER,
		portThreshFCSErrPerSec  
			INTEGER,
		portThreshLogRejPerSec
			INTEGER,
		portThreshTxErrorRatio
			INTEGER,
		portThreshRxErrorRatio
			INTEGER,
		portThreshTxPercentUtl
			INTEGER,
		portThreshRxPercentUtl
			INTEGER
}
portThreshRlpIndex OBJECT-TYPE
	SYNTAX INTEGER
	ACCESS read-only
	STATUS mandatory
	DESCRIPTION "The RLP Number."
	::= { portThreshEntry 1 }

portThreshIndex OBJECT-TYPE
	SYNTAX INTEGER
	ACCESS read-only
	STATUS mandatory
	DESCRIPTION "The Port Number."
	::= { portThreshEntry 2 }

portThreshRxFramesPerSec OBJECT-TYPE
	SYNTAX INTEGER
	ACCESS read-only
	STATUS mandatory
	DESCRIPTION "The threshold for Rcvd frames per second on the port."
	::= { portThreshEntry 3 }

portThreshTxFramesPerSec OBJECT-TYPE
	SYNTAX INTEGER
	ACCESS read-only
	STATUS mandatory
	DESCRIPTION "The threshold for Txmitted frames per second on the port."
	::= { portThreshEntry 4 }

portThreshRtxFramesPerSec OBJECT-TYPE
	SYNTAX INTEGER
	ACCESS read-only
	STATUS mandatory
	DESCRIPTION "The threshold for Retransmitted frames per second on the port."
	::= { portThreshEntry 5 }

portThreshFCSErrPerSec OBJECT-TYPE
	SYNTAX INTEGER
	ACCESS read-only
	STATUS mandatory
	DESCRIPTION "The threshold for FCS errors per second on the port."
	::= { portThreshEntry 6 }

portThreshLogRejPerSec OBJECT-TYPE
	SYNTAX INTEGER
	ACCESS read-only
	STATUS mandatory
	DESCRIPTION "The threshold for Logical Rejects per second on the port."
	::= { portThreshEntry 7 }

portThreshTxErrorRatio OBJECT-TYPE
	SYNTAX INTEGER
	ACCESS read-only
	STATUS mandatory
	DESCRIPTION "The threshold for Txmit error ratio on the port."
	::= { portThreshEntry 8 }

portThreshRxErrorRatio OBJECT-TYPE
	SYNTAX INTEGER
	ACCESS read-only
	STATUS mandatory
	DESCRIPTION "The threshold for Rcv error ratio on the port."
	::= { portThreshEntry 9 }

portThreshTxPercentUtl OBJECT-TYPE
	SYNTAX INTEGER
	ACCESS read-only
	STATUS mandatory
	DESCRIPTION "The threshold for Txmit percent utilization on the port."
	::= { portThreshEntry 10 }

portThreshRxPercentUtl OBJECT-TYPE
	SYNTAX INTEGER
	ACCESS read-only
	STATUS mandatory
	DESCRIPTION "The threshold for Rcv percent utilization on the port."
	::= { portThreshEntry 11 }

-- **********************
-- *  THE BRIDGE GROUP  *
-- **********************

bridge OBJECT IDENTIFIER ::= { local 9 }

bridgeAdminVirtualLANID 	OBJECT-TYPE
				SYNTAX INTEGER (0..4095)
				ACCESS read-write
				STATUS mandatory
				DESCRIPTION 
					"LAN id inserted into token ring RIF field representing
					 internal virtual ring, for LLC2 or bridged traffic"
				::= { bridge 1 }

bridgeOperVirtualLANID 	OBJECT-TYPE
			SYNTAX INTEGER (0..4095)
			ACCESS read-only
			STATUS mandatory
			DESCRIPTION 
					"LAN id inserted into token ring RIF field representing
					 internal virtual ring, for LLC2 or bridged traffic"
			::= { bridge 2 }

bridgeEnabled	OBJECT-TYPE
		SYNTAX INTEGER {
			no (1),
			yes (2)
		}
		ACCESS read-write
		STATUS mandatory
		DESCRIPTION 
			"When yes the spanning tree algorithm is in effect and all
			 traffic types may be bridged. When no only llc/2 terminated
			 traffic is allowed on bridge interfaces."
		DEFVAL { yes }
		::= { bridge 3 }

bridgeMaxSizeForwardingTable 	OBJECT-TYPE
				SYNTAX INTEGER (128..65535)
				ACCESS read-write
				STATUS mandatory
				DESCRIPTION 
					"Number of entries allowed in the bridge forwarding
					 table"
				DEFVAL { 65535 }
				::= { bridge 4 }

bridgeIPEnabled OBJECT-TYPE
		SYNTAX INTEGER {
				no (1),
				yes (2)
		}
		ACCESS read-write
		STATUS mandatory
		DESCRIPTION 
				"When yes, and BRIDGING ENABLED, IP traffic will be bridged,
				 otherwise IP traffic will be routed."
		DEFVAL { no }
		::= { bridge 5 }

bridgeIPXEnabled	OBJECT-TYPE
			SYNTAX INTEGER {
					no (1),
					yes (2)
			}
			ACCESS read-write
			STATUS mandatory
			DESCRIPTION 
				"When yes, and BRIDGING ENABLED, IPX traffic will be bridged,
				 otherwise IPX traffic will be routed."
			DEFVAL { no }
			::= { bridge 6 }

bridgeAdminSRBID	OBJECT-TYPE
			SYNTAX INTEGER (0..15)
			ACCESS read-write
			STATUS mandatory
			DESCRIPTION 
				"bridge ID to be inserted into token ring RIF field, 
				this bridge"
			DEFVAL { 0 } 
			::= { bridge 7 }

bridgeOperSRBID	OBJECT-TYPE
		SYNTAX INTEGER (0..15)
		ACCESS read-only
		STATUS mandatory
		DESCRIPTION 
				"bridge ID to be inserted into token ring RIF field, 
				this bridge"
		::= { bridge 8 }

bridgeDefaultEthernetFrameType	OBJECT-TYPE
                        	SYNTAX INTEGER {
						type-II (1),
						ieee8023 (2)
				}
	                        ACCESS      read-write
        	                STATUS      mandatory
                	        DESCRIPTION 
								"default frame type to be used when 
								 forwarding traffic on ethernet interfaces."
				DEFVAL { type-II }
				::= { bridge 9 }

-- **************************
-- *  THE NETLINK IP GROUP  *
-- **************************

ipNl OBJECT IDENTIFIER ::= { local 11}

--
--  The Netlink IP Node Defaults Objects
--

nlIpDefaultRIPVersion OBJECT-TYPE
	SYNTAX INTEGER {
		ripVersion1(1),
		rip1Compatible(2),
		ripVersion2(3)
	}
	ACCESS read-write
	STATUS mandatory
	DESCRIPTION "The version of RIP that will be used by IP."
	DEFVAL { ripVersion1 }
	::= { ipNl 1 }

-- *****************************
-- *  THE NETLINK VOICE GROUP  *
-- *****************************

voice OBJECT IDENTIFIER ::= { local 12 }

--
--  The Netlink Voice System Level Objects
--

voiceSystemVoiceNodeNum OBJECT-TYPE
    SYNTAX INTEGER (1..9999)
    ACCESS read-write
    STATUS mandatory
    DESCRIPTION "The number that identifies this node."
    DEFVAL { 1 }
    ::= { voice 1 }

voiceSystemRingVolFreq OBJECT-TYPE
    SYNTAX INTEGER {
                v75-hz-16-66 (1),
                v80-hz-20-00 (2),
                v75-hz-25-00 (3),
                v60-hz-50-00 (4),
                v75-hz-50-00 (5)
                }
    ACCESS read-write
    STATUS mandatory
    DESCRIPTION "The frequency and voltage of the telephone ring circuit.
                In two wire OPX mode, the node provides ring voltage to
                the telephone when it is called by a remote unit."
    DEFVAL { v80-hz-20-00 }
    ::= { voice 2 }

voiceSystemCountryCode OBJECT-TYPE
    SYNTAX INTEGER (1..999)
    ACCESS read-write
    STATUS mandatory
    DESCRIPTION "The telephone dialing prefix code that identifies
                the country in which the node is installed."
    DEFVAL { 1 }
    ::= { voice 3 }

voiceSystemDialDigits OBJECT-TYPE
    SYNTAX INTEGER (2..4)
    ACCESS read-write
    STATUS mandatory
    DESCRIPTION "The number of digits that will be used in the speed
                dialing scheme, as well as the number of digits one
                can specify for the Auto Dial feature. This requires
                rebooting for the change to take effect."
    DEFVAL { 3 }
    ::= { voice 4 }

voiceSystemVoiceRatesMin OBJECT-TYPE
    SYNTAX INTEGER {
                bps-4800 (1),
                bps-8000 (2),
                bps-32000 (3),
                bps-64000 (4)
                }
    ACCESS read-write
    STATUS mandatory
    DESCRIPTION "The minimum operating rate of all voice channels when
                congestion occurs."
    DEFVAL { bps-4800 }
    ::= { voice 5 }

voiceSystemVoiceRatesMax OBJECT-TYPE
    SYNTAX INTEGER {
                bps-4800 (1),
                bps-8000 (2),
                bps-32000 (3),
                bps-64000 (4)
                }
    ACCESS read-write
    STATUS mandatory
    DESCRIPTION "The maximum operating digitization rate of all voice
                channels when there is no congestion."
    DEFVAL { bps-64000 }
    ::= { voice 6 }

voiceSystemExtDialDigits OBJECT-TYPE
    SYNTAX INTEGER (0..16)
    ACCESS read-write
    STATUS mandatory
    DESCRIPTION "The number of extended dial digits that can be defined
                in the speed map table and/or entered by the user of
                attached equipment as part of a dial string. This requires
                rebooting for the change to take effect."
    DEFVAL { 0 }
    ::= { voice 7 }

--
-- The Netlink Voice Speed Dial Map table
--

voiceSpeedDialTable OBJECT-TYPE
    SYNTAX  SEQUENCE OF VoiceSpeedDialEntry
    ACCESS  not-accessible
    STATUS  mandatory
    DESCRIPTION
            "A list of speed-dial numbers."
    ::= { voice 8 }

voiceSpeedDialEntry OBJECT-TYPE
    SYNTAX  VoiceSpeedDialEntry
    ACCESS  not-accessible
    STATUS  mandatory
    DESCRIPTION
            "A Voice Speed Dial entry containing objects relating to
            the speed-dial number that are configurable by the user."
    INDEX   { voiceSpeedDialDigits }
    ::= { voiceSpeedDialTable 1 }

VoiceSpeedDialEntry ::=
    SEQUENCE {
        voiceSpeedDialDigits
            OCTET STRING,
        voiceSpeedDialLongDialMap
            OCTET STRING,
        voiceSpeedDialExtDialStr
            OCTET STRING,
        voiceSpeedDialRowStatus
            RowStatus
    }

voiceSpeedDialDigits OBJECT-TYPE
    SYNTAX  OCTET STRING (SIZE(1..4))
    ACCESS  read-only
    STATUS  mandatory
    DESCRIPTION
            "The speed-dial number. A question mark wildcard can be used
            for any digit, and an asterisk wildcard can be used for any
            number of digits."
    ::= { voiceSpeedDialEntry 1 }

voiceSpeedDialLongDialMap OBJECT-TYPE
    SYNTAX  OCTET STRING (SIZE(6))
    ACCESS  read-write
    STATUS  mandatory
    DESCRIPTION
            "The number for which the speed-dial number is a shortcut."
    ::= { voiceSpeedDialEntry 2 }

voiceSpeedDialExtDialStr OBJECT-TYPE
    SYNTAX  OCTET STRING (SIZE(1..16))
    ACCESS  read-write
    STATUS  mandatory
    DESCRIPTION
            "The extended set of digits that will be forwarded with the
            call if portVoiceOperExtDigitsSource in the physical port
            record is set to Map."
    ::= { voiceSpeedDialEntry 3 }

voiceSpeedDialRowStatus OBJECT-TYPE
    SYNTAX  RowStatus
    ACCESS  read-write
    STATUS  mandatory
    DESCRIPTION
            "This variable is used to manage the creation and deletion
            of conceptual rows in the voiceSpeedDialTable and follows the
            SNMPv2 RowStatus conventions by supporting the following values:

                 - `active', which indicates that the conceptual row is
                available for use by the managed device.  For a management
                protocol set operation, a genErr response is returned when
                the row does not exist.

                 - `createAndGo', which is supplied by a management
                 station wishing to create a new instance of a
                 conceptual row and to have its status automatically set
                 to active, making it available for use by the managed
                 device.  For a management protocol set operation, a
                 genErr response is returned when the row already exists.

                 - `destroy', which is supplied by a management station
                 wishing to delete all of the instances associated with
                 an existing conceptual row.

            Note that all of the above values may be specified in a
            management protocol set operation, and only the 'active'
            value will be returned in response to a management protocol
            retrieval operation.  For a management protocol set operation,
            if other variable bindings are included in the same PDU, then
            a genErr response is returned."
    ::= { voiceSpeedDialEntry 4 }

END
