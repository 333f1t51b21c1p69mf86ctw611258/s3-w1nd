MICOM-NODE-MIB DEFINITIONS ::= BEGIN
	IMPORTS
		Counter, Gauge, IpAddress, enterprises
                   		 	FROM RFC1155-SMI
		OBJECT-TYPE
                    			FROM RFC-1212
		TRAP-TYPE
                			FROM RFC-1215
		IpAddress
				FROM RFC1065-SMI
		DisplayString 
				FROM SNMPv2-TC;

-- group OBJECT IDENTIFIERS

--	iso							OBJECT IDENTIFIER ::= {1}
--	org							OBJECT IDENTIFIER ::= {iso 3}
--	dod							OBJECT IDENTIFIER ::= {org 6}
--	internet					OBJECT IDENTIFIER ::= {dod 1}
--	mgmt						OBJECT IDENTIFIER ::= {internet 2}
--	private						OBJECT IDENTIFIER ::= {internet 4}
--	enterprises					OBJECT IDENTIFIER ::= {private 1}
	micom						OBJECT IDENTIFIER ::= {enterprises 335}
	products					OBJECT IDENTIFIER ::= {micom 1}

	marathon-netrunner			OBJECT IDENTIFIER ::= {products 1}
	micom-proxy					OBJECT IDENTIFIER ::= {products 2}

	marathon-netrunner-proxy	OBJECT IDENTIFIER ::= {micom-proxy 1}

	security 					OBJECT IDENTIFIER ::= {marathon-netrunner-proxy 1}
	diagnostics	 				OBJECT IDENTIFIER ::= {marathon-netrunner-proxy 2}
	configuration		 		OBJECT IDENTIFIER ::= {marathon-netrunner-proxy 3}
	control	 					OBJECT IDENTIFIER ::= {marathon-netrunner-proxy 4}
	status						OBJECT IDENTIFIER ::= {marathon-netrunner-proxy 5}
	statistics 					OBJECT IDENTIFIER ::= {marathon-netrunner-proxy 6}

	system 						OBJECT IDENTIFIER ::= {configuration 1}
	card 						OBJECT IDENTIFIER ::= {configuration 2}
	port 						OBJECT IDENTIFIER ::= {configuration 3}
	channel 					OBJECT IDENTIFIER ::= {configuration 4}
	link 						OBJECT IDENTIFIER ::= {configuration 5}
	interface					OBJECT IDENTIFIER ::= {configuration 6}
	trap 						OBJECT IDENTIFIER ::= {configuration 7}
	proxy 						OBJECT IDENTIFIER ::= {configuration 8}

	attributes 					OBJECT IDENTIFIER ::= {system 1}
	messages 					OBJECT IDENTIFIER ::= {system 2}

	sync-channel				OBJECT IDENTIFIER ::= {channel 1}
	async-channel				OBJECT IDENTIFIER ::= {channel 2}
	voice-fax-channel			OBJECT IDENTIFIER ::= {channel 3}
	digital-voice-channel		OBJECT IDENTIFIER ::= {channel 4}

	mux-link					OBJECT IDENTIFIER ::= {link 1}
	esi-link					OBJECT IDENTIFIER ::= {link 2}
	x-dot-21-link				OBJECT IDENTIFIER ::= {link 3}
	local-esi-link				OBJECT IDENTIFIER ::= {link 4}
	esi-secondary-link			OBJECT IDENTIFIER ::= {link 5}
	frame-relay-link			OBJECT IDENTIFIER ::= {link 6}

	t1-interface				OBJECT IDENTIFIER ::= {interface 1}
	e1-interface				OBJECT IDENTIFIER ::= {interface 2}

	statistics-configuration	OBJECT IDENTIFIER ::= {statistics 1}
	statistics-periodic			OBJECT IDENTIFIER ::= {statistics 2}
	statistics-accumulated		OBJECT IDENTIFIER ::= {statistics 3}

-- Security Group

-- N_CMOS.O_LCDPSW ======================================================

lcdSecurityPassword OBJECT-TYPE
	SYNTAX	DisplayString (SIZE (0..8))
	ACCESS	write-only
	STATUS	mandatory
	DESCRIPTION	"Access password to the LCD/Keypad located on front of 
			the integration unit."
	::= {security 1}

-- N_CMOS.O_CMDPSW =====================================================

cmdPortSecurityGroup    OBJECT IDENTIFIER ::= {security 2}

cmdPortSecurityGlobalPassword OBJECT-TYPE
	SYNTAX	DisplayString (SIZE (0..8))
	ACCESS	write-only
	STATUS	mandatory
	DESCRIPTION	"Access password to all functions. Password must be 
			alphanumeric characters (A-Z, 0-9) up to 8 characters." 
	 ::= { cmdPortSecurityGroup 1}

cmdPortSecurityStatusPassword OBJECT-TYPE
	SYNTAX	DisplayString (SIZE (0..8))
	ACCESS	write-only
	STATUS	mandatory
	DESCRIPTION	"Access password to view, status, and exit Command 
			Facility functions. Password must be alphanumeric
		 	characters (A-Z, 0-9) up to 8 characters." 
	::= { cmdPortSecurityGroup 2}

-- N_CMOS.O_NMSSYS ==================================================

nmsSecurityPPPPassword OBJECT-TYPE
	SYNTAX	DisplayString (SIZE (0..8))
	ACCESS	write-only
	STATUS	mandatory
	DESCRIPTION	"Access password to the $PPP Facility. Password must be 
			alphanumeric characters (A-Z, 0-9) upto 8 characters." 
	::= {security 3}


-- Diagnostics Group

-- N_DIAG.O_PING ==========================================================

pingResponse OBJECT-TYPE
	SYNTAX	INTEGER {
		responded (1),
		notResponding (2)
		}
	ACCESS	read-only
	STATUS	mandatory
	DESCRIPTION	"Determines whether or not the node is reachable." 
	::= {diagnostics 1}

-- N_DIAG.O_VOICE =========================================================

voiceChannelDiagTable OBJECT-TYPE
	SYNTAX	SEQUENCE OF VoiceChannelDiagEntry
	ACCESS	not-accessible
	STATUS	mandatory
	DESCRIPTION	"This table provides the system diagnostics function to test the 
			voice/fax module(s) if installed." 
	::= {diagnostics 2}

voiceChannelDiagEntry OBJECT-TYPE
	SYNTAX	VoiceChannelDiagEntry
	ACCESS	not-accessible
	STATUS	mandatory
	DESCRIPTION	"An entry within the table specifying particular channel on voice module." 
	INDEX		{voiceChannelDiagCardNumber, voiceChannelDiagChannelNumber}
	::= {voiceChannelDiagTable 1}

VoiceChannelDiagEntry ::= SEQUENCE {
	voiceChannelDiagCardNumber		INTEGER,
	voiceChannelDiagChannelNumber		INTEGER,
	voiceChannelDiagCommand		INTEGER
	}

voiceChannelDiagCardNumber OBJECT-TYPE
	SYNTAX	INTEGER (1..5)
	ACCESS	read-only
	STATUS	mandatory
	DESCRIPTION	"Identifies the module/card number for the specified channel 
			to be tested." 
	::= {voiceChannelDiagEntry 1}

voiceChannelDiagChannelNumber OBJECT-TYPE
	SYNTAX	INTEGER (1..12)
	ACCESS	read-only
	STATUS	mandatory
	DESCRIPTION	"Identifies the channel number to which this entry pertains." 
	::= {voiceChannelDiagEntry 2}

voiceChannelDiagCommand OBJECT-TYPE
	SYNTAX	INTEGER {
		terminateTest (1),
		inputLevelDisplay (2),
		selfTest (3),
		putChannelInLoopback (4)
		}
	ACCESS	write-only
	STATUS	mandatory
	DESCRIPTION	"Options to initiate different type of tests or to terminate the tests.
			Option 2 allows monitoring of the level of the input voice signal. Option
			3 verifies that the voice channel is working properly. Option 4 causes
			the voice channel to compress the local speech signal and then to pass
			this signal through the reconstruction process back to the local receiver." 
	::= {voiceChannelDiagEntry 3}

-- N_DIAG.O_SYNC ==========================================================

syncChannelDiagTable OBJECT-TYPE
	SYNTAX	SEQUENCE OF SyncChannelDiagEntry
	ACCESS	not-accessible
	STATUS	mandatory
	DESCRIPTION	"Table to control the testing and diagnosing of specific 
			sync channel." 
	::= {diagnostics 3}

syncChannelDiagEntry OBJECT-TYPE
	SYNTAX	SyncChannelDiagEntry
	ACCESS	not-accessible
	STATUS	mandatory
	DESCRIPTION	"Entry into the diagnostic table for a specific channel on 
			specified module." 
	INDEX		{syncChannelDiagCardNumber, syncChannelDiagChannelNumber}
	::= {syncChannelDiagTable 1}

SyncChannelDiagEntry ::= SEQUENCE {
	syncChannelDiagCardNumber		INTEGER,
	syncChannelDiagChannelNumber		INTEGER,
	syncChannelDiagCommand		INTEGER
	}

syncChannelDiagCardNumber OBJECT-TYPE
	SYNTAX	INTEGER (1..5)
	ACCESS	read-only
	STATUS	mandatory
	DESCRIPTION	"The specified module/card number of the channel to be tested." 
	::= {syncChannelDiagEntry 1}

syncChannelDiagChannelNumber OBJECT-TYPE
	SYNTAX	INTEGER (1..6)
	ACCESS	read-only
	STATUS	mandatory
	DESCRIPTION	"The specified channel number to be tested." 
	::= {syncChannelDiagEntry 2}

syncChannelDiagCommand OBJECT-TYPE
	SYNTAX	INTEGER {
		terminateTest (1),
		putChannelInLoopback (2)
		}
	ACCESS	write-only
	STATUS	mandatory
	DESCRIPTION	"Command option to terminate and initiate the test. The test
			loops the control signals and data back." 
	::= {syncChannelDiagEntry 3}

-- System Attribute Group

-- N_CMOS.O_PROMID ========================================================

sysPromID OBJECT-TYPE
	SYNTAX	DisplayString (SIZE (1..18)) 
	ACCESS	read-only
	STATUS	mandatory
	DESCRIPTION	"Identifies the unique PROM identifier." 
	::= {attributes 1}

-- N_CMOS.O_HSTYPE ========================================================

sysTypeGroup    OBJECT IDENTIFIER ::= {attributes 2}

sysSoftwareType OBJECT-TYPE
	SYNTAX	INTEGER {
		marathon(1),
		netrunner(2)
		}
	ACCESS	read-only
	STATUS	mandatory
	DESCRIPTION	"Identifies the software base type running on the Integration unit." 
	::= {sysTypeGroup 1}

sysHardwareType OBJECT-TYPE
	SYNTAX	INTEGER {
		unknown (1),
		fiftyECCM (2),
		oneKCCM (3),
		fiveKCCM (4),
		tenKCCM (5),
		fiveKTurboCCM (6),
		twentyKCCM (7),
		seventyfiveECCM (8),
		seventyfiveEwithFR (9),
		twoKCCM (10),
		threeK (11),
		twoKTPro (12),
		fiveKTPro (13),
		twentyKPro (14)
		}
	ACCESS	read-only
	STATUS	mandatory
	DESCRIPTION	"Identifies the type of CCM module present in the Integration unit." 
	::= {sysTypeGroup 2}

sysOperationalType OBJECT-TYPE
	SYNTAX	INTEGER {
		node (1),
		feeder (2)
		}
	ACCESS	read-only
	STATUS	mandatory
	DESCRIPTION	"Identifies the operational type of the Integration unit as node 
			or feeder." 
	::= {sysTypeGroup 3}

sysSoftwarePhase OBJECT-TYPE
	SYNTAX	INTEGER {
		phase3dot0 (1),
		phase3dot1 (2),
		phase3dot2 (3),
		phase3dot2C (4),
		phase4dot0 (5),
		phase4dot1 (6),
		phase4dot2 (7),
		phase4dot1G (8),
		phase4dot2c (9),
		phase4dot3 (10),
		phase5dot0 (11),
		phase4dot3BorC (12),
		phase5dot0B (13),
		aboveKnownPhases (999)
		}
	ACCESS	read-only
	STATUS	mandatory
	DESCRIPTION	"Identifies the revision of the operating software running on 
			the node." 
	::= {sysTypeGroup 4}

sysFeatureType OBJECT-TYPE
	SYNTAX	INTEGER {
		featurePak (1),
		dualBank (2),
		singleBank (3),
		simSingleDual (4)
		}
	ACCESS	read-only
	STATUS	mandatory
	DESCRIPTION	"Identifies the type of the feature pack installed on the unit." 
	::= {sysTypeGroup 5}

sysFeatureRTC OBJECT-TYPE
	SYNTAX	INTEGER {
		present (1),
		notPresent (2)
		}
	ACCESS	read-only
	STATUS	mandatory
	DESCRIPTION	"Identifies whether or not the real time clock is present on the unit.
			Note that NMS modules are available with RTC." 
	::= {sysTypeGroup 6}

-- N_CMOS.O_NODNAM ========================================================

sysLocNodeLinkTable OBJECT-TYPE
	SYNTAX	SEQUENCE OF SysLocNodeLinkEntry
	ACCESS	not-accessible
	STATUS	mandatory
	DESCRIPTION	"Table containing MB-Feeder connection information." 
	::= {attributes 3}

sysLocNodeLinkEntry OBJECT-TYPE
	SYNTAX	SysLocNodeLinkEntry
	ACCESS	not-accessible
	STATUS	mandatory
	DESCRIPTION	"Entry within the table identifying the name, type, and number
			of connected MB-Feeder (if any)." 
	INDEX		{sysLocNodeLinkIndex}
	::= {sysLocNodeLinkTable 1}

SysLocNodeLinkEntry ::= SEQUENCE {
	sysLocNodeLinkIndex			INTEGER,
	sysLocNodeLinkNodeNameOfFeeder	DisplayString,
	sysLocNodeLinkNodeType		INTEGER,
	sysLocNodeLinkNodeNumber		INTEGER
	}

sysLocNodeLinkIndex OBJECT-TYPE
	SYNTAX	INTEGER (1..6)
	ACCESS	read-only
	STATUS	mandatory
	DESCRIPTION	"Instances into the table for each (1-6) link entry." 
	 ::= {sysLocNodeLinkEntry 1}

sysLocNodeLinkNodeNameOfFeeder OBJECT-TYPE
	SYNTAX	DisplayString (SIZE(0..8))
	ACCESS	read-only
	STATUS	mandatory
	DESCRIPTION	"Indicates the name of the connected (if any) feeder to a 
			particular port." 
	 ::= {sysLocNodeLinkEntry 2}

sysLocNodeLinkNodeType OBJECT-TYPE
	SYNTAX	INTEGER {
		notConfigured (1),
		marathon (2),
		mbFeeder (3)
		}
	ACCESS	read-only
	STATUS	mandatory
	DESCRIPTION	"Identifies whether or not the MB-Feeder is connected to
			a particular port." 
	 ::= {sysLocNodeLinkEntry 3}

sysLocNodeLinkNodeNumber OBJECT-TYPE
	SYNTAX	INTEGER (0..255)
	ACCESS	read-only
	STATUS	mandatory
	DESCRIPTION	"Indicates the number of the connected (if any) feeder to a 
			particular port. A value of zero represent that the feeder is 
			not present." 
	 ::= {sysLocNodeLinkEntry 4}


-- N_CMOS.O_DATTIM ======================================================

sysDateTime OBJECT-TYPE
	SYNTAX	OCTET STRING (SIZE (7))
	ACCESS	read-write
	STATUS	mandatory
	DESCRIPTION	"Sets the current date and the time on the unit.  Format (byte 
			sequence) is Month, Day, Hour, Minutes, Seconds, Day of Week, Year." 
	::= { attributes 4}


-- N_CMOS. O_RCLASS ========================================================

sysClassCfgTable OBJECT-TYPE
	SYNTAX	SEQUENCE OF SysClassCfgEntry
	ACCESS	not-accessible
	STATUS	mandatory
	DESCRIPTION	"Table to configure a class. Class is defined as a port or grouping
			of ports dedicated to a specific application or location." 
	::= {attributes 5}

sysClassCfgEntry OBJECT-TYPE
	SYNTAX	SysClassCfgEntry
	ACCESS	not-accessible
	STATUS	mandatory
	DESCRIPTION	"An entry into the table for a specific class number." 
	INDEX		{sysClassCfgClassNumber}
	 ::= {sysClassCfgTable 1}

SysClassCfgEntry ::= SEQUENCE {
	sysClassCfgClassNumber		INTEGER,
	sysClassCfgClassName		DisplayString,
	sysClassCfgClassSecondary	INTEGER,
	sysClassCfgClassMessage		DisplayString,
	sysClassCfgClassPassword	DisplayString,
	sysClassCfgNoActivityTimeOut	INTEGER,
	sysClassCfgEntryStatus		INTEGER
	}

sysClassCfgClassNumber OBJECT-TYPE
	SYNTAX	INTEGER (1..64)
	ACCESS	read-write
	STATUS	mandatory
	DESCRIPTION	"The available class to be configured numbered from 1 to 64." 
	 ::= {sysClassCfgEntry 1}

sysClassCfgClassName OBJECT-TYPE
	SYNTAX	DisplayString  (SIZE (2..8))
	ACCESS	read-write
	STATUS	mandatory
	DESCRIPTION	"Assigns a class name to a selected class number. Class name
			can be up to eight characters long and may use characters A-Z, 
			0-9, and _." 
	 ::= {sysClassCfgEntry 2}

sysClassCfgClassSecondary OBJECT-TYPE
	SYNTAX	INTEGER (0..64)
	ACCESS	read-write
	STATUS	mandatory
	DESCRIPTION	"The designated secondary class to the specified class used to 
			automatically route connections to this class if the primary
			class channels are busy." 
	 ::= {sysClassCfgEntry 3}

sysClassCfgClassMessage OBJECT-TYPE
	SYNTAX	DisplayString  (SIZE (0..61))
	ACCESS	read-write
	STATUS	mandatory
	DESCRIPTION	"Displays (on command facility) when the user connects to 
			a port within the class." 
	::= {sysClassCfgEntry 4}

sysClassCfgClassPassword OBJECT-TYPE
	SYNTAX	DisplayString  (SIZE (0..8))
	ACCESS	write-only
	STATUS	mandatory
	DESCRIPTION	"Protects the access to a particular class. The default is no
			password (NULL Password)." 
	::= {sysClassCfgEntry 5}

sysClassCfgNoActivityTimeOut OBJECT-TYPE
	SYNTAX	INTEGER (0..255)
	ACCESS	read-write
	STATUS	mandatory
	DESCRIPTION	"The no activity feature monitors the class channel.  After a
			specified period of time, if there is no activity on the channel, it
			will be disconnected. Value 0 = disabled; values 1-255 = the timeout
			interval in minutes." 
	::= {sysClassCfgEntry 6}

sysClassCfgEntryStatus OBJECT-TYPE
	SYNTAX	INTEGER {
		active (1),
		notInService (2),
		notReady (3),
		createAndWait (5),
		destroy (6)
		}
	ACCESS	read-write
	STATUS	mandatory
	DESCRIPTION	"Object to create conceptual row entry in the table.  Internally used
			to cache all the column objects till the commit is done through active(1).
			Option 6 (destroy) deletes the entry (class) from the configured classes." 
	::= { sysClassCfgEntry 7}

-- N_CMOS.O_ACCNOD ========================================================

sysAccessNodeName OBJECT-TYPE
	SYNTAX	DisplayString (SIZE (0..8))
	ACCESS	read-write
	STATUS	mandatory
	DESCRIPTION	"This is the name of the node which has been selected as the
				access point for the MICOMVision Manager in the Network.
				Configuring this object for a node results in the MICOM Alarms
				being forwarded to this specified Access node and the NMS system
				being informed of pending alarms awaiting retrieval."
	 ::= {attributes 6}

-- N_CMOS.O_FLASH ========================================================

sysFlashDownloadGroup  OBJECT IDENTIFIER ::= { attributes 7}

sysFlashDownloadPassword OBJECT-TYPE
	SYNTAX	DisplayString  (SIZE(0..8))
	ACCESS	write-only
	STATUS	mandatory
	DESCRIPTION	"Configures the security password for the download facility." 
	::= {sysFlashDownloadGroup 1}

sysFlashDownloadUseFile OBJECT-TYPE
	SYNTAX	INTEGER {
		mostRecent(1),
		useFileOne (2),
		useFileTwo (3)
		}
	ACCESS	read-write
	STATUS	mandatory
	DESCRIPTION	"Configures which Flash Bank that will be loaded from when the
				marathon is reset to re-load from flash." 
	::= {sysFlashDownloadGroup 2}

sysFlashDownloadDataActivityTimeout OBJECT-TYPE
	SYNTAX	INTEGER
	ACCESS	read-write
	STATUS	mandatory
--	DEFVAL	2
	DESCRIPTION	"Configures the Data Activity Timeout to be used while downloading
				an image to Flash Memory.  The range is 30 - 240 seconds." 
	::= {sysFlashDownloadGroup 3}

-- N_CMOS.O_MESH ======================================================

sysMeshRouting OBJECT-TYPE
	SYNTAX	INTEGER {
		enable (1),
		disable (2)
		}
	ACCESS	read-write
	STATUS	mandatory
	DESCRIPTION	"Configures whether mesh routing is enabled for this Integration unit." 
	::= {attributes 8}

-- N_CMOS.O_BOOTID ======================================================

sysBootID OBJECT-TYPE
	SYNTAX	DisplayString (SIZE (1..18)) 
	ACCESS	read-only
	STATUS	mandatory
	DESCRIPTION	"Indicates the boot identifier if boot prom is present." 
	::= {attributes 9}

-- N_CMOS.O_NETTIM ======================================================

sysNetTime OBJECT-TYPE
	SYNTAX	OCTET STRING (SIZE (7))
	ACCESS	read-write
	STATUS	mandatory
	DESCRIPTION	"The date and time to be configured on all the Integration units 
			on the network.  Format (byte sequence) is Month, Day, Hour, Minutes,
			Seconds, Day of Week, Year." 
	::= { attributes 10}

--CODE DOWNLOD ======================================================

sysCodeDownloadGroup  OBJECT IDENTIFIER ::= { attributes 11}

sysCodeDownloadType OBJECT-TYPE
	SYNTAX	INTEGER {
		ccmBase (1),
		voiceModule (2),
		tamModule (3),
		eamModule (4),
		eli2Module (5)
		}
	ACCESS	read-write
	STATUS	mandatory
	DESCRIPTION	"Identifies the type of Code Download that is to be performed."
	::= { sysCodeDownloadGroup 1}

sysCodeDownloadNodeName OBJECT-TYPE
	SYNTAX	DisplayString (SIZE(1..8))
	ACCESS	read-write
	STATUS	mandatory
	DESCRIPTION	"The name of the node to which software is to be downloaded." 
	::= { sysCodeDownloadGroup 2}

sysCodeDownloadSlotNumber OBJECT-TYPE
	SYNTAX	INTEGER (1..5)
	ACCESS	read-write
	STATUS	mandatory
	DESCRIPTION	"The slot number of the module to which software is to be downloaded." 
	::= { sysCodeDownloadGroup 3}

sysCodeDownloadChannelNumber OBJECT-TYPE
	SYNTAX	INTEGER
	ACCESS	read-write
	STATUS	mandatory
	DESCRIPTION	"The Voice Channel number to which software is to be downloaded. 
			Only valid for Voice." 
	::= { sysCodeDownloadGroup 4}

sysCodeDownloadImageFile OBJECT-TYPE
	SYNTAX	DisplayString (SIZE(0..15))
	ACCESS	read-write
	STATUS	mandatory
	DESCRIPTION	"The name of the code image file to be downloaded." 
	::= { sysCodeDownloadGroup 5}

sysCodeDownloadFlashBank OBJECT-TYPE
	SYNTAX	INTEGER (1..2)
	ACCESS	read-write
	STATUS	mandatory
	DESCRIPTION	"The destination flash bank to be downloaded.
			Only for CCM download." 
	::= { sysCodeDownloadGroup 6}

sysCodeDownloadRestartFromBank OBJECT-TYPE
	SYNTAX	INTEGER {
		bankOne (1),
		bankTwo (2),
		mostRecent (3)
		}
	ACCESS	read-write
	STATUS	mandatory
	DESCRIPTION	"Identifies the subsequent flash bank to be started from. 
			Only for CCM download." 
	::= { sysCodeDownloadGroup 7}

sysCodeDownloadReset OBJECT-TYPE
	SYNTAX	INTEGER {
		resetAfterDownload (1),
		dontResetAfterDownload (2)
		}
	ACCESS	read-write
	STATUS	mandatory
	DESCRIPTION	"Value of 1 identifies that the reset of the module/node 
			is required after successful download." 
	::= { sysCodeDownloadGroup 8}

sysCodeDownloadActionStatus OBJECT-TYPE
	SYNTAX	INTEGER
	ACCESS	read-write
	STATUS	mandatory
	DESCRIPTION	"Option 0 initiates a request for the code download. The status 
			of the process is conveyed via options 1 through n." 
	::= { sysCodeDownloadGroup 9}

sysCodeDownloadFileSize OBJECT-TYPE
	SYNTAX	INTEGER 
	ACCESS	read-only
	STATUS	mandatory
	DESCRIPTION	"This is the Total Number of Bytes in the image file that is being 
			downloaded.  Valid only after a download has started." 
	::= { sysCodeDownloadGroup 10}

sysCodeDownloadBytesDownloaded OBJECT-TYPE
	SYNTAX	INTEGER 
	ACCESS	read-only
	STATUS	mandatory
	DESCRIPTION	"This is the Total Number of Bytes that have been sent to the Integration
			unit.  Upon completion, this should equal the sysCodeDownloadFileSize
			paramater.  Valid only after a download has been started." 
	::= { sysCodeDownloadGroup 11}

sysCodeDownloadNodeNumber OBJECT-TYPE
	SYNTAX	INTEGER 
	ACCESS	read-write
	STATUS	mandatory
	DESCRIPTION	"The numeric value (Node ID #) that represents this node in the network." 
	::= { sysCodeDownloadGroup 12}

-- System Messages Group

-- This groups configures dialog messages which are asynchronous, configurable messages
-- and prompts displayed for information, configuration or requesting inputs on the command
-- line facility

-- N_CMOS.O_WELCM ======================================================

sysMessageWelcome OBJECT-TYPE
	SYNTAX	DisplayString  (SIZE(1..61))
	ACCESS	read-write
	STATUS	mandatory
	DESCRIPTION	"Displays when the user first successfully connects to the Integration unit." 
	 ::= {messages 1}

-- N_CMOS.O_CHPMS ======================================================

sysMessageChannelPasswd OBJECT-TYPE
	SYNTAX	DisplayString  (SIZE(1..31))
	ACCESS	read-write
	STATUS	mandatory
	DESCRIPTION	"Prompts the user for the password associated for the sign-on
			channel. This is the first dialog message that appears when the
			user attempts to connect to the network from the command 
			line facility." 
	::= { messages 2}

-- N_CMOS.O_CLREQ ======================================================

sysMessageClassRequest OBJECT-TYPE
	SYNTAX	DisplayString  (SIZE(1..31))
	ACCESS	read-write
	STATUS	mandatory
	DESCRIPTION	"Prompts (at the command facility line) the async channel 
			user for the destination class or channel." 
	 ::= { messages 3}

-- N_CMOS.O_CONMS ======================================================

sysMessageConnected OBJECT-TYPE
	SYNTAX	DisplayString  (SIZE(1..31))
	ACCESS	read-write
	STATUS	mandatory
	DESCRIPTION	"Displays (on the command facility line) when a connection 
			to any resource (class or matrix switch) has been established
			across an interconnect link ." 
	 ::= { messages 4}

-- N_CMOS.O_QUEMS ======================================================

sysMessageQueued OBJECT-TYPE
	SYNTAX	DisplayString  (SIZE(1..17))
	ACCESS	read-write
	STATUS	mandatory
	DESCRIPTION	"Displays (on the command facility line) when a user is waiting 
			far a channel in wait queue." 
	 ::= { messages 5}

-- N_CMOS.O_DISMS ======================================================

sysMessageDisconnected OBJECT-TYPE
	SYNTAX	DisplayString  (SIZE(1..17))
	ACCESS	read-write
	STATUS	mandatory
	DESCRIPTION	"Displays (on the command facility line) when the connection
			has been broken. It is only sent to the call originator using
			switching (This is not for force connections)." 
	 ::= { messages 6}

-- N_CMOS.O_CALMS ======================================================

sysMessageCallInProgress OBJECT-TYPE
	SYNTAX	DisplayString  (SIZE(1..17))
	ACCESS	read-write
	STATUS	mandatory
	DESCRIPTION	"Displays (on the command facility line) while the call is in
			process of being connected." 
	 ::= { messages 7}

-- N_CMOS.O_NAWMS ======================================================

sysMessageNoAnswer OBJECT-TYPE
	SYNTAX	DisplayString  (SIZE(1..17))
	ACCESS	read-write
	STATUS	mandatory
	DESCRIPTION	"Displays (on the command facility line) when there is no
			answer from the destination port." 
	 ::= { messages 8}

-- N_CMOS.O_UNAMS ======================================================

sysMessageUnassigned OBJECT-TYPE
	SYNTAX	DisplayString  (SIZE(1..17))
	ACCESS	read-write
	STATUS	mandatory
	DESCRIPTION	"Displays (on the command facility line) when a node, class 
			or channel is unknown in the network." 
	 ::= { messages 9}

-- N_CMOS.O_UAVMS ======================================================

sysMessageUnavailable OBJECT-TYPE
	SYNTAX	DisplayString  (SIZE(1..17))
	ACCESS	read-write
	STATUS	mandatory
	DESCRIPTION	"Displays (on the command facility line) when a user request 
			a resource which exists, but is not in service (operational)." 
	 ::= {messages 10}

-- N_CMOS.O_BSYMS ======================================================

sysMessageBusy OBJECT-TYPE
	SYNTAX	DisplayString  (SIZE(1.. 17))
	ACCESS	read-write
	STATUS	mandatory
	DESCRIPTION	"Displays (on the command facility line) only to the user using 
			matrix switching when the requested resource is in use." 
	 ::= { messages 11}

-- N_CMOS.O_INCMS ======================================================

sysMessageIncompatible OBJECT-TYPE
	SYNTAX	DisplayString  (SIZE(1.. 17))
	ACCESS	read-write
	STATUS	mandatory
	DESCRIPTION	"Displays (on the command facility line) for any attempted 
			connection that is not compatible with the configuration." 
	 ::= { messages 12}

-- N_CMOS.O_CLPMS ======================================================

sysMessageClassPasswd OBJECT-TYPE
	SYNTAX	DisplayString  (SIZE(1..31))
	ACCESS	read-write
	STATUS	mandatory
	DESCRIPTION	"Prompts (on the command facility line) for the password
			of the requested class." 
	 ::= { messages 13}

-- N_CMOS.O_LCDBAN ======================================================

sysMessageLCDKeypadBanner OBJECT-TYPE
	SYNTAX	DisplayString  (SIZE(1..20))
	ACCESS	read-write
	STATUS	mandatory
	DESCRIPTION	"Displays the banner string on the LCD keypad." 
	 ::= { messages 14}



-- CARD GROUP

-- N_CMOS.O_MCARDS =======================================================

cardTable OBJECT-TYPE
	SYNTAX	SEQUENCE OF CardEntry
	ACCESS	not-accessible
	STATUS	mandatory
	DESCRIPTION	"Table to view the hardware configuration of the Integration unit." 
	::= {card 1}

cardEntry OBJECT-TYPE
	SYNTAX	CardEntry
	ACCESS	not-accessible
	STATUS	mandatory
	DESCRIPTION	"Entry pertaining to the present module(s)." 
	INDEX		{cardSlotNumber}
	::= {cardTable 1}

CardEntry ::= SEQUENCE {
	cardSlotNumber		INTEGER,
	cardModuleID		INTEGER,
	cardPcbRevision		INTEGER
	}

cardSlotNumber OBJECT-TYPE
	SYNTAX	INTEGER {
		slotA (1),
		slotB (2),
		slotC (3),
		slotD (4),
		slotE (5),
		slotNMS (6)
		}
	ACCESS	read-only
	STATUS	mandatory
	DESCRIPTION	"Identifies the location of the module within the unit." 
	::= {cardEntry 1}

cardModuleID OBJECT-TYPE
	SYNTAX	INTEGER {
		modCcmDmaESD (1),
		modCcmDmaDual20Mhz (2),
		mod5kCcm (4),
		mod5kCcmwESD (5),
		mod5kCcmOem (6),
		modNMS (8),
		modNMS-RTC (9),
		mod1kCcm (12),
		mod50ECcm (13),
		mod1kCcmOem (14),
		mod50ECcmOem (15),
		mod10kCcm (16),
		mod10kCcmOem (18),
		mod20kCcm (20),
		mod5kTurboCcm (24),
		mod5kTurboProCcm (28),
		mod20kProCcm (36),
		modCEM12Async-1D (48),
		modCEM12Async-1DwESD (49),
		modCEM12Async-LD (52),
		modCEM12Async-LDwESD (53),
		modCEM6SyncAsync (56),
		modCEM6SyncAsync-ESD (57),
		modCEM6SyncAsyncDma (60),
		modCEM6SyncAsyncDma-ESD (61),
		modCEM32-IDD2x16 (64),
		modCEM6AsyncOnly (68),
		modCEM32-IDD (72),
		mod75ECcm-FrameRelay (76),
		mod75ECcm-FrameRelayOEM (78),
		mod2kCcm (80),
		mod2kCcmOEM (82),
		mod3kCcmSingleVoice (84),
		mod3kCcmDualVoice (85),
		mod75ECcm (92),
		mod75ECcmOEM (94),
		modVoice-1-chan (96),
		modVoice-2-chan (97),
		modVoice-1-chan-International (104),
		modVoice-2-chan-International (105),
		modVoice-1-chan-UVM (108),
		modVoice-2-chan-UVM (109),
		modDigitalVoiceExp (112),
		modVoice-1-chan-TUVM (116),
		modVoice-2-chan-TUVM (117),
		modVoice-1-chan-CVM (120),
		modVoice-2-chan-CVM (121),
		mod2kTurboCcm (156),
		modLan-eli-1 (320),
		modLan-eli-1-DualProc (321),
		modLan-eli-2 (322),
		modLan-RemoteLanRouter (340),
		modLan-RemoteLanRouter-LowCost (344),
		modIsdnMultipleBri (1000),
		modIsdnSingleBri (1001),
		modE1AccessDualPort (992),
		modE1AccessSinglePort (993),
		modE1AccessDualPortNoLinks (994),
		modE1AccessSinglePortNoLinks (995),
		modT1AccessDualPort (996),
		modT1AccessSinglePort (997),
		modT1AccessDualPortNoLinks (998),
		modT1AccessSinglePortNoLinks (999),
		modModem14dot4Kb (1005),
		modModem9dot6Kb (1008),
		modModem12dot4KbParadyne (1009),
		modModem19dot2KbParadyne (1010),
		modIsu-1-chan (1012),
		modIsu-2-chan (1013),
		modCEM6Dma (1016)
		}
	ACCESS	read-only
	STATUS	mandatory
	DESCRIPTION	"Identifies the part number of the module in the specific location.
			0FFFFh if no NMS card installed, 03ffh if no card installed." 
	::= {cardEntry 2}

cardPcbRevision OBJECT-TYPE
	SYNTAX	INTEGER {
		revA (1),
		revB (2),
		revC (3),
		revD (4),
		revE (5),
		revF (6),
		revG (7),
		revH (8),
		revI (9),
		revJ (10),
		revK (11),
		revL (12),
		revM (13),
		revN (14),
		revO (15),
		revP (16),
		revQ (17),
		revR (18),
		revS (19),
		revT (20),
		revU (21),
		revV (22),
		revW (23),
		revX (24),
		revY (25),
		revZ (26),
		revAA (27),
		revAB (28),
		revAC (29),
		revAD (30),
		revAE (31),
		revAF (32),
		revAG (33),
		revAH (34),
		revAI (35),
		revAJ (36),
		revAK (37),
		revAL (38),
		revAM (39),
		revAN (40),
		revAO (41),
		revAP (42),
		revAQ (43),
		revAR (44),
		revAS (45),
		revAT (46),
		revAU (47),
		revAV (48),
		revAW (49),
		revAX (50),
		revAY (51),
		revAZ (52),
		rev1 (53),
		rev2 (54),
		rev3 (55),
		rev4 (56),
		rev5 (57),
		rev6 (58),
		rev7 (59),
		rev8 (60),
		rev9 (61),
		rev10 (62),
		rev11 (63),
		rev12 (64)
		}
	ACCESS	read-only
	STATUS	mandatory
	DESCRIPTION	"Identifies the revision level of the module. 0ffh if no NMS card
			installed, 03Fh if no card installed." 
	::= {cardEntry 3}


-- NUMBER of cards in a node

numberOfCards OBJECT-TYPE
	SYNTAX	INTEGER (1..6)
	ACCESS	read-only
	STATUS	mandatory
	DESCRIPTION	"The total number of cards installed in the Integration unit." 
	::= {card 2}

-- N_CMOS.O_LANTYP ========================================================

eliCardFunctionTable OBJECT-TYPE
	SYNTAX	SEQUENCE OF EliCardFunctionEntry
	ACCESS	not-accessible
	STATUS	mandatory
	DESCRIPTION	"Table containing the functionality on resident eli cards (if any)." 
	::= {card 3}

eliCardFunctionEntry OBJECT-TYPE
	SYNTAX	EliCardFunctionEntry
	ACCESS	not-accessible
	STATUS	mandatory
	DESCRIPTION	"Entry within the table to specify a particular slot where an eli
			card is located." 
	INDEX		{eliCardFunctionSlotNumber}
	::= {eliCardFunctionTable 1}

EliCardFunctionEntry ::= SEQUENCE {
	eliCardFunctionSlotNumber		INTEGER,
	eliCardFunctionPromID			DisplayString,
	eliCardFunctionTypeRTSFunction		INTEGER,
	eliCardFunctionTypeBridgeFunction	INTEGER,
	eliCardFunctionTypeRouterFunction	INTEGER,
	eliCardFunctionFlashMemory		INTEGER
	}

eliCardFunctionSlotNumber OBJECT-TYPE
	SYNTAX	INTEGER (2..5)
	ACCESS	read-only
	STATUS	mandatory
	DESCRIPTION	"The slot number of the eli card." 
	  ::= {eliCardFunctionEntry 1}

eliCardFunctionPromID OBJECT-TYPE
	SYNTAX	DisplayString  (SIZE(0..8))
	ACCESS	read-only
	STATUS	mandatory
	DESCRIPTION	"The prom part number of the software that is installed and
				running on the eli card." 
	  ::= {eliCardFunctionEntry 2}

eliCardFunctionTypeRTSFunction OBJECT-TYPE
	SYNTAX	INTEGER {
		on (1),
		off (2)
		}
	ACCESS	read-only
	STATUS	mandatory
	DESCRIPTION	"Identifies whether this eli card performs the function of
				an RTS or not." 
	  ::= {eliCardFunctionEntry 3}

eliCardFunctionTypeBridgeFunction OBJECT-TYPE
	SYNTAX	INTEGER {
		on (1),
		off (2)
		}
	ACCESS	read-only
	STATUS	mandatory
	DESCRIPTION	"Identifies whether this eli card performs the function of
				a bridge or not." 
	  ::= {eliCardFunctionEntry 4}

eliCardFunctionTypeRouterFunction OBJECT-TYPE
	SYNTAX	INTEGER {
		on (1),
		off (2)
		}
	ACCESS	read-only
	STATUS	mandatory
	DESCRIPTION	"Identifies whether this eli card performs the function of
				a router or not." 
	  ::= {eliCardFunctionEntry 5}

eliCardFunctionFlashMemory OBJECT-TYPE
	SYNTAX	INTEGER {
		on (1),
		off (2)
		}
	ACCESS	read-only
	STATUS	mandatory
	DESCRIPTION	"Identifies whether this eli card contains flash memory or not." 
	  ::= {eliCardFunctionEntry 6}

-- N_CMOS.O_T1TYPE ======================================================

t1e1CardSoftwareInfoTable OBJECT-TYPE
	SYNTAX	SEQUENCE OF T1e1CardSoftwareInfoEntry
	ACCESS	not-accessible
	STATUS	mandatory
	DESCRIPTION	"Table describing the software on resident (if any) T1 or E1 card." 
	::= {card 4}

t1e1CardSoftwareInfoEntry OBJECT-TYPE
	SYNTAX	T1e1CardSoftwareInfoEntry 
	ACCESS	not-accessible
	STATUS	mandatory
	DESCRIPTION	"Entry within the table to specify a particular T1 or E1 card." 
	INDEX		{t1e1CardSoftwareInfoCardNumber}
	 ::= {t1e1CardSoftwareInfoTable 1}

T1e1CardSoftwareInfoEntry ::= SEQUENCE {
	t1e1CardSoftwareInfoCardNumber		INTEGER,
	t1e1CardSoftwareInfoCardType		INTEGER,
	t1e1CardSoftwareInfoReleaseLevel		INTEGER,
	t1e1CardSoftwareInfoSoftwareID		DisplayString,
	t1e1CardSoftwareInfoBootCode		DisplayString
	}

t1e1CardSoftwareInfoCardNumber OBJECT-TYPE
	SYNTAX	INTEGER (2..5)
	ACCESS	read-only
	STATUS	mandatory
	DESCRIPTION	"Displays the Card number of the T1 or E1 module." 
	::= { t1e1CardSoftwareInfoEntry 1}

t1e1CardSoftwareInfoCardType OBJECT-TYPE
	SYNTAX	INTEGER {
		t1 (1),
		e1 (2)
		}
	ACCESS	read-only
	STATUS	mandatory
	DESCRIPTION	"Displays the access module type; T1 or E1." 
	::= { t1e1CardSoftwareInfoEntry 2}

t1e1CardSoftwareInfoReleaseLevel OBJECT-TYPE
	SYNTAX	INTEGER {
		releaseZero (1),
		releaseOne (2),
		releaseTwo (3)
		}
	ACCESS	read-only
	STATUS	mandatory
	DESCRIPTION	"Displays which Software release is installed on the T1/E1 card." 
	::= { t1e1CardSoftwareInfoEntry 3}

t1e1CardSoftwareInfoSoftwareID OBJECT-TYPE
	SYNTAX	DisplayString
	ACCESS	read-only
	STATUS	mandatory
	DESCRIPTION	"Displays which Software part number is installed on the T1/E1 card." 
	::= { t1e1CardSoftwareInfoEntry 4}

t1e1CardSoftwareInfoBootCode OBJECT-TYPE
	SYNTAX	DisplayString 
	ACCESS	read-only
	STATUS	mandatory
	DESCRIPTION	"Displays which boot prom part number is installed on the T1/E1 card." 
	::= { t1e1CardSoftwareInfoEntry 5}

-- PORT GROUP

portCfgTable OBJECT-TYPE
	SYNTAX	SEQUENCE OF PortCfgEntry
	ACCESS	not-accessible
	STATUS	mandatory
	DESCRIPTION	"Table to establish the type of port connection to be assigned to
			the selected port." 
	::= {port 1}

portCfgEntry OBJECT-TYPE
	SYNTAX	PortCfgEntry
	ACCESS	not-accessible
	STATUS	mandatory
	DESCRIPTION	"Entry into the table for the selected port." 
	INDEX		{portCfgCardNumber, portCfgChannelNumber}
	::= {portCfgTable 1}

PortCfgEntry ::= SEQUENCE {
	portCfgCardNumber		INTEGER,
	portCfgChannelNumber		INTEGER,
	portCfgChannelType		INTEGER
	}

portCfgCardNumber OBJECT-TYPE
	SYNTAX	INTEGER (1..5)
	ACCESS	read-only
	STATUS	mandatory
	DESCRIPTION	"Indicates the card/module of the channel to be configured." 
	::= {portCfgEntry 1}

portCfgChannelNumber OBJECT-TYPE
	SYNTAX	INTEGER (1..6)
	ACCESS	read-only
	STATUS	mandatory
	DESCRIPTION	"Indicates the channel/port number to be configured." 
	::= {portCfgEntry 2}

portCfgChannelType OBJECT-TYPE
	SYNTAX	INTEGER {
		mux (1),
		async (2),
		sync (3),
		esi (4),
		x21 (5),
		localEsi (6),
		esiSecondary (7),
		frameRelay (8)
		}
	ACCESS	write-only
	STATUS	mandatory
	DESCRIPTION	"Assigns the type of connection to the selected port.
			Note:  A node reset is required after setting the port
			configuration.  Also note that if a channel is currently
			connected, forced or switch connected, the channel must first
			be disconnected.  The procedure to do this would be to place
			the channel out of service (chControlCommand disable(2)), then
			disconnect (chControlCommand forceDIsconnect(4)) the channel." 
	::= {portCfgEntry 3}


syncPortCfgTable OBJECT-TYPE
	SYNTAX	SEQUENCE OF SyncPortCfgEntry
	ACCESS	not-accessible
	STATUS	mandatory
	DESCRIPTION	"Table to configure the protocol for the specified sync channel." 
	::= {port 2}

syncPortCfgEntry OBJECT-TYPE
	SYNTAX	SyncPortCfgEntry
	ACCESS	not-accessible
	STATUS	mandatory
	DESCRIPTION	"Entry into the table specifying a particular channel on a particular
			module/card." 
	INDEX		{syncPortCfgCardNumber, syncPortCfgChannelNumber}
	::= {syncPortCfgTable 1} 

SyncPortCfgEntry ::= SEQUENCE {
	syncPortCfgCardNumber			INTEGER,
	syncPortCfgChannelNumber		INTEGER,
	syncPortCfgProtocol			INTEGER
	}

syncPortCfgCardNumber OBJECT-TYPE
	SYNTAX	INTEGER (1..5)
	ACCESS	read-only
	STATUS	mandatory
	DESCRIPTION	"Identifies the card/module of the sync channel to be configured." 
	::= {syncPortCfgEntry 1}

syncPortCfgChannelNumber OBJECT-TYPE
	SYNTAX	INTEGER (1..6)
	ACCESS	read-only
	STATUS	mandatory
	DESCRIPTION	"Indicates the sync channel number to be configured." 
	::= {syncPortCfgEntry 2}

syncPortCfgProtocol OBJECT-TYPE
	SYNTAX	INTEGER {
		dlcChannel (1),
		asciiBisync (2),
		ebcdicBisync (3),
		hpSync (4),
		rts (5),
		syncPad (6),
		micomDlc (7),
		micomVoice (8),
		fastPacket (9),
		tdm (10)
		}
	ACCESS	read-write
	STATUS	mandatory
	DESCRIPTION	"Assigns the sync protocol to the selected port. Note: A node reset is
			required after the protocol is configured." 
	::= {syncPortCfgEntry 3}


-- N_CMOS.O_FCMDPT ========================================================

fCmdPortPhyParaTable OBJECT-TYPE
	SYNTAX	SEQUENCE OF FCmdPortPhyParaEntry
	ACCESS	not-accessible
	STATUS	mandatory
	DESCRIPTION	"Table of configurations for the physical parameters of the 
			fixed command port on an NMS module." 
	::= {port 3}

fCmdPortPhyParaEntry OBJECT-TYPE
	SYNTAX	FCmdPortPhyParaEntry
	ACCESS	not-accessible
	STATUS	mandatory
	DESCRIPTION	"Entry within the table to specify the fixed command port
			channel number (2) on an NMS module/card (6)." 
	INDEX	{fCmdPortPhyParaCardNumber, fCmdPortPhyParaChannelNumber}
	::= {fCmdPortPhyParaTable 1}

FCmdPortPhyParaEntry ::= SEQUENCE {
	fCmdPortPhyParaCardNumber		INTEGER,
	fCmdPortPhyParaChannelNumber		INTEGER,
	fCmdPortPhyParaStopBits			INTEGER,
	fCmdPortPhyParaCodeLevel		INTEGER,
	fCmdPortPhyParaDataRate		INTEGER,
	fCmdPortPhyParaEcho			INTEGER,
	fCmdPortPhyParaCRDelay		INTEGER,
	fCmdPortPhyParaLFDelay		INTEGER,
	fCmdPortPhyParaFFDelay			INTEGER,
	fCmdPortPhyParaParity			INTEGER
	}

fCmdPortPhyParaCardNumber  OBJECT-TYPE
	SYNTAX	INTEGER (6)
	ACCESS	read-only
	STATUS	mandatory
	DESCRIPTION	"The card number (=6) of the NMS module containing the fixed cmd port." 
	::= {fCmdPortPhyParaEntry 1}

fCmdPortPhyParaChannelNumber  OBJECT-TYPE
	SYNTAX	INTEGER (2)
	ACCESS	read-only
	STATUS	mandatory
	DESCRIPTION	"The channel number (=2) of the fixed cmd port on the NMS module." 
	::= {fCmdPortPhyParaEntry 2}

fCmdPortPhyParaStopBits	 OBJECT-TYPE
	SYNTAX	INTEGER {
		onebit (1),
		onePointFiveBits (2),
		twoBits (3)
		}
	ACCESS	read-write
	STATUS	mandatory
	DESCRIPTION	"Sets the number of stop-bits inserted at the end of a character." 
	::= {fCmdPortPhyParaEntry 3}

fCmdPortPhyParaCodeLevel OBJECT-TYPE
	SYNTAX	INTEGER {
		fiveBits (1),
		sixBits (2),
		sevenBits (3),
		eightBits (4),
		nineBits (5)
		}
	ACCESS	read-write
	STATUS	mandatory
	DESCRIPTION	"Sets the number of data bits per character. This includes the
			parity bit." 
	::= {fCmdPortPhyParaEntry 4}

fCmdPortPhyParaDataRate OBJECT-TYPE
	SYNTAX	INTEGER {
		abr (1),
		rate50 (2),
		rate75 (3),
		rate110 (4),
		rate134dot5 (5),
		rate150 (6),
		rate200 (7),
		rate225 (8),
		rate300 (9),
		rate600 (10),
		rate1200 (11),
		rate1800 (12),
		rate2400 (13),
		rate3600 (14),
		rate4800 (15),
		rate7200 (16),
		rate9600 (17),
		rate14400 (18),
		rate19200 (19),
		rate28800 (20),
		rate38400 (21)
		}
	ACCESS	read-write
	STATUS	mandatory
	DESCRIPTION	"Sets the data rate in bits per seconds of the fixed command port." 
	::= {fCmdPortPhyParaEntry 5}

fCmdPortPhyParaEcho OBJECT-TYPE
	SYNTAX	INTEGER {
		on (1),
		off (2)
	}
	ACCESS	read-write
	STATUS	mandatory
	DESCRIPTION	"Determines whether the Integration unit should echo input from the terminal
				or not." 
	::= {fCmdPortPhyParaEntry 6}

fCmdPortPhyParaCRDelay OBJECT-TYPE
	SYNTAX	INTEGER (0..99)
	ACCESS	read-write
	STATUS	mandatory
	DESCRIPTION	"Configures the number of character delays that should be introduced
				after each CR (carriage return)." 
	::= {fCmdPortPhyParaEntry 7}

fCmdPortPhyParaLFDelay OBJECT-TYPE
	SYNTAX	INTEGER (0..99)
	ACCESS	read-write
	STATUS	mandatory
	DESCRIPTION	"Configures the number of character delays that should be introduced
				after each LF (line feed)." 
	::= {fCmdPortPhyParaEntry 8}

fCmdPortPhyParaFFDelay OBJECT-TYPE
	SYNTAX	INTEGER (0..99)
	ACCESS	read-write
	STATUS	mandatory
	DESCRIPTION	"Configures the number of chanacter delays that should be introduced
				afer each FF (form feed)." 
	::= {fCmdPortPhyParaEntry 9}

fCmdPortPhyParaParity OBJECT-TYPE
	SYNTAX	INTEGER {
		space (1),
		odd (2),
		even (3),
		mark (4),
		none (5),
		auto (6)
		}
	ACCESS	read-write
	STATUS	mandatory
	DESCRIPTION	"Sets the message and data parity."
	::= {fCmdPortPhyParaEntry 10}


-- N_CMOS.O_LOGPRT ========================================================

logPortPhyParaTable OBJECT-TYPE
	SYNTAX	SEQUENCE OF LogPortPhyParaEntry
	ACCESS	not-accessible
	STATUS	mandatory
	DESCRIPTION	"Table to configure the log port (present on NMS module) 
			parameters." 
	::= {port 4}

logPortPhyParaEntry OBJECT-TYPE
	SYNTAX	LogPortPhyParaEntry
	ACCESS	not-accessible
	STATUS	mandatory
	DESCRIPTION	"Entry within the table to specify the log port
			channel number (1) on an NMS module/card (6)." 
	INDEX		{logPortPhyParaCardNumber, logPortPhyParaChannelNumber}
	::= {logPortPhyParaTable 1}

LogPortPhyParaEntry ::= SEQUENCE {
	logPortPhyParaCardNumber		INTEGER,
	logPortPhyParaChannelNumber		INTEGER,
	logPortPhyParaStopBits			INTEGER,
	logPortPhyParaCodeLevel			INTEGER,
	logPortPhyParaDataRate			INTEGER,
	logPortPhyParaCRDelay			INTEGER,
	logPortPhyParaLFDelay			INTEGER,
	logPortPhyParaFFDelay			INTEGER,
	logPortPhyParaXONChar			INTEGER,
	logPortPhyParaXOFFChar			INTEGER,
	logPortPhyParaFlowControl		INTEGER,
	logPortPhyParaBufferControl		INTEGER,
	logPortPhyParaParity			INTEGER
	}

logPortPhyParaCardNumber  OBJECT-TYPE
	SYNTAX	INTEGER (6)
	ACCESS	read-only
	STATUS	mandatory
	DESCRIPTION	"The card number (=6) of the NMS Module that contains the log port." 
	::= {logPortPhyParaEntry 1}

logPortPhyParaChannelNumber  OBJECT-TYPE
	SYNTAX	INTEGER (1)
	ACCESS	read-only
	STATUS	mandatory
	DESCRIPTION	"The channel number of the log port (=1)." 
	::= {logPortPhyParaEntry 2}

logPortPhyParaStopBits	 OBJECT-TYPE
	SYNTAX	INTEGER {
		oneBit (1),
		onePointFiveBits (2),
		twoBits (3)
		}
	ACCESS	read-write
	STATUS	mandatory
	DESCRIPTION	"Configures the number of stop bits that the Integration unit should
				generate and check for on this channel." 
	::= {logPortPhyParaEntry 3}

logPortPhyParaCodeLevel OBJECT-TYPE
	SYNTAX	INTEGER {
		fiveBits (1),
		sixBits (2),
		sevenBits (3),
		eightBits (4),
		nineBits (5)
		}
	ACCESS	read-write
	STATUS	mandatory
	DESCRIPTION	"Sets the number of data bits per character. This includes the
			parity bit." 
	::= {logPortPhyParaEntry 4}

logPortPhyParaDataRate	 OBJECT-TYPE
	SYNTAX	INTEGER {
		rate50 (2),
		rate75 (3),
		rate110 (4),
		rate134dot5 (5),
		rate150 (6),
		rate200 (7),
		rate300 (9),
		rate600 (10),
		rate1200 (11),
		rate1800 (12),
		rate2400 (13),
		rate3600 (14),
		rate4800 (15),
		rate7200 (16),
		rate9600 (17),
		rate14400 (18),
		rate19200 (19),
		rate28800 (20),
		rate38400 (21)
		}
	ACCESS	read-write
	STATUS	mandatory
	DESCRIPTION	"Sets the data rate in bits per seconds of the log port." 
	::= {logPortPhyParaEntry 5}

logPortPhyParaCRDelay OBJECT-TYPE
	SYNTAX	INTEGER (0..99)
	ACCESS	read-write
	STATUS	mandatory
	DESCRIPTION	"Configures the number of Character Delays required to be
				inserted after each CR (carriage return)." 
	::= {logPortPhyParaEntry 6}

logPortPhyParaLFDelay OBJECT-TYPE
	SYNTAX	INTEGER (0..99)
	ACCESS	read-write
	STATUS	mandatory
	DESCRIPTION	"Configures the number of Character Delays required to be
				inserted after each LF (Line Feed)." 
	::= {logPortPhyParaEntry 7}

logPortPhyParaFFDelay OBJECT-TYPE
	SYNTAX	INTEGER (0..99)
	ACCESS	read-write
	STATUS	mandatory
	DESCRIPTION	"Configures the number of Character Delays required to be
				inserted after each FF (form feed)."
	::= {logPortPhyParaEntry 8}

logPortPhyParaXONChar	 OBJECT-TYPE
	SYNTAX	INTEGER {
		dc1 (1),
		dc2 (2),
		dc3 (3),
		dc4 (4)
		}
	ACCESS	read-write
	STATUS	mandatory
	DESCRIPTION	"Configures which character the Integration unit should check for
				and respond to for stopping data flow on a channel." 
	::= {logPortPhyParaEntry 9}

logPortPhyParaXOFFChar OBJECT-TYPE
	SYNTAX	INTEGER {
		dc1 (1),
		dc2 (2),
		dc3 (3),
		dc4 (4)
		}
	ACCESS	read-write
	STATUS	mandatory
	DESCRIPTION	"Configures which character the Marathon should check for
				and respond to for re-starting data flow on a channel." 
	::= {logPortPhyParaEntry 10}

logPortPhyParaFlowControl OBJECT-TYPE
	SYNTAX	INTEGER {
		none (1),
		xonXof (2),
		dtr (3),
		xonXofDtr (4),
		wangx (5),
		rts (6),
		dataGeneral (7)
		}
	ACCESS	read-write
	STATUS	mandatory
	DESCRIPTION	"Configures which type of flow control should be used
				for the log port." 
	::= {logPortPhyParaEntry 11}

logPortPhyParaBufferControl OBJECT-TYPE
	SYNTAX	INTEGER {
		none (1),
		xonXof (2),
		cts (3),
		wangx (4)
		}
	ACCESS	read-write
	STATUS	mandatory
	DESCRIPTION	"Configures what type of buffer control to be used
				in the communications with the log port." 
	::= {logPortPhyParaEntry 12}

logPortPhyParaParity OBJECT-TYPE
	SYNTAX	INTEGER {
		space (1),
		odd (2),
		even (3),
		mark (4),
		none (5)
		}
	ACCESS	read-write
	STATUS	mandatory
	DESCRIPTION	"Configures what type of parity to use with the log port." 
	::= {logPortPhyParaEntry 13}


-- N_CMOS.O_EXTMDM ======================================================

commandPortExtModemNumber  OBJECT-TYPE
	SYNTAX	DisplayString  (SIZE (0..32))
	ACCESS	read-write
	STATUS	mandatory
	DESCRIPTION	"Modem phone number to call to send ASCII events out." 
	::= {port 5}


-- N_CMOS.O_CMDPRT ======================================================

commandPortDataActivityTimeout  OBJECT-TYPE
	SYNTAX	INTEGER (0..60)
	ACCESS	read-write
	STATUS	mandatory
	DESCRIPTION	"Configures the command facility port inactivity timeout (minutes)." 
	::= {port 6}

-- Pre-Configuration SYNC Port ============================================

syncPortPreConfigTable OBJECT-TYPE
	SYNTAX	SEQUENCE OF SyncPortPreConfigEntry
	ACCESS	not-accessible
	STATUS	mandatory
	DESCRIPTION	"Table to configure a sync channel protocol prior to configuring
			a port as a sync channel. By using this table to 'preset' the sync
			protocol, only 1 node reset is needed following the sync channel
			assignment to complete the configuration." 
	::= {port 7}

syncPortPreConfigEntry OBJECT-TYPE
	SYNTAX	SyncPortPreConfigEntry
	ACCESS	not-accessible
	STATUS	mandatory
	DESCRIPTION	"Entry within the table to specify a particular sync channel for
			pre-configuration on a specific module/card." 
	INDEX		{syncPortPreConfigCardNumber, syncPortPreConfigChannelNumber}
	::= {syncPortPreConfigTable 1} 

SyncPortPreConfigEntry ::= SEQUENCE {
	syncPortPreConfigCardNumber		INTEGER,
	syncPortPreConfigChannelNumber		INTEGER,
	syncPortPreConfigProtocol		INTEGER
	}

syncPortPreConfigCardNumber OBJECT-TYPE
	SYNTAX	INTEGER (1..5)
	ACCESS	read-only
	STATUS	mandatory
	DESCRIPTION	"Identifies the module/card for sync channel pre-configuration." 
	::= {syncPortPreConfigEntry 1}

syncPortPreConfigChannelNumber OBJECT-TYPE
	SYNTAX	INTEGER (1..6)
	ACCESS	read-only
	STATUS	mandatory
	DESCRIPTION	"Identifies the port number for sync channel pre-configuration." 
	::= {syncPortPreConfigEntry 2}

syncPortPreConfigProtocol OBJECT-TYPE
	SYNTAX	INTEGER {
		dlcChannel (1),
		asciiBisync (2),
		ebcdicBisync (3),
		hpSync (4),
		rts (5),
		syncPad (6),
		micomDlc (7),
		micomVoice (8),
		fastPacket (9),
		tdm (10)
		}
	ACCESS	write-only
	STATUS	mandatory
	DESCRIPTION	"The protocol to be used for pre-configuring a sync channel." 
	::= {syncPortPreConfigEntry 3}


-- CHANNEL GROUP

-- N_CMOS.O_SYNCH ========================================================

syncChPhyParaTable OBJECT-TYPE
	SYNTAX	SEQUENCE OF SyncChPhyParaEntry
	ACCESS	not-accessible
	STATUS	mandatory
	DESCRIPTION	"For the configuration of synchronous channels, this table controls
			and modifies the operating parameters for the port." 
	::= {sync-channel 1}

syncChPhyParaEntry OBJECT-TYPE
	SYNTAX	SyncChPhyParaEntry
	ACCESS	not-accessible
	STATUS	mandatory
	DESCRIPTION	"Entry into the table pertaining to a specific sync channel on a
			specific module." 
	INDEX		{syncChPhyParaCardNumber, syncChPhyParaChannelNumber}
	::= {syncChPhyParaTable 1}

SyncChPhyParaEntry ::= SEQUENCE {
	syncChPhyParaCardNumber		INTEGER,
	syncChPhyParaChannelNumber		INTEGER,
	syncChPhyParaDataRate			INTEGER,
	syncChPhyParaCarrierMode		INTEGER,
	syncChPhyParaInterfaceType		INTEGER,
	syncChPhyParaIdleFill			INTEGER,
	syncChPhyParaHighSyncChar		OCTET STRING,
	syncChPhyParaLowSyncChar		OCTET STRING,
	syncChPhyParaNumLeadSyncCount	INTEGER,
	syncChPhyParaMaxTxBlockSize		INTEGER,
	syncChPhyParaPadChar			OCTET STRING,
	syncChPhyParaNumLeadingPads		INTEGER,
	syncChPhyParaNumTrailingPads		INTEGER,
	syncChPhyParaClockFlowControl		INTEGER,
	syncChPhyParaEncoding			INTEGER,
	syncChPhyParaChTxClocking		INTEGER,
	syncChPhyParaChRxClocking		INTEGER,
	syncChPhyParaPriority			INTEGER,
	syncChPhyParaDSRControl		INTEGER,
	syncChPhyParaBufferControl		INTEGER,
	syncChPhyParaMaxRxBlockSize		INTEGER,
	syncChPhyParaProtocol			INTEGER,
	syncChPhyParaClaimedBandwidth		INTEGER,
	syncChPhyParaDLCTransitRate		INTEGER
	}

syncChPhyParaCardNumber OBJECT-TYPE
	SYNTAX	INTEGER (1..5)
	ACCESS	read-only
	STATUS	mandatory
	DESCRIPTION	"The card/module number of the channel this entry pertains to." 
	::= {syncChPhyParaEntry 1}

syncChPhyParaChannelNumber OBJECT-TYPE
	SYNTAX	INTEGER (1..6)
	ACCESS	read-only
	STATUS	mandatory
	DESCRIPTION	"The channel number on a specified module this configuration
			entry pertains to." 
	::= {syncChPhyParaEntry 2}

syncChPhyParaDataRate OBJECT-TYPE
	SYNTAX	INTEGER {
		rate1200 (1),
		rate2400 (2),
		rate3600 (3),
		rate4800 (4),
		rate7200 (5),
		rate9600 (6),
		rate12000 (7),
		rate14400 (8),
		rate16800 (9),
		rate19200 (10),
		rate28800 (11),
		rate38400 (12),
		rate48000 (13),
		rate56000 (14),
		rate64000 (15)
		}
	ACCESS	read-write
	STATUS	mandatory
--	DEFVAL	2
	DESCRIPTION	"Sets data rate in bits per second for the user sync channel. Default 
			is 2400." 
	::= {syncChPhyParaEntry 3}

syncChPhyParaCarrierMode OBJECT-TYPE
	SYNTAX	INTEGER {
		variable (1),
		constant (2)
		}
	ACCESS	read-write
	STATUS	mandatory
	DESCRIPTION	"Defines when carrier is held high, either constant or variable.
			This parameter is configurable for all Sync protocols EXCEPT tdm(10)
			and fastPacket(9).  For Sync protocol, rtsCts(5), the parameter
			default is Option 'variable(1)'.  For Sync protocols - dlcChannel(1),
			asciiBisync(2), ebcdicBisync(3), hpSync(4), syncPad(6), micomDlc(7),
			and micomVoice(8); the parameter default is Option 'constant(2)'." 
	::= {syncChPhyParaEntry 4}

syncChPhyParaInterfaceType OBJECT-TYPE
	SYNTAX	INTEGER {
		toDTE (1),
		toDCE (2)
		}
	ACCESS	read-write
	STATUS	mandatory
--	DEFVAL	1
	DESCRIPTION	"Sets the user channel for toDTE to interface with data terminal
			equipment; and toDCE to interface with data communication equipment
			such as a tail-circuit modem.  This parameter is configurable for all
			Sync protocols EXCEPT fastPacket(9)."
	::= {syncChPhyParaEntry 5}

syncChPhyParaIdleFill OBJECT-TYPE
	SYNTAX	INTEGER {
		flagFill (1),
		auto (2),
		autoMod128 (3),
		markFill (4)
		}
	ACCESS	read-write
	STATUS	mandatory
--	DEFVAL	1
	DESCRIPTION	"Selects what the Integration unit will output when the line
			is idle.  This parameter is configurable ONLY for Sync protocol
			dlcChannel(1)."
	::= {syncChPhyParaEntry 6}

syncChPhyParaHighSyncChar OBJECT-TYPE
	SYNTAX	OCTET STRING (SIZE(1))
	ACCESS	read-write
	STATUS	mandatory
--	DEFVAL	16
	DESCRIPTION	"Sets the value (high byte) of the leading sync character for
			the start of the block.  This parameter is configurable ONLY for
			Sync protocol syncPad(6)."
	::= {syncChPhyParaEntry 7}

syncChPhyParaLowSyncChar OBJECT-TYPE
	SYNTAX	OCTET STRING (SIZE(1))
	ACCESS	read-write
	STATUS	mandatory
	DESCRIPTION	" Sets the value (low byte) of the leading sync character for
			the start of the block.  This parameter is configurable for all
			Sync protocols EXCEPT dlcChannel(1), micomDlc(7), and micomVoice(8)."
	::= {syncChPhyParaEntry 8}

syncChPhyParaNumLeadSyncCount OBJECT-TYPE
	SYNTAX	INTEGER (0..9)
	ACCESS	read-write
	STATUS	mandatory
--	DEFVAL	3
	DESCRIPTION	"Sets the number of leading sync characters that the Integration
			unit will generate on the output (0-9). This will allow the device
			on the selected channel to synchronize. Enter zero to specify 
			all leading syncs as transparent. They will not be stripped out.
			This parameter is ONLY configurable for Sync protocols asciiBisync(2),
			ebcdicBisync(3), hpSync(4), rtsCts(5), and syncPad(6),"
	::= {syncChPhyParaEntry 9}

syncChPhyParaMaxTxBlockSize OBJECT-TYPE
	SYNTAX	INTEGER (1..9999)
	ACCESS	read-write
	STATUS	mandatory
	DESCRIPTION	"Sets the block size in bytes of the data to the Integration
			unit from the attached device.  This parameter is configurable
			for all Sync protocols EXCEPT micomDlc(7), fastPacket(9), and
			tdm(10).

			For Sync protocol hpSync(4), the parameter default is 9876.  For
			Sync protocol micomVoice(8), the parameter default is 1024.  For
			Sync protocols dlcChannel(1), asciiBisync(2), ebcdicBisync(3),
			rtsCts(5), and syncPad(6); the parameter default is 512."
	::= {syncChPhyParaEntry 10}

syncChPhyParaPadChar OBJECT-TYPE
	SYNTAX	OCTET STRING (SIZE(1))
	ACCESS	read-write
	STATUS	mandatory
--	DEFVAL	FF
	DESCRIPTION	"Sets the value of pad character (alpha numeric). It precedes the
			sync character and follows the end of the block. It is used to pad
			the block.  This parameter is ONLY configurable for the Sync protocols
			asciiBisync(2), ebcdicBisync(3), hpSync(4), rtsCts(5), and syncPad(6)."
	::= {syncChPhyParaEntry 11}

syncChPhyParaNumLeadingPads OBJECT-TYPE
	SYNTAX	INTEGER (1..9)
	ACCESS	read-write
	STATUS	mandatory
	DESCRIPTION	"Sets the number of leading pad characters to be transmitted at
			the start of the block for a time delay (1-9).  This parameter is
			ONLY configurable for the Sync protocols asciiBisync(2), ebcdicBisync(3),
			hpSync(4), rtsCts(5), and syncPad(6).

			For Sync protocols asciiBisync(2), ebcdicBisync(3), and hpSync(4) the
			parameter default is 1.  For Sync protocol rtsCts(5) the default is
			3.  For Sync protocol syncPad(6) the default is 2."
	::= {syncChPhyParaEntry 12}

syncChPhyParaNumTrailingPads OBJECT-TYPE
	SYNTAX	INTEGER (0..20)
	ACCESS	read-write
	STATUS	mandatory
	DESCRIPTION	" Sets the number of trailing pad characters to be transmitted at
			the end of the block.  This parameter is ONLY configurable for the
			Sync protocols asciiBisync(2), ebcdicBisync(3), hpSync(4), rtsCts(5),
			and syncPad(6).

			For Sync protocols asciiBisync(2), ebcdicBisync(3), hpSync(4), and
			syncPad(6) the parameter default is 2.  For Sync protocol rtsCts(5)
			the default is 3."
	::= {syncChPhyParaEntry 13}

syncChPhyParaClockFlowControl OBJECT-TYPE
	SYNTAX	INTEGER {
		enable (1),
		disable (2)
		}
	ACCESS	read-write
	STATUS	mandatory
--	DEFVAL	1
	DESCRIPTION	"Selects whether or not the local sync channel will be flow
			controlled.  This parameter is configurable for all Sync protocols
			EXCEPT fastPacket(9), and tdm(10)."
	::= {syncChPhyParaEntry 14}

syncChPhyParaEncoding OBJECT-TYPE 
	SYNTAX	INTEGER {
		nrz (1),
		nrzi (2)
		}
	ACCESS	read-write
	STATUS	mandatory
--	DEFVAL	1
	DESCRIPTION	"Selects one of the two types of encoding,  NRZ or NRZI, 
			depending on the attached device.  This parameter is ONLY
			configurable for Sync protocol dlcChannel(1)."
	::= {syncChPhyParaEntry 15}

syncChPhyParaChTxClocking OBJECT-TYPE
	SYNTAX	INTEGER {
		internal (1),
		external (2)
		}
	ACCESS	read-write
	STATUS	mandatory
--	DEFVAL 	1
	DESCRIPTION	"Sets the channel's source for transmit clock.  This
			parameter, combined with the syncChPhyParaChRxClocking
			parameter, corresponds to the Channel Clocking parameter
			which is displayed in the Sync channel configuration menu
			of the unit's $CMD facility.  This parameter is configurable
			for all Sync protocols EXCEPT fastPacket(9)."
	::= {syncChPhyParaEntry 16}

syncChPhyParaChRxClocking OBJECT-TYPE
	SYNTAX	INTEGER {
		internal (1),
		external (2)
		}
	ACCESS	read-write
	STATUS	mandatory
--	DEFVAL 	1
	DESCRIPTION	"Sets the channel's source for receive clock.  This
			parameter, combined with the syncChPhyParaChTxClocking
			parameter, corresponds to the Channel Clocking parameter
			which is displayed in the Sync channel configuration menu
			of the unit's $CMD facility.  This parameter is configurable
			for all Sync protocols EXCEPT fastPacket(9)."
	::= {syncChPhyParaEntry 17}

syncChPhyParaPriority OBJECT-TYPE
	SYNTAX	INTEGER {
		low (1),
		high (2)
		}
	ACCESS 	read-write
	STATUS	mandatory
--	DEFVAL	1
	DESCRIPTION	"Selects the priority of the port, high or low.  This parameter
			is configurable for all Sync protocols EXCEPT tdm(10)." 
	::= {syncChPhyParaEntry 18}

syncChPhyParaDSRControl OBJECT-TYPE
	SYNTAX	INTEGER {
		normal (1),
		fornedOn (2),
		localDTR (3)
		}
	ACCESS	read-write
	STATUS	mandatory
--	DEFVAL	1
	DESCRIPTION	"Selects whether the remote DTR changes appear on the 
			local DSR or are ignored." 
	::= {syncChPhyParaEntry 19}

syncChPhyParaBufferControl OBJECT-TYPE
	SYNTAX	INTEGER {
		none (1),
		cts (2)
		}
	ACCESS	read-write
	STATUS	mandatory
--	DEFVAL	1
	DESCRIPTION	"Used to regulate data transmission from a device attached 
			to user channel.  This parameter is configurable for all Sync
			protocols EXCEPT fastPacket(9) and tdm(10)."
	::= {syncChPhyParaEntry 20}

syncChPhyParaMaxRxBlockSize OBJECT-TYPE
	SYNTAX	INTEGER (1..9999)
	ACCESS	read-write
	STATUS	mandatory
	DESCRIPTION	"Sets the block size in bytes of the data to attached device 
			from the Integration unit.  This parameter is configurable for
			all Sync protocols EXCEPT micomDlc(7), fastPacket(9), and tdm(10).

			For Sync protocol hpSync(4), the parameter default is 9876.  For
			Sync protocol micomVoice(8), the parameter default is 1024.  For
			Sync protocols dlcChannel(1), asciiBisync(2), ebcdicBisync(3),
			rtsCts(5), and syncPad(6); the parameter default is 512."
	::= {syncChPhyParaEntry 21}

syncChPhyParaProtocol OBJECT-TYPE
	SYNTAX	INTEGER {
		dlc (1),
		asciiBisync (2),
		ebcdicBisync (3),
		hpSync (4),
		rtsCts (5),
		syncPad (6),
		micomDlc (7),
		micomVoice (8),
		fastPacket (9),
		tdm (10)
		}
	ACCESS	read-only
	STATUS	mandatory
	DESCRIPTION	"Sets the sync channel protocol." 
	::= {syncChPhyParaEntry 22}

syncChPhyParaClaimedBandwidth OBJECT-TYPE
	SYNTAX	INTEGER
	ACCESS	read-write
	STATUS	mandatory
	DESCRIPTION	"Sets the claimed bandwidth of the sync channel.  This
			is the amount of bandwidth that should be reserved on a link
			for this channel / 10.  -ie-  If you want to reserve 9600 bps
			for this channel you should set this to 960.  This parameter
			is configurable for all Sync protocols EXCEPT tdm(10)." 
	::= {syncChPhyParaEntry 23}

syncChPhyParaDLCTransitRate OBJECT-TYPE
	SYNTAX	INTEGER {
		channelRate (1),
		rate1200 (2),
		rate2400 (3),
		rate3600 (4),
		rate4800 (5),
		rate7200 (6),
		rate9600 (7),
		rate12000 (8),
		rate14400 (9),
		rate16800 (10),

		rate19200 (11),
		rate28800 (12),
		rate38400 (13),
		rate48000 (14),
		rate56000 (15),
		rate64000 (16)
		}
	ACCESS	read-write
	STATUS	mandatory
	DESCRIPTION	"Sets the transit rate of the sync channel.  This parameter
			is ONLY configurable for the Sync protocol dlcChannel(1)." 
--	DEFVAL	1
	::= {syncChPhyParaEntry 24}

-- N_CMOS.O_ASYNC ========================================================

asyncChPhyParaTable OBJECT-TYPE
	SYNTAX	SEQUENCE OF AsyncChPhyParaEntry
	ACCESS	not-accessible
	STATUS	mandatory
	DESCRIPTION	"For the configuration of asynchronous channels, this table controls
			and modifies the operating parameters for the port." 
	::= {async-channel 1}

asyncChPhyParaEntry OBJECT-TYPE
	SYNTAX	AsyncChPhyParaEntry
	ACCESS	not-accessible
	STATUS	mandatory
	DESCRIPTION	"Entry into the table pertaining to a specific channel on a specific module." 
	INDEX		{asyncChPhyParaCardNumber, asyncChPhyParaChannelNumber}
	::= {asyncChPhyParaTable 1}

AsyncChPhyParaEntry ::= SEQUENCE {
	asyncChPhyParaCardNumber		INTEGER,
	asyncChPhyParaChannelNumber		INTEGER,
	asyncChPhyParaStopBits			INTEGER,
	asyncChPhyParaCodeLevel		INTEGER,
	asyncChPhyParaDataRate			INTEGER,
	asyncChPhyParaEcho			INTEGER,
	asyncChPhyParaHPXMode		INTEGER,
	asyncChPhyParaConnectTo		INTEGER,
	asyncChPhyParaRemCTSControl		INTEGER,
	asyncChPhyParaCRDelay			INTEGER,
	asyncChPhyParaLFDelay			INTEGER,
	asyncChPhyParaFFDelay			INTEGER,
	asyncChPhyParaXONChar		INTEGER,
	asyncChPhyParaXOFFChar		INTEGER,
	asyncChPhyParaCmdFacilityAccess	INTEGER,
	asyncChPhyParaCmdModeEntry		INTEGER,
	asyncChPhyParaLocChannelConfig	INTEGER,
	asyncChPhyParaCmdModeAccess		INTEGER,
	asyncChPhyParaTandemSupport		INTEGER,
	asyncChPhyParaSmoothScroll		INTEGER,
	asyncChPhyParaFlowControl		INTEGER,
	asyncChPhyParaBufferControl		INTEGER,
	asyncChPhyParaFlowControlStrip		INTEGER,
	asyncChPhyParaSyncLossDisconnect	INTEGER,
	asyncChPhyParaEIAControls		INTEGER,
	asyncChPhyParaPriority			INTEGER,
	asyncChPhyParaParity			INTEGER,
	asyncChPhyParaCompression		INTEGER
	}

asyncChPhyParaCardNumber  OBJECT-TYPE
	SYNTAX	INTEGER (1..5)
	ACCESS	read-only
	STATUS	mandatory
	DESCRIPTION	"The module/card number containing the async channel to which
			the entry pertains to." 
	::= {asyncChPhyParaEntry 1}

asyncChPhyParaChannelNumber  OBJECT-TYPE
	SYNTAX	INTEGER (1..32)
	ACCESS	read-only
	STATUS	mandatory
	DESCRIPTION	"The async channel number to which the entry pertains to." 
	::= {asyncChPhyParaEntry 2}

asyncChPhyParaStopBits	 OBJECT-TYPE
	SYNTAX	INTEGER {
		oneBit (1),
		onePointFiveBits (2),
		twoBits (3)
		}
	ACCESS	read-write
	STATUS	mandatory
--	DEFVAL	1
	DESCRIPTION	"Sets the number of stop-bits inserted at the end of a character." 
	::= {asyncChPhyParaEntry 3}

asyncChPhyParaCodeLevel OBJECT-TYPE
	SYNTAX	INTEGER {
		fiveBits (1),
		sixBits (2),
		sevenBits (3),
		eightBits (4),
		nineBits (5)
		}
	ACCESS	read-write
	STATUS	mandatory
--	DEFVAL	4
	DESCRIPTION	"Sets the number of data bits per character. This includes the
			parity bit." 
	::= {asyncChPhyParaEntry 4}

asyncChPhyParaDataRate	 OBJECT-TYPE
	SYNTAX	INTEGER {
		abr (1),
		rate50 (2),
		rate75 (3),
		rate110 (4),
		rate134dot5 (5),
		rate150 (6),
		rate200 (7),
		rate225 (8),
		rate300 (9),
		rate600 (10),
		rate1200 (11),
		rate1800 (12),
		rate2400 (13),
		rate3600 (14),
		rate4800 (15),
		rate7200 (16),
		rate9600 (17),
		rate14400 (18),
		rate19200 (19),
		rate28800 (20),
		rate38400 (21)
		}
	ACCESS	read-write
	STATUS	mandatory
--	DEFVAL	17
	DESCRIPTION	"Sets the data rate in bits per seconds of the async user channel." 
	::= {asyncChPhyParaEntry 5}

asyncChPhyParaEcho OBJECT-TYPE
	SYNTAX	INTEGER {
		on (1),
		off (2)
	}
	ACCESS	read-write
	STATUS	mandatory
--	DEFVAL	2
	DESCRIPTION	"Turns the echo function on or off when the terminal(2) option
			is selected for the asyncChPhyParaConnectTo object." 
	::= {asyncChPhyParaEntry 6}

asyncChPhyParaHPXMode OBJECT-TYPE
	SYNTAX	INTEGER {
		on (1),
		off (2)
	}
	ACCESS	read-write
	STATUS	mandatory
--	DEFVAL	2
	DESCRIPTION	"Sould be set to ON only when Hewlett Packerd HP-3000 view
			systems using type 26XX display stations (operating under
			term type 10) are connected to the port being configured." 
	::= {asyncChPhyParaEntry 7}

asyncChPhyParaConnectTo OBJECT-TYPE
	SYNTAX	INTEGER {
		host (1),
		terminal (2)
	}
	ACCESS	read-write
	STATUS	mandatory
--	DEFVAL	2
	DESCRIPTION	" Sets the type of equipment which is connected to the
			port, a host or terminal (also printer)." 
	::= {asyncChPhyParaEntry 8}

asyncChPhyParaRemCTSControl OBJECT-TYPE
	SYNTAX	INTEGER {
		forcedOn (1),
		normal (2)
	}
	ACCESS	read-write
	STATUS	mandatory
--	DEFVAL	1
	DESCRIPTION	"Determines whether remote CTS signal is strapped or transparent." 
	::= {asyncChPhyParaEntry 9}

asyncChPhyParaCRDelay OBJECT-TYPE
	SYNTAX	INTEGER (0..99)
	ACCESS	read-write
	STATUS	mandatory
--	DEFVAL	0
	DESCRIPTION	"Sets the delay in character times to allow for mechanical
			action to take place when a carriage return control character
			is transmitted to a channel." 
	::= {asyncChPhyParaEntry 10}

asyncChPhyParaLFDelay OBJECT-TYPE
	SYNTAX	INTEGER (0..99)
	ACCESS	read-write
	STATUS	mandatory
--	DEFVAL	0
	DESCRIPTION	"Sets the delay in character times to allow for mechanical
			action to take place when a line feed control character is
			transmitted to a channel." 
	::= {asyncChPhyParaEntry 11}

asyncChPhyParaFFDelay OBJECT-TYPE
	SYNTAX	INTEGER (0..99)
	ACCESS	read-write
	STATUS	mandatory
--	DEFVAL	0
	DESCRIPTION	"Sets the delay in character times to allow for mechanical
			action to take place when a form feed control character is
			transmitted to a channel." 
	::= {asyncChPhyParaEntry 12}

asyncChPhyParaXONChar OBJECT-TYPE
	SYNTAX	INTEGER {
		dc1 (1),
		dc2 (2),
		dc3 (3),
		dc4 (4)
		}
	ACCESS	read-write
	STATUS	mandatory
--	DEFVAL	1
	DESCRIPTION	"Defines the different XON characters." 
	::= {asyncChPhyParaEntry 13}

asyncChPhyParaXOFFChar OBJECT-TYPE
	SYNTAX	INTEGER {
		dc1 (1),
		dc2 (2),
		dc3 (3),
		dc4 (4)
		}
	ACCESS	read-write
--	DEFVAL	3
	STATUS	mandatory
	DESCRIPTION	"Defines the different XOFF characters." 
	::= {asyncChPhyParaEntry 14}

asyncChPhyParaCmdFacilityAccess OBJECT-TYPE
	SYNTAX	INTEGER {
		enable (1),
		disable (2)
		}
	ACCESS	read-write
	STATUS	mandatory
--	DEFVAL	1
	DESCRIPTION	"Permits or denies (the port being configured) access to the
			Command Facility Main Menu to view or change the system
			operating parameters." 
	::= {asyncChPhyParaEntry 15}

asyncChPhyParaCmdModeEntry OBJECT-TYPE
	SYNTAX	INTEGER {
		ctlXctlY (1),
		ctlXbreak (2)
		}
	ACCESS	read-write
	STATUS	mandatory
--	DEFVAL	2
	DESCRIPTION	"Selects the control character sequence to access to the 
			Command Mode." 
	::= {asyncChPhyParaEntry 16}

asyncChPhyParaLocChannelConfig OBJECT-TYPE
	SYNTAX	INTEGER {
		enable (1),
		disable (2)
		}
	ACCESS	read-write
	STATUS	mandatory
--	DEFVAL	1
	DESCRIPTION	"Controls the access to the Local Channel Configuration Menu." 
	::= {asyncChPhyParaEntry 17}

asyncChPhyParaCmdModeAccess OBJECT-TYPE
	SYNTAX	 INTEGER {
		enable (1),
		disable (2)
		}
	ACCESS	read-write
	STATUS	mandatory
--	DEFVAL	1
	DESCRIPTION	"Permits or deny (the port being configured) access to
			the Command Mode." 
	::= {asyncChPhyParaEntry 18}

asyncChPhyParaTandemSupport OBJECT-TYPE
	SYNTAX	INTEGER {
		on (1),
		off (2)
		}
	ACCESS	read-write
	STATUS	mandatory
--	DEFVAL	2
	DESCRIPTION	"Should set to ON only when Tandem Computers are connected
			to the channel being configured." 
	::= {asyncChPhyParaEntry 19}

asyncChPhyParaSmoothScroll OBJECT-TYPE
	SYNTAX	INTEGER {
		on (1),
		off (2)
		}
	ACCESS	read-write
	STATUS	mandatory
--	DEFVAL	2
	DESCRIPTION	"Should be set to ON only when DEC VT100 smooth scroll
			terminals are connected to the system." 
	::= {asyncChPhyParaEntry 20}

asyncChPhyParaFlowControl OBJECT-TYPE
	SYNTAX	INTEGER {
		none (1),
		xonXof (2),
		dtr (3),
		xonXofDtr (4),
		wangx (5),
		rts (6),
		dataGeneral (7)
		}
	ACCESS	read-write
	STATUS	mandatory
--	DEFVAL	2
	DESCRIPTION	"An attached device uses flow control to start or stop data
			flow from the Integration unit. The attached device may control data
			flow by use of XON/XOFF, DTR, XON/XOFF + DTR or a
			special WANGX character." 
	::= {asyncChPhyParaEntry 21}

asyncChPhyParaBufferControl OBJECT-TYPE
	SYNTAX	INTEGER {
		none (1),
		xonXof (2),
		cts (3),
		wangx (4)
		}
	ACCESS	read-write
	STATUS	mandatory
--	DEFVAL	2
	DESCRIPTION	"Buffer control to start or stop the data flow from the 
			attached device. The attached device may control data
			flow by use of XON/XOFF, CTS, or a special WANGX
			character." 
	::= {asyncChPhyParaEntry 22}

asyncChPhyParaFlowControlStrip OBJECT-TYPE
	SYNTAX	INTEGER {
		strip (1),
		pass (2)
		}
	ACCESS	read-write
	STATUS	mandatory
--	DEFVAL	2
	DESCRIPTION	"Allows the flow control characters to be passed through or
			stripped from the Integration unit." 
	::= {asyncChPhyParaEntry 23}

asyncChPhyParaSyncLossDisconnect OBJECT-TYPE
	SYNTAX	INTEGER {
		enable (1),
		disable (2)
		}
	ACCESS	read-write
	STATUS	mandatory
--	DEFVAL	2
	DESCRIPTION	"When enabled, the local node toggles the controls and
			purges the data. This occurs when the link has experienced
			a sync loss condition for more than 20 seconds." 
	::= {asyncChPhyParaEntry 24}

asyncChPhyParaEIAControls OBJECT-TYPE
	SYNTAX	INTEGER {
		enable (1),
		disable (2)
		}
	ACCESS	read-write
	STATUS	mandatory
--	DEFVAL	1
	DESCRIPTION	"Ability to recognize or ignore the EIA control signals from the
			attached device." 
	::= {asyncChPhyParaEntry 25}

asyncChPhyParaPriority OBJECT-TYPE
	SYNTAX	INTEGER {
		high (1),
		low (2)
		}
	ACCESS	read-write
	STATUS	mandatory
--	DEFVAL	1
	DESCRIPTION	"Decides whether or not this channel is to receive a high
			or low priority for use. A high priority channel will take
			precedence over a channel with low priority." 
	::= {asyncChPhyParaEntry 26}

asyncChPhyParaParity OBJECT-TYPE
	SYNTAX	INTEGER {
		space (1),
		odd (2),
		even (3),
		mark (4),
		none (5)
		}
	ACCESS	read-write
	STATUS	mandatory
--	DEFVAL	5
	DESCRIPTION	"Sets the message and data parity for the Integration unit. Depending on the
			asyncChPhyParaCodeLevel selection of 5-8 bits, the available parity
			is space, odd, even, mark, and none.  For code level 9 bits, the 
			available choice is odd or even." 
	::= {asyncChPhyParaEntry 27}

asyncChPhyParaCompression OBJECT-TYPE
	SYNTAX	INTEGER {
		enable (1),
		disable (2)
		}
	ACCESS	read-write
	STATUS	mandatory
--	DEFVAL	1
	DESCRIPTION	"When enabled, the unit compresses a block of data when transmitting.
			Fewer bytes are required for the transfer thus increasing the data
			transfer rate (making it faster)." 
	::= {asyncChPhyParaEntry 28}


-- N_CMOS.O_ASYSWI =======================================================

asyncChSwParaTable OBJECT-TYPE
	SYNTAX	SEQUENCE OF AsyncChSwParaEntry
	ACCESS	not-accessible
	STATUS	mandatory
	DESCRIPTION	"Table for configuration of async channel switching parameters." 
	::= {async-channel 2}

asyncChSwParaEntry OBJECT-TYPE
	SYNTAX	AsyncChSwParaEntry
	ACCESS	not-accessible
	STATUS	mandatory
	DESCRIPTION	"Entry within the table to specify a particular async channel number
			on a specific module/card." 
	INDEX		{asyncChSwParaCardNumber, asyncChSwParaChannelNumber}
	::= {asyncChSwParaTable 1}

AsyncChSwParaEntry ::= SEQUENCE {
	asyncChSwParaCardNumber		INTEGER,
	asyncChSwParaChannelNumber		INTEGER,
	asyncChSwParaDestinationClass		DisplayString,
	asyncChSwParaConnectProtocol		INTEGER,
	asyncChSwParaRcvInhibit			INTEGER,
	asyncChSwParaResourceClassNumber	INTEGER,
	asyncChSwParaCallInhibit		INTEGER,
	asyncChSwParaUnbalanceRates		INTEGER,
	asyncChSwParaCharacterSet		INTEGER,
	asyncChSwParaMatrixSwitching		INTEGER,
	asyncChSwParaChannelPassword		DisplayString
	}


asyncChSwParaCardNumber OBJECT-TYPE
	SYNTAX	INTEGER (1..5)
	ACCESS	read-only
	STATUS	mandatory
	DESCRIPTION	"Identifies the module/card number for the async channel specific
			to the channel switching parameters." 
	::= {asyncChSwParaEntry 1}

asyncChSwParaChannelNumber OBJECT-TYPE
	SYNTAX	INTEGER (1..32)
	ACCESS	read-only
	STATUS	mandatory
	DESCRIPTION	"Identifies the async channel specific to the channel switching parameters." 
	::= {asyncChSwParaEntry 2}

asyncChSwParaDestinationClass OBJECT-TYPE
	SYNTAX	DisplayString  (SIZE (0..17))
	ACCESS	read-write
	STATUS	mandatory
	DESCRIPTION	"Assign the destination class name to the async channel for class switching." 
	::= {asyncChSwParaEntry 3}

asyncChSwParaConnectProtocol OBJECT-TYPE
	SYNTAX	INTEGER {
		dedicated (1),
		dtr (2),
		autoAnswer (3)
		}
	ACCESS	read-write
	STATUS	mandatory
--	DEFVAL	1
	DESCRIPTION	"Selects the connect protocol for the port being configured. The
			protocol must be compatible with the attached device." 
	::= {asyncChSwParaEntry 4}

asyncChSwParaRcvInhibit OBJECT-TYPE
	SYNTAX	INTEGER {
		enable (1),
		disable (2)
		}
	ACCESS	read-write
	STATUS	mandatory
--	DEFVAL	2
	DESCRIPTION	"Controls the port being configured from receiving a connection
			request." 
	::= {asyncChSwParaEntry 5}

asyncChSwParaResourceClassNumber OBJECT-TYPE
	SYNTAX	INTEGER (0..64)
	ACCESS	read-write
	STATUS	mandatory
	DESCRIPTION	"Assigns a resource class number (1 - 64) to the async channel.
			Zero reflects no resource class assignment." 
	::= {asyncChSwParaEntry 6}

asyncChSwParaCallInhibit OBJECT-TYPE
	SYNTAX	INTEGER {
		enable (1),
		disable (2)
		}
	ACCESS	read-write
	STATUS	mandatory
--	DEFVAL	2
	DESCRIPTION	"Controls the port being configured from making a connection
			request." 
	::= {asyncChSwParaEntry 7}

asyncChSwParaUnbalanceRates OBJECT-TYPE
	SYNTAX	INTEGER {
		enable (1),
		disable (2)
		}
	ACCESS	read-write
	STATUS	mandatory
--	DEFVAL	1
	DESCRIPTION	"Controls the connections of ports which have dissimilar
			baud rates (different speed)." 
	::= {asyncChSwParaEntry 8}

asyncChSwParaCharacterSet OBJECT-TYPE
	SYNTAX	INTEGER {
		ascii (1),
		nonAscii (2)
		}
	ACCESS	read-write
	STATUS	mandatory
--	DEFVAL	1
	DESCRIPTION	"Option to select either an ASCII or non-ASCII character set." 
	::= {asyncChSwParaEntry 9}

asyncChSwParaMatrixSwitching OBJECT-TYPE
	SYNTAX	INTEGER {
		enable (1),
		disable (2)
		}
	ACCESS	read-write
	STATUS	mandatory
--	DEFVAL	1
	DESCRIPTION	"The ability of the port to make a connection request by 
			specifying a node/channel number." 
	::= {asyncChSwParaEntry 10}

asyncChSwParaChannelPassword OBJECT-TYPE
	SYNTAX	DisplayString  (SIZE (0..8))
	ACCESS	write-only
	STATUS	mandatory
	DESCRIPTION	"A unique password attached to the port being configured
			to control access for security." 
	::= {asyncChSwParaEntry 11}


-- VOICE CHANNEL

-- N_CMOS.O_VOICE =========================================================

voiceFaxChPhyParaTable OBJECT-TYPE
	SYNTAX	SEQUENCE OF VoiceFaxChPhyParaEntry
	ACCESS	not-accessible
	STATUS	mandatory
	DESCRIPTION	"Table for configuring the voice/Fax channel physical parameters." 
	::= {voice-fax-channel 1}

voiceFaxChPhyParaEntry OBJECT-TYPE
	SYNTAX	VoiceFaxChPhyParaEntry
	ACCESS	not-accessible
	STATUS	mandatory
	DESCRIPTION	"Entry within the table to specify a particular voice/Fax channel number
			on a specific module/card." 
	INDEX		{voiceFaxChPhyParaCardNumber, voiceFaxChPhyParaChannelNumber}
	::= {voiceFaxChPhyParaTable 1}

VoiceFaxChPhyParaEntry ::= SEQUENCE {
	voiceFaxChPhyParaCardNumber				INTEGER,
	voiceFaxChPhyParaChannelNumber			INTEGER,
	voiceFaxChPhyParaWireOperation			INTEGER,
	voiceFaxChPhyParaViewSignallingType		INTEGER,
	voiceFaxChPhyParaBergStrapType			INTEGER,
	voiceFaxChPhyParaSuppression			INTEGER,
	voiceFaxChPhyParaCfgSignallingType		INTEGER,
	voiceFaxChPhyParaOPXNumberOfRings		INTEGER,
	voiceFaxChPhyParaFXOSupervisorDisc		INTEGER,
	voiceFaxChPhyParaRingFrequency			INTEGER,
	voiceFaxChPhyParaJitter					INTEGER,
	voiceFaxChPhyParaDTMFRegeneration		INTEGER,
	voiceFaxChPhyParaAutoLevelEnhancement	INTEGER,
	voiceFaxChPhyParaBackground				INTEGER,
	voiceFaxChPhyParaDigitizingRate			INTEGER,
	voiceFaxChPhyParaBusyMode				INTEGER,
	voiceFaxChPhyParaVoiceFaxMode			INTEGER,
	voiceFaxChPhyParaBandwidthAssignment	INTEGER,
	voiceFaxChPhyParaInputGain				INTEGER,
	voiceFaxChPhyParaChannelType			INTEGER,
	voiceFaxChPhyParaEMTypeStrapping		INTEGER,
	voiceFaxChPhyParaOutputAttenuation		INTEGER,
	voiceFaxChPhyParaPriority				INTEGER,
	voiceFaxChPhyParaFaxDigitizingRate		INTEGER,
	voiceFaxChPhyParaLineImpedance			INTEGER,
	voiceFaxChPhyParaMaxOutputLevel			INTEGER,
	voiceFaxChPhyParaRegenerationDelay		INTEGER,
	voiceFaxChPhyParaMaxDialDigitTimeLimit	INTEGER,
	voiceFaxChPhyParaMaxNumFwdDigits		INTEGER,
	voiceFaxChPhyParaCallProgressionTones	INTEGER,
	voiceFaxChPhyParaRegenFormat			INTEGER,
	voiceFaxChPhyParaChannelVersion			INTEGER
	}

voiceFaxChPhyParaCardNumber OBJECT-TYPE
	SYNTAX	INTEGER (2..5)
	ACCESS	read-only
	STATUS	mandatory
	DESCRIPTION	"Identifies the module/card number for the voice/Fax channel specific
			to the channel's physical parameters." 
	::= {voiceFaxChPhyParaEntry 1}

voiceFaxChPhyParaChannelNumber OBJECT-TYPE
	SYNTAX	INTEGER (1..2)
	ACCESS	read-only
	STATUS	mandatory
	DESCRIPTION	"Identifies the voice/Fax channel specific to the channel's 
			physical parameters." 
	::= {voiceFaxChPhyParaEntry 2}

voiceFaxChPhyParaWireOperation OBJECT-TYPE
	SYNTAX	INTEGER {
		fourWire (1),
		twoWire (2)
		}
	ACCESS	read-write
	STATUS	mandatory
	DESCRIPTION	"Sets the voice channel for either 2-wire or 4-wire analog 
			operation. Valid only when  voiceFaxChPhyParaBergStrapType
			indicates em(2) or enhancedEm(5)."  
	::= {voiceFaxChPhyParaEntry 3}
		
voiceFaxChPhyParaViewSignallingType OBJECT-TYPE
	SYNTAX	INTEGER {
		emTypeIdc (1),
		emTypeIIdc (2),
		emTypeIIIdc (3),
		emTypeIVdc (4),
		emTypeVdc (5),
		emTypeI2280 (6),
		emTypeII2280 (7),
		emTypeIII2280 (8),
		emTypeIV2280 (9),
		emTypeV2280 (10),
		emPulsedDc (11),
		emPulsedIDc (12),
		emPulsedIIDc (13),
		emPulsedIIIDc (14),
		emPulsedIVDc (15),
		emPulseVDc (16),
		ktsRepeated (17),
		ktsInterrupt2by4 (18),
		ktsInterrupt1by2(19),
		opx (20),
		fxsRepeated (21),
		fxsInterrupt2by4 (22),
		fxsInterrupt1by2 (23),
		fxsFaxRepeated (24),
		fxsFaxInterrupt2by4 (25),
		fxsFaxInterrupt1by2 (26),
		fxo (27),
		fxsIterrupted (28),
		faxIterrupted (29)
		}
	ACCESS	read-only
	STATUS	mandatory
	DESCRIPTION	"Indicates the signalling type.  This parameter is computed
			from the strapping and signalling interface configuration." 
	::= {voiceFaxChPhyParaEntry 4}

voiceFaxChPhyParaBergStrapType OBJECT-TYPE
	SYNTAX	INTEGER {
		kts (1),
		em (2),
		opx (3),
		enhancedFxs (4),
		enhancedEm (5),
		enhancedFxo (6),
		standardFxs (7),
		standardEm (8),
		standardFxo (9),
		groundstartFxs (10),
		groundstartFxo (11),
		threePort (12)
		}
	ACCESS	read-only
	STATUS	mandatory
	DESCRIPTION	"Indicates the Berg Hardware Strap configuration on the 
			voice/Fax channel." 
	::= {voiceFaxChPhyParaEntry 5}

voiceFaxChPhyParaSuppression OBJECT-TYPE
	SYNTAX	INTEGER
	ACCESS	read-only
	STATUS	mandatory
	DESCRIPTION	"During idle periods in which suppression is enabled (=0),
			the sending voice channel DSP generates suppression service
			frames containing a noise level estimate and no data.  This 
			is sent to the receiving voice channel DSP which will either
			regenerate the noise level or silence the output depending on
			the configuration of voiceFaxChPhyParaBackground." 
	::= {voiceFaxChPhyParaEntry 6}

voiceFaxChPhyParaCfgSignallingType OBJECT-TYPE
	SYNTAX	INTEGER {
		emDc (1),
		em2280Tone (2),
		emWink (3),
		emPulsedDc (4),
		repeated (5),
		interruptOR2by4 (6),
		interrupt1by2 (7)
		}
	ACCESS	read-write
	STATUS	mandatory
	DESCRIPTION	"Configures where the ring signal is generated (locally or by
			remote PBX equipment) and the ring cadence (timing of rings and
			silence periods).  This parameter is ONLY configurable for E&M,
			Enhanced and Standard E&M, 3-Port Fax, and Enhanced and Standard
			FXS voice modules.  The following is a matrix of valid signaling
			type options for each configurable voice module, given the Channel
			Version value (voiceFaxChPhyParaChannelVersion) and Integration
			Unit software release (sysSoftwarePhase).

			Voice Module    Configurable Options     Chan Version   Release
			------------    --------------------     ------------   -------
			E&M             emDC,em2280,emPulseDc         2         ALL

            KTS             repeated,interruptOR2by4,     2         ALL
			                interrupt1by2

			Std/Enh E&M     emDC,em2280,emPulseDC        2,3,5      ALL

			                emDC,em2280,emPulseDC,       6,7        Phase 5.1
			                emWink                                  and Above

			3-Port Fax      repeated,interruptOR2by4     3,5-7      ALL

			Std/Enh FXS     repeated,interruptOR2by4,    2,3        ALL
			                interrupt1by2

			                repeated,interruptOR2by4     5-7        Phase 5.0
			                                                        and Above " 
	::= {voiceFaxChPhyParaEntry 7}

voiceFaxChPhyParaOPXNumberOfRings OBJECT-TYPE
	SYNTAX	INTEGER (1..9)
	ACCESS	read-write
	STATUS	mandatory
	DESCRIPTION	"From customer equipment, the number of rings generated
			before hearing the voice/fax module dial tone of the local
			Integration unit.  This parameter is ONLY configurable for
			the OPX, and Standard and Enhanced FXO voice modules." 
	::= {voiceFaxChPhyParaEntry 8}

voiceFaxChPhyParaFXOSupervisorDisc OBJECT-TYPE
	SYNTAX	INTEGER {
		powerInterrupt (1),
		tone (2)
		}
	ACCESS	read-write
	STATUS	mandatory
	DESCRIPTION	"Configures the means to disconnect a telephone connection.  
			Either an absence of loop current (powerInterrupt) or presence
			of a call progress tone (tone).  Select configuration to match
			customer equipment provisions. This parameter is ONLY configurable
			for the Standard and Enhanced FXO voice modules." 
	::= {voiceFaxChPhyParaEntry 9}

voiceFaxChPhyParaRingFrequency OBJECT-TYPE
	SYNTAX	INTEGER {
		freq25Hz (1),
		freq50Hz (2)
		}
	ACCESS	read-write
	STATUS	mandatory
	DESCRIPTION	"Selects the ringing frequency to be used to indicate an
			incoming call.  This parameter is ONLY configurable for the KTS,
			3-Port Fax, and Standard and Enhanced FXS voice modules." 
	::= {voiceFaxChPhyParaEntry 10}

voiceFaxChPhyParaJitter OBJECT-TYPE
	SYNTAX	INTEGER
	ACCESS	read-only
	STATUS	mandatory
	DESCRIPTION	"Maintains continuous voice delivery by compensating (in
			milliseconds) for the transmission delay of packets.  Jitter
			provides compensation for the difference in arrival time and
			expected arrival time of voice packets. (Range is 1 - 200 ms.)
			This parameter is configurable by all voice modules with a
			Channel Version (voiceFaxChPhyParaChannelVersion) equal to '5'
			or higher and residing in an Integration Unit with a software
			release (sysSoftwarePhase) of Phase 5.1 and Above (EXCLUDES 
			the E&M, KTS and OPX voice modules)."
	::= {voiceFaxChPhyParaEntry 11}

voiceFaxChPhyParaDTMFRegeneration OBJECT-TYPE
	SYNTAX	INTEGER {
		disable (1),
		enable (2)
		}
	ACCESS	read-write
	STATUS	mandatory
	DESCRIPTION	"DTMF Regeneration, when enabled, ensures that the DTMF
			signals at the remote side are regenerated with a uniform
			on/off time of 100 milliseconds.  This option is only compatible
			with other Voice/Fax modules that configure this parameter.
			This parameter is configurable by all voice modules with a
			Channel Version (voiceFaxChPhyParaChannelVersion) equal to '7'
			or higher and residing in an Integration Unit with a software
			release (sysSoftwarePhase) of Phase 5.1C and Above (EXCLUDES
			the E&M, KTS and OPX voice modules)."
	::= {voiceFaxChPhyParaEntry 12}

voiceFaxChPhyParaAutoLevelEnhancement OBJECT-TYPE
	SYNTAX	INTEGER {
		disable (1),
		enable (2)
		}
	ACCESS	read-write
	STATUS	mandatory
	DESCRIPTION	"Automatic Level Enhancement, when enabled, boosts weak 
			input signals above the noise threshold to a minimum usable
			level for voice/Fax channels.  This parameter is configurable
			by all voice modules with a Channel Version
			(voiceFaxChPhyParaChannelVersion) equal to '5' or higher and
			residing in an Integration Unit with a software release
			(sysSoftwarePhase) of Phase 5.1 and Above (EXCLUDES the E&M,
			KTS and OPX voice modules)."
	::= {voiceFaxChPhyParaEntry 13}

voiceFaxChPhyParaBackground OBJECT-TYPE
	SYNTAX	INTEGER {
		regenerated (1),
		silence (2)
		}
	ACCESS	read-write
	STATUS	mandatory
	DESCRIPTION	"The ability of passing background noise or silencing the
			channel by the receiving voice channel DSP during idle periods.
			First option allows the background noise to be regenerated
			during the periods, whereas the second option suppresses
			background noise during idle periods."
	::= {voiceFaxChPhyParaEntry 14}


voiceFaxChPhyParaDigitizingRate OBJECT-TYPE
	SYNTAX	INTEGER {
		rate4000 (1),
		rate4800 (2),
		rate6400 (3),
		rate7200 (4),
		rate8000 (5),
		rate9600 (6),
		rate12000 (7),
		rate14400 (8),
		rate16000 (9),
		rateG729 (10)
		}
	ACCESS	read-write
	STATUS	mandatory
	DESCRIPTION	"Configures the compression bandwidth for the voice channel. 
			Larger bandwidths produce crisper voice communications.  However,
			larger voice channel bandwidths may result in overbooking of
			composite bandwidth.  The G.729 Digitizing Rate option (rateG729)
			is ONLY configurable for voice modules with a Channel Version
			(voiceFaxChPhyParaChannelVersion) equal to '5' or higher (EXCLUDES 
			the E&M, KTS and OPX voice modules)."
	::= {voiceFaxChPhyParaEntry 15}

voiceFaxChPhyParaBusyMode OBJECT-TYPE
	SYNTAX	INTEGER {
		forcedOff (1),
		forcedOn (2),
		systemControlled (3)
		}
	ACCESS	read-write
	STATUS	mandatory
	DESCRIPTION	"Controls how the busyout state of the channel is determined." 
	::= {voiceFaxChPhyParaEntry 16}

voiceFaxChPhyParaVoiceFaxMode OBJECT-TYPE
	SYNTAX	INTEGER {
		voiceFax (1),
		voiceOnly (2)
		}
	ACCESS	read-write
	STATUS	mandatory
	DESCRIPTION	"Selects the channel signal processing type, voice/fax or voice only." 
	::= {voiceFaxChPhyParaEntry 17}

voiceFaxChPhyParaBandwidthAssignment OBJECT-TYPE
	SYNTAX	INTEGER {
		voiceActivated (1),
		continuous (2),
		dynamic (3)
		}
	ACCESS	read-write
	STATUS	mandatory
	DESCRIPTION	"Selects how the channel uses link bandwidth: all the
			time (continuous); only when voice/fax signals are present
			(voiceActivated); or dynamically.  Option 3 (dynamic) is not
			valid when the voiceFaxChPhyParaDigitizingRate value is
			configured for G.729." 
	::= {voiceFaxChPhyParaEntry 18}

voiceFaxChPhyParaInputGain OBJECT-TYPE
	SYNTAX	INTEGER (-6..22)
	ACCESS	read-write
	STATUS	mandatory
	DESCRIPTION	"Selects one of 29 input level gain values in 1 dB increments.
			This range of values applies only to the KTS, OPX, and E&M voice
			modules.  The remaining voice modules utilize the following 'value'
			range: -6 thru 19, inclusive." 
	::= {voiceFaxChPhyParaEntry 19}

voiceFaxChPhyParaChannelType OBJECT-TYPE
	SYNTAX	INTEGER
	ACCESS	read-only
	STATUS	mandatory
	DESCRIPTION	"Unconfigurable by the User" 
	::= {voiceFaxChPhyParaEntry 20}

voiceFaxChPhyParaEMTypeStrapping OBJECT-TYPE
	SYNTAX	INTEGER {
		emTypeI (1),
		emTypeII (2),
		emTypeIII (3),
		emTypeIV (4),
		emTypeV (5)
		}
	ACCESS	read-only
	STATUS	mandatory
	DESCRIPTION	"Reflects the Ear and Mouth circuit configuration type (I - V)
			on voice/Fax channels that are strapped for E&M." 
	::= {voiceFaxChPhyParaEntry 21}

voiceFaxChPhyParaOutputAttenuation OBJECT-TYPE
	SYNTAX	INTEGER (0..28)
	ACCESS	read-write
	STATUS	mandatory
	DESCRIPTION	"Selects one out of 29 output level attenuation values in 1 dB 
			increments. 0 = no attenuation, 28 = maximum attenuation.  This
			range of values applies only to the KTS, OPX, and E&M voice modules.
			The remaining voice modules utilize the following 'value' range:
			0 thru 25, inclusive." 
	::= {voiceFaxChPhyParaEntry 22}

voiceFaxChPhyParaPriority OBJECT-TYPE
	SYNTAX	INTEGER {
		high (1),
		low (2)
		}
	ACCESS	read-write
	STATUS	mandatory
	DESCRIPTION	"Selects the priority of the channel, either high or low." 
	::= {voiceFaxChPhyParaEntry 23}

voiceFaxChPhyParaFaxDigitizingRate OBJECT-TYPE
	SYNTAX	INTEGER {
		useVoiceRate (1),
		rate2400 (2),
		rate4800 (3),
		rate7200 (4),
		rate9600 (5)
		}
	ACCESS	read-write
	STATUS	mandatory
	DESCRIPTION	"Sets the compression bandwidth for voice channel Fax operations." 
	::= {voiceFaxChPhyParaEntry 24}

voiceFaxChPhyParaLineImpedance OBJECT-TYPE
	SYNTAX	INTEGER {
		impedance600Ohms (1),
		complex (2)
		}
	ACCESS	read-write
	STATUS	mandatory
	DESCRIPTION	"Provides impedance matching choices for the Enhanced FXS,
			Enhanced FXO, and Enhanced E&M 2-wire interface modules. This
			parameter is ONLY configurable for these voice modules.  The
			port impedance of the E&M interface module configured for 4-wire
			operation is fixed at 600 ohms resistive and is not configurable." 
	::= {voiceFaxChPhyParaEntry 25}

voiceFaxChPhyParaMaxOutputLevel OBJECT-TYPE
	SYNTAX	INTEGER {
		level0dBmNominal (1),
		levelPlus7dBm (2)
		}
	ACCESS	read-write
	STATUS	mandatory
	DESCRIPTION	"Intended to be used for equipment operated outside of U.S.A
			and Canada. This parameter is ONLY configurable for the Enhanced
			E&M voice module.  Option (1) must be selected within the U.S.A 
			(or Canada) if this module was originally configured for 4-wire
			operation and you have just reconfigured it to 2-wire operation.
			Otherwise, the voice/fax module will not operate properly." 
	::= {voiceFaxChPhyParaEntry 26}

voiceFaxChPhyParaRegenerationDelay OBJECT-TYPE
	SYNTAX	INTEGER (1..15)
	ACCESS	read-write
	STATUS	mandatory
	DESCRIPTION	"The selected delay, ranging from 1 to 15 seconds,
			compensates for the time it takes for the remote PBX to
			go off-hook and provide a dial tone to the voice channel
			for completing the call setup.  The default is 1 second.
			This parameter is configurable for all voice modules with
			a Channel Version (voiceFaxChPhyParaChannelVersion) greater
			than or equal to '3' (EXCLUDES the E&M, KTS and OPX voice
			modules)."
	::= {voiceFaxChPhyParaEntry 27}

voiceFaxChPhyParaMaxDialDigitTimeLimit OBJECT-TYPE
	SYNTAX	INTEGER (1..15)
	ACCESS	read-write
	STATUS	mandatory
	DESCRIPTION	"The dial digit time limit is the maximum time allowed
			for accepting dialed digits.  When the dial digit time
			limit is reached, further digits are not accepted, and the
			accumulated digits are compared to the configured number of
			digits.  If the accumulated number is less than the configured
			number, a fast busy response is generated.  If the accumulated
			number is equal to or more than the configured number, the
			digits are forwarded.  The default is 10 seconds.  This
			parameter is configurable for all voice modules with a Channel
			Version (voiceFaxChPhyParaChannelVersion) greater than or equal
			to '3' (EXCLUDES the E&M, KTS and OPX voice modules)."
	::= {voiceFaxChPhyParaEntry 28}

voiceFaxChPhyParaMaxNumFwdDigits OBJECT-TYPE
	SYNTAX	INTEGER (0..16)
	ACCESS	read-write
	STATUS	mandatory
	DESCRIPTION	"The selected value specifies the maximum number of
			dialing digits to be forwarded to the destination voice
			channel without having to wait until the dial digit time
			limit is reached.  The range is 0-16, with zero disabling
			the store and forward feature. The default value is 0.
			This parameter is configurable for all voice modules with
			a Channel Version (voiceFaxChPhyParaChannelVersion) greater
			than or equal to '3' (EXCLUDES the E&M, KTS and OPX voice
			modules)."
	::= {voiceFaxChPhyParaEntry 29}

voiceFaxChPhyParaCallProgressionTones OBJECT-TYPE
	SYNTAX	INTEGER {
		northAmerica (1),
		japan (2),
		unitedKingdom (3),
		germany (4),
		france (5),
		centralAmerica (6),
		chile (7),
		australia (8)
		}
	ACCESS	read-write
	STATUS	mandatory
	DESCRIPTION	"This option allows you to match the call progress to 
			those of one of eight countries or areas.  This parameter
			is configurable for all voice modules with a Channel Version
			(voiceFaxChPhyParaChannelVersion) greater than or equal to
			'3' (EXCLUDES the E&M, KTS and OPX voice modules)."
	::= {voiceFaxChPhyParaEntry 30}

voiceFaxChPhyParaRegenFormat OBJECT-TYPE
	SYNTAX	INTEGER {
		pulsedDialing (1),
		dtmfDialing (2)
		}
	ACCESS	read-write
	STATUS	mandatory
	DESCRIPTION	"Regeneration format supports the store and forward function.
			Dial format allows the voice/fax channel to match the outgoing 
			dialing digits format with the format of the interfacing PBX.
			This parameter is configurable for all voice modules with
			a Channel Version (voiceFaxChPhyParaChannelVersion) greater
			than or equal to '3' (EXCLUDES the E&M, KTS and OPX voice
			modules)."
	::= {voiceFaxChPhyParaEntry 31}

voiceFaxChPhyParaChannelVersion OBJECT-TYPE
	SYNTAX	INTEGER {
		phase1and2and2dot5Fconn (1),
		phase3VSW(2),
		phase3dot1UV (3),
		voiceDialingImprovement (4),
		g729DigitizingRateSupported (5),
		phase5dot1 (6),
		dtmfRegne (7),
		casVer2 (8)
		}
	ACCESS	read-only
	STATUS	mandatory
	DESCRIPTION	"Identifies the voice/Fax compression algorithm used (installed 
			software version) by the voice/Fax channel." 
	::= {voiceFaxChPhyParaEntry 32}


-- N_CMOS.O_VOCSWI =======================================================

voiceFaxChSwParaTable OBJECT-TYPE
	SYNTAX	SEQUENCE OF VoiceFaxChSwParaEntry
	ACCESS	not-accessible
	STATUS	mandatory
	DESCRIPTION	"Table for configuring the voice/Fax channel switching parameters." 
	::= {voice-fax-channel 2}

voiceFaxChSwParaEntry OBJECT-TYPE
	SYNTAX	VoiceFaxChSwParaEntry
	ACCESS	not-accessible
	STATUS	mandatory
	DESCRIPTION	"Entry within the table to specify a particular voice/Fax channel number
			on a specific module/card for channel switching configuration." 
	INDEX		{voiceFaxChSwParaCardNumber, voiceFaxChSwParaChannelNumber}
	::= {voiceFaxChSwParaTable 1}

VoiceFaxChSwParaEntry ::= SEQUENCE {
	voiceFaxChSwParaCardNumber		INTEGER,
	voiceFaxChSwParaChannelNumber	INTEGER,
	voiceFaxChSwParaVoiceExtension		DisplayString,
	voiceFaxChSwParaFaxExtension		DisplayString,
	voiceFaxChSwParaAutoCallNumber	DisplayString,
	voiceFaxChSwParaReceiveInhibit		INTEGER,
	voiceFaxChSwParaCallInhibit		INTEGER
	}

voiceFaxChSwParaCardNumber OBJECT-TYPE
	SYNTAX	INTEGER (1..5)
	ACCESS	read-only
	STATUS	mandatory
	DESCRIPTION	"Identifies the module/card number for the voice/Fax channel specific
			to the channel's switching parameters." 
	::= {voiceFaxChSwParaEntry 1}

voiceFaxChSwParaChannelNumber OBJECT-TYPE
	SYNTAX	INTEGER (1..6)
	ACCESS	read-only
	STATUS	mandatory
	DESCRIPTION	"Identifies the voice/Fax channel specific to the channel's 
			switching parameters." 
	::= {voiceFaxChSwParaEntry 2}

voiceFaxChSwParaVoiceExtension OBJECT-TYPE
	SYNTAX	DisplayString  (SIZE (1..4))
	ACCESS	read-write
	STATUS	mandatory
	DESCRIPTION	"Defines the voice extension for the voice/fax channel.
			The voice extension must consist of NUMERIC characters
			only; and the number of digits in the extension MUST match
			the value set for the voiceFaxChSwNumberOfDigitsInPhoneNumber
			parameter." 
	::= {voiceFaxChSwParaEntry 3}

voiceFaxChSwParaFaxExtension OBJECT-TYPE
	SYNTAX	DisplayString  (SIZE (1..4))
	ACCESS	read-write
	STATUS	mandatory
	DESCRIPTION	"Defines the fax extension for the voice/fax channel.
			The fax extension must consist of NUMERIC characters only;
			and the number of digits in the extension MUST match the
			value set for the voiceFaxChSwNumberOfDigitsInPhoneNumber
			parameter.  This parameter is ONLY valid for 3-Port Fax
			modules." 
	::= {voiceFaxChSwParaEntry 4}

voiceFaxChSwParaAutoCallNumber OBJECT-TYPE
	SYNTAX	DisplayString  (SIZE (1..4))
	ACCESS	read-write
	STATUS	mandatory
	DESCRIPTION	"This is the extension number of a voice/fax port that is 
			called immediately if this voice/fax port goes off hook. 
			If no entry is made in this field, this function is disabled.
			The Auto Call Number must consist of NUMERIC characters only." 
	::= {voiceFaxChSwParaEntry 5}

voiceFaxChSwParaReceiveInhibit  OBJECT-TYPE
	SYNTAX	INTEGER {
		on (1),
		off (2)
		}
	ACCESS	read-write
	STATUS	mandatory
	DESCRIPTION	"Option (1) prevents this voice/fax channel from receiving calls.
			The default is Option (2)." 
	::= {voiceFaxChSwParaEntry 6}

voiceFaxChSwParaCallInhibit  OBJECT-TYPE
	SYNTAX	INTEGER{
		on (1),
		off (2)
		}
	ACCESS	read-write
	STATUS	mandatory
	DESCRIPTION	"Option (1) prevents this voice/fax channel from initiating calls.
			The default is Option (2)." 
	::= {voiceFaxChSwParaEntry 7}


-- N_CMOS.O_VOCSYS ========================================================

voiceFaxChSwNumberOfDigitsInPhoneNumber OBJECT-TYPE
	SYNTAX	INTEGER (1..4)
	ACCESS	read-write
	STATUS	mandatory
	DESCRIPTION	"Number of digits in a phone number (1 - 4).  Note that all
			Integration units in a network must have the same value for
			this parameter." 
	 ::= {voice-fax-channel 3}

-- DIGITAL VOICE CHANNEL

-- N_CMOS.O_VOICE =========================================================

digitalVoiceChPhyParaTable OBJECT-TYPE
	SYNTAX	SEQUENCE OF DigitalVoiceChPhyParaEntry
	ACCESS	not-accessible
	STATUS	mandatory
	DESCRIPTION	"Table for configuring digital voice module (DVM) physical 
			parameters." 
	::= {digital-voice-channel 1}

digitalVoiceChPhyParaEntry OBJECT-TYPE
	SYNTAX	DigitalVoiceChPhyParaEntry
	ACCESS	not-accessible
	STATUS	mandatory
	DESCRIPTION	"Entry within the table to specify a particular DVM channel number
			on a specific module/card." 
	INDEX		{digitalVoiceChPhyParaCardNumber, digitalVoiceChPhyParaChannelNumber}
	::= {digitalVoiceChPhyParaTable 1}

DigitalVoiceChPhyParaEntry ::= SEQUENCE {
	digitalVoiceChPhyParaCardNumber			INTEGER,
	digitalVoiceChPhyParaChannelNumber		INTEGER,
	digitalVoiceChPhyParaViewSignallingType		INTEGER,
	digitalVoiceChPhyParaBergStrapType		INTEGER,
	digitalVoiceChPhyParaPortEmulation 		INTEGER,
	digitalVoiceChPhyParaSuppression		INTEGER,
	digitalVoiceChPhyParaJitter			INTEGER,
	digitalVoiceChPhyParaDTMFRegeneration	INTEGER,
	digitalVoiceChPhyParaAutoGainControl		INTEGER,
	digitalVoiceChPhyParaBackground			INTEGER,
	digitalVoiceChPhyParaDigitizingRate		INTEGER,
	digitalVoiceChPhyParaBusyMode			INTEGER,
	digitalVoiceChPhyParaVoiceFaxMode		INTEGER,
	digitalVoiceChPhyParaBandwidthAssignment	INTEGER,
	digitalVoiceChPhyParaInputGain			INTEGER,
	digitalVoiceChPhyParaChannelType		INTEGER,
	digitalVoiceChPhyParaOutputAttenuation		INTEGER,
	digitalVoiceChPhyParaPriority			INTEGER,
	digitalVoiceChPhyParaFaxDigitizingRate		INTEGER,
	digitalVoiceChPhyParaRegenerationDelay		INTEGER,
	digitalVoiceChPhyParaMaxDialDigitTimeLimit	INTEGER,
	digitalVoiceChPhyParaMaxNumFwdDigits		INTEGER,
	digitalVoiceChPhyParaCallProgressionTones	INTEGER,
	digitalVoiceChPhyParaRegenerationFormat		INTEGER,
	digitalVoiceChPhyParaCompander			INTEGER,
	digitalVoiceChPhyParaPremiumVoice 		INTEGER,
	digitalVoiceChPhyParaModuleIdentification		INTEGER,
	digitalVoiceChPhyParaChannelVersion		INTEGER
	}

digitalVoiceChPhyParaCardNumber OBJECT-TYPE
	SYNTAX	INTEGER (2..5)
	ACCESS	read-only
	STATUS	mandatory
	DESCRIPTION	"Identifies the module/card number for the DVM channel specific
			to the channel's physical parameters." 
	::= {digitalVoiceChPhyParaEntry 1}

digitalVoiceChPhyParaChannelNumber OBJECT-TYPE
	SYNTAX	INTEGER (1..12)
	ACCESS	read-only
	STATUS	mandatory
	DESCRIPTION	"Identifies the DVM channel specific to the channel's 
			physical parameters." 
	::= {digitalVoiceChPhyParaEntry 2}

digitalVoiceChPhyParaViewSignallingType OBJECT-TYPE
	SYNTAX	INTEGER {
		tieTrunk (1),
		transparent (2),
		dc5bInvert (3),
		tieInvert (4),
		dc5b (5),
		casVers01 (6),
		r2byQdot421 (7)
		}
	ACCESS	read-only
	STATUS	mandatory
	DESCRIPTION	"Indicates the DVM signalling type.  Note that Options 3, 5, 6,
			and 7 are only valid for E1 interfaces." 
	::= {digitalVoiceChPhyParaEntry 3}

digitalVoiceChPhyParaBergStrapType OBJECT-TYPE
	SYNTAX	INTEGER {
		digitalVoiceModule (1)
		}
	ACCESS	read-only
	STATUS	mandatory
	DESCRIPTION	"Indicates the Berg Hardware Strap configuration which is
			a constant value for DVM channels." 
	::= {digitalVoiceChPhyParaEntry 4}

digitalVoiceChPhyParaPortEmulation OBJECT-TYPE
	SYNTAX	INTEGER {
		tieTrunk (1),
		tieInvert (2),
		dc5bInvert (3),
		transparent (4),
		dc5b (5),
		casVers01 (6),
		r2byQdot421 (7)
		}
	ACCESS	read-write
	STATUS	mandatory
	DESCRIPTION	"Indicates the DVM port emulation.  Note that Options 3, 5,
			6, and 7 are only valid for E1 interfaces.  Options 3, 6, and 7
			are only configurable for DVMs with a Channel Version of '6' or
			greater, and which are running in a CCM software release environment
			of Phase 5.1 or greater." 
	::= {digitalVoiceChPhyParaEntry 5}

digitalVoiceChPhyParaSuppression OBJECT-TYPE
	SYNTAX	INTEGER
	ACCESS	read-only
	STATUS	mandatory
	DESCRIPTION	"During idle periods in which suppression is enabled (=0),
			the sending DVM channel DSP generates suppression service
			frames containing a noise level estimate and no data.  This 
			is sent to the receiving DVM channel DSP which will either
			regenerate the noise level or silence the output depending on
			the configuration of digitalVoiceChPhyParaBackground." 
	::= {digitalVoiceChPhyParaEntry 6}

digitalVoiceChPhyParaJitter OBJECT-TYPE
	SYNTAX	INTEGER
	ACCESS	read-only
	STATUS	mandatory
	DESCRIPTION	"Maintains continuous voice delivery by compensating (in
			milliseconds) for the transmission delay of packets.  Jitter
			provides compensation for the difference in arrival time and
			expected arrival time of DVM packets. (Range is 1 - 200 ms.).
			This parameter is configurable for DVMs with a Channel Version
			(voiceFaxChPhyParaChannelVersion) equal to '6' or higher, and
			residing in an Integration Unit with a software release
			(sysSoftwarePhase) of Phase 5.1 or Above."
	::= {digitalVoiceChPhyParaEntry 7}

digitalVoiceChPhyParaDTMFRegeneration OBJECT-TYPE
	SYNTAX	INTEGER {
		disable (1),
		enable (2)
		}
	ACCESS	read-write
	STATUS	mandatory
	DESCRIPTION	"DTMF Regeneration, when enabled, ensures that the DTMF
			signals at the remote side are regenerated with a uniform
			on/off time of 100 milliseconds.  This option is only compatible
			with other Voice/Fax modules that configure this parameter.
			This parameter is configurable DVMs with a Channel Version
			(voiceFaxChPhyParaChannelVersion) of '7' or greater and residing
			in an Integration Unit with a software release (sysSoftwarePhase)
			of Phase 5.1C and Above."
	::= {digitalVoiceChPhyParaEntry 8}

digitalVoiceChPhyParaAutoGainControl OBJECT-TYPE
	SYNTAX	INTEGER {
		disable (1),
		enable (2)
		}
	ACCESS	read-write
	STATUS	mandatory
	DESCRIPTION	"Automatic Gain Control, when enabled, boosts weak 
			input signals above the noise threshold to a minimum 
			usable level for DVM channels." 
	::= {digitalVoiceChPhyParaEntry 9}

digitalVoiceChPhyParaBackground OBJECT-TYPE
	SYNTAX	INTEGER {
		regenerated (1),
		silence (2)
		}
	ACCESS	read-write
	STATUS	mandatory
	DESCRIPTION	"The ability of passing background noise or silencing the channel 
			by the receiving DVM channel DSP during idle periods. First option
			allows the background noise to be regenerated during the periods, 
			whereas the second option suppresses background noise during 
			idle periods."
	::= {digitalVoiceChPhyParaEntry 10}


digitalVoiceChPhyParaDigitizingRate OBJECT-TYPE
	SYNTAX	INTEGER {
		rate4000 (1),
		rate4800 (2),
		rate6400 (3),
		rate7200 (4),
		rate8000 (5),
		rate9600 (6),
		rate12000 (7),
		rate14400 (8),
		rate16000 (9),
		rateG729 (10)
		}
	ACCESS	read-write
	STATUS	mandatory
	DESCRIPTION	"Configures the compression bandwidth for the DVM channel. 
			Larger bandwidths produce crisper voice communications. 
			However, larger DVM channel bandwidths may result in overbooking 
			of composite bandwidth.  The G.729 Digitizing Rate option
			(rateG729) is ONLY configurable for DVMs with a Channel Version
			(voiceFaxChPhyParaChannelVersion) of '5' or greater."
	::= {digitalVoiceChPhyParaEntry 11}

digitalVoiceChPhyParaBusyMode OBJECT-TYPE
	SYNTAX	INTEGER {
		forcedOff (1),
		forcedOn (2),
		systemControlled (3)
		}
	ACCESS	read-write
	STATUS	mandatory
	DESCRIPTION	"Controls how the busyout state of the DVM channel is determined." 
	::= {digitalVoiceChPhyParaEntry 12}

digitalVoiceChPhyParaVoiceFaxMode OBJECT-TYPE
	SYNTAX	INTEGER {
		voiceFax (1),
		voiceOnly (2)
		}
	ACCESS	read-write
	STATUS	mandatory
	DESCRIPTION	"Selects the DVM channel signal processing type, voice/fax or 
			voice only." 
	::= {digitalVoiceChPhyParaEntry 13}

digitalVoiceChPhyParaBandwidthAssignment OBJECT-TYPE
	SYNTAX	INTEGER {
		voiceActivated (1),
		continuous (2),
		dynamic (3)
		}
	ACCESS	read-write
	STATUS	mandatory
	DESCRIPTION	"Selects how the DVM channel uses link bandwidth: all the time 
			(continuous);only when voice/fax signals are present 
			(voiceActivated); or dynamically.  Option 3 not valid for G.729 
			value of digitalVoiceChPhyParaDigitizingRate." 
	::= {digitalVoiceChPhyParaEntry 14}

digitalVoiceChPhyParaInputGain OBJECT-TYPE
	SYNTAX	INTEGER (-6..8)
	ACCESS	read-write
	STATUS	mandatory
	DESCRIPTION	"Selects one of 15 input level gain values in 1 dB increments.
			The range is from -6 to 8, inclusive." 
	::= {digitalVoiceChPhyParaEntry 15}

digitalVoiceChPhyParaChannelType OBJECT-TYPE
	SYNTAX	INTEGER
	ACCESS	read-only
	STATUS	mandatory
	DESCRIPTION	"Unconfigurable by the User" 
	::= {digitalVoiceChPhyParaEntry 16}

digitalVoiceChPhyParaOutputAttenuation OBJECT-TYPE
	SYNTAX	INTEGER (0..8)
	ACCESS	read-write
	STATUS	mandatory
	DESCRIPTION	"Selects one out of 9 DVM output level attenuation values in 1 dB 
			increments. The range is 0 - 8, where =0 is no attenuation and =8 is
			 maximum attenuation." 
	::= {digitalVoiceChPhyParaEntry 17}

digitalVoiceChPhyParaPriority OBJECT-TYPE
	SYNTAX	INTEGER {
		high (1),
		low (2)
		}
	ACCESS	read-write
	STATUS	mandatory
	DESCRIPTION	"Selects the priority of the DVM channel, either high or low." 
	::= {digitalVoiceChPhyParaEntry 18}

digitalVoiceChPhyParaFaxDigitizingRate OBJECT-TYPE
	SYNTAX	INTEGER {
		useVoiceRate (1),
		rate2400 (2),
		rate4800 (3),
		rate7200 (4),
		rate9600 (5)
		}
	ACCESS	read-write
	STATUS	mandatory
	DESCRIPTION	"Sets the compression bandwidth for DVM channel Fax operations." 
	::= {digitalVoiceChPhyParaEntry 19}

digitalVoiceChPhyParaRegenerationDelay OBJECT-TYPE
	SYNTAX	INTEGER (1..15)
	ACCESS	read-write
	STATUS	mandatory
	DESCRIPTION	"The selected delay, ranging from 1 to 15 seconds, compensates 
			for the time it takes for the remote PBX to go off-hook and 
			provide a dial tone to the DVM channel for completing the 
			call setup.  The default is 1 second." 
	::= {digitalVoiceChPhyParaEntry 20}

digitalVoiceChPhyParaMaxDialDigitTimeLimit OBJECT-TYPE
	SYNTAX	INTEGER (1..15)
	ACCESS	read-write
	STATUS	mandatory
	DESCRIPTION	"The DVM dial digit time limit is the maximum time allowed for 
			accepting dialed digits.  When the dial digit time limit is 
			reached, further digits are not accepted, and the accumulated 
			digits are compared to the configured number of digits.  If the 
			accumulated number is less than the configured number, a fast 
			busy response is generated.  If the accumulated number is equal 
			to or more than the configred number, the digits are forwarded.
			The default is 10 seconds." 
	::= {digitalVoiceChPhyParaEntry 21}

digitalVoiceChPhyParaMaxNumFwdDigits OBJECT-TYPE
	SYNTAX	INTEGER (0..16)
	ACCESS	read-write
	STATUS	mandatory
	DESCRIPTION	"The selected value specifies the maximum number of dialing 
			digits to be forwarded by the DVM to the destination voice 
			channel without having to wait until the DVM dial digit time limit 
			is reached.  The range is 0-16, with zero disabling the store 
			and forward feature. The default value is 0." 
	::= {digitalVoiceChPhyParaEntry 22}

digitalVoiceChPhyParaCallProgressionTones OBJECT-TYPE
	SYNTAX	INTEGER {
		northAmerica (1),
		japan (2),
		unitedKingdom (3),
		germany (4),
		france (5),
		centralAmerica (6),
		chile (7),
		australia (8)
		}
	ACCESS	read-write
	STATUS	mandatory
	DESCRIPTION	"This option allows you to match the DVM channel call progress 
			to those of one of eight countries or areas." 
	::= {digitalVoiceChPhyParaEntry 23}

digitalVoiceChPhyParaRegenerationFormat OBJECT-TYPE
	SYNTAX	INTEGER {
		pulsedDialing (1),
		dtmfDialing (2)
		}
	ACCESS	read-write
	STATUS	mandatory
	DESCRIPTION	"DVM regeneration format supports the store 
			and forward function.  Designed for E&M and FXO interfaces,
			regeneration format allows the DVM channel to match the outgoing 
			dialing digits format with the format of the interfacing PBX." 
	::= {digitalVoiceChPhyParaEntry 24}

digitalVoiceChPhyParaCompander OBJECT-TYPE
	SYNTAX	INTEGER {
		uLaw (1),
		aLaw (2)
		}
	ACCESS	read-write
	STATUS	mandatory
	DESCRIPTION	"Option (1), uLaw, should be selected as the standard t1 
			compander format.  Option (2), aLaw, should be selected as 
			the standard e1 compander format.  Note that there is a rare
			mismatch to t1 equipment that uses an aLaw compander format." 
	::= {digitalVoiceChPhyParaEntry 25}

digitalVoiceChPhyParaPremiumVoice OBJECT-TYPE
	SYNTAX	INTEGER {
		disable (1),
		enable (2)
		}
	ACCESS	read-write
	STATUS	mandatory
	DESCRIPTION	"Option (2) allows transparent pass-through of uncompressed
			voice frames between DVM ports.  This option is used when two
			Integration unit voice ports may connect through the same PBX.
			Option (1) is used for normal operation in which calls always
			terminate in a telephone set.  This parameter is configurable
			for DVMs with a Channel Version (voiceFaxChPhyParaChannelVersion)
			equal to '5' or higher."
	::= {digitalVoiceChPhyParaEntry 26}

digitalVoiceChPhyParaModuleIdentification OBJECT-TYPE
	SYNTAX	INTEGER {
		t1 (1),
		e1 (2),
		invalid (3)
		}
	ACCESS	read-only
	STATUS	mandatory
	DESCRIPTION	"Identifies whether the DVM interfaces with a t1 vs. an e1 card." 
	::= {digitalVoiceChPhyParaEntry 27}

digitalVoiceChPhyParaChannelVersion OBJECT-TYPE
	SYNTAX	INTEGER {
		digitalVoiceModule (1),
		g729DigitizingRateSupported (2),
		phase5dot1 (3),
		dtmfRegne (4),
		casVer2 (5)
		}
	ACCESS	read-only
	STATUS	mandatory
	DESCRIPTION	"Identifies the compression algorithm used (installed software 
			version) by the DVM channel." 
	::= {digitalVoiceChPhyParaEntry 28}


-- N_CMOS.O_VOCSWI =======================================================

digitalVoiceChSwParaTable OBJECT-TYPE
	SYNTAX	SEQUENCE OF DigitalVoiceChSwParaEntry
	ACCESS	not-accessible
	STATUS	mandatory
	DESCRIPTION	"Table for configuring the DVM channel switching parameters." 
	::= {digital-voice-channel 2}

digitalVoiceChSwParaEntry OBJECT-TYPE
	SYNTAX	DigitalVoiceChSwParaEntry
	ACCESS	not-accessible
	STATUS	mandatory
	DESCRIPTION	"Entry within the table to specify a particular DVM channel number
			on a specific module/card for channel switching configuration." 
	INDEX		{digitalVoiceChSwParaCardNumber, digitalVoiceChSwParaChannelNumber}
	::= {digitalVoiceChSwParaTable 1}

DigitalVoiceChSwParaEntry ::= SEQUENCE {
	digitalVoiceChSwParaCardNumber	INTEGER,
	digitalVoiceChSwParaChannelNumber	INTEGER,
	digitalVoiceChSwParaVoiceExtension	DisplayString,
	digitalVoiceChSwParaAutoCallNumber	DisplayString,
	digitalVoiceChSwParaReceiveInhibit	INTEGER,
	digitalVoiceChSwParaCallInhibit		INTEGER
	}

digitalVoiceChSwParaCardNumber OBJECT-TYPE
	SYNTAX	INTEGER (2..5)
	ACCESS	read-only
	STATUS	mandatory
	DESCRIPTION	"Identifies the module/card number for the DVM channel specific
			to the channel's switching parameters." 
	::= {digitalVoiceChSwParaEntry 1}

digitalVoiceChSwParaChannelNumber OBJECT-TYPE
	SYNTAX	INTEGER (1..12)
	ACCESS	read-only
	STATUS	mandatory
	DESCRIPTION	"Identifies the DVM channel specific to the channel's 
			switching parameters." 
	::= {digitalVoiceChSwParaEntry 2}

digitalVoiceChSwParaVoiceExtension OBJECT-TYPE
	SYNTAX	DisplayString  (SIZE (0..4))
	ACCESS	read-write
	STATUS	mandatory
	DESCRIPTION	"Defines the voice extension for the DVM channel.
			The voice extension must consist of NUMERIC characters
			only." 
	::= {digitalVoiceChSwParaEntry 3}

digitalVoiceChSwParaAutoCallNumber OBJECT-TYPE
	SYNTAX	DisplayString  (SIZE (0..4))
	ACCESS	read-write
	STATUS	mandatory
	DESCRIPTION	"This is the extension number of a voice/fax port that is 
			called immediately if this DVM channel goes 'off hook'. 
			If no entry is made in this field, this function is disabled.
			The Auto Call Number must consist of NUMERIC characters only." 
	::= {digitalVoiceChSwParaEntry 4}

digitalVoiceChSwParaReceiveInhibit  OBJECT-TYPE
	SYNTAX	INTEGER {
		on (1),
		off (2)
		}
	ACCESS	read-write
	STATUS	mandatory
	DESCRIPTION	"Option (1) prevents this DVM channel from receiving calls.
			The default is Option (2)." 
	::= {digitalVoiceChSwParaEntry 5}

digitalVoiceChSwParaCallInhibit  OBJECT-TYPE
	SYNTAX	INTEGER{
		on (1),
		off (2)
		}
	ACCESS	read-write
	STATUS	mandatory
	DESCRIPTION	"Option (1) prevents this DVM channel from initiating calls.
			The default is Option (2)." 
	::= {digitalVoiceChSwParaEntry 6}


-- LINK GROUP


-- N_CMOS.O_PORT =========================================================

muxLinkCfgTable OBJECT-TYPE
	SYNTAX	SEQUENCE OF MuxLinkCfgEntry
	ACCESS	not-accessible
	STATUS	mandatory
	DESCRIPTION	"Table for configuring the clocking for a Mux Feeder link." 
	::= {mux-link 1}

muxLinkCfgEntry OBJECT-TYPE
	SYNTAX	MuxLinkCfgEntry
	ACCESS	not-accessible
	STATUS	mandatory
	DESCRIPTION	"Entry within the table to specify a particular Mux link port 
			number on a specific module/card." 
	INDEX		{muxLinkCfgCardNumber, muxLinkCfgChannelNumber}
	::= {muxLinkCfgTable 1} 

MuxLinkCfgEntry ::= SEQUENCE {
	muxLinkCfgCardNumber		INTEGER,
	muxLinkCfgChannelNumber	INTEGER,
	muxLinkCfgDataRate		INTEGER
	}

muxLinkCfgCardNumber OBJECT-TYPE
	SYNTAX	INTEGER (1..5)
	ACCESS	read-only
	STATUS	mandatory
	DESCRIPTION	"Identifies the module/card number specific to a particular 
			Mux link port." 
	::= {muxLinkCfgEntry 1}

muxLinkCfgChannelNumber OBJECT-TYPE
	SYNTAX	INTEGER (1..6)
	ACCESS	read-only
	STATUS	mandatory
	DESCRIPTION	"Identifies the specific Mux Link port number specific to 
			the link's clocking configuration." 
	::= {muxLinkCfgEntry 2}

muxLinkCfgDataRate OBJECT-TYPE
	SYNTAX	INTEGER {
		external (1),
		rate2400Sync (2),
		rate4800Sync (3),
		rate9600Sync (4),
		rate12000Sync (5),
		rate14400Sync (6),
		rate16800Sync (7),
		rate19200Sync (8),
		rate9600Async (9),
		rate1800Async (10),
		rate1200Async (11)
		}
	ACCESS	read-write
	STATUS	mandatory
--	DEFVAL	1
	DESCRIPTION	"Sets the type of clocking to be used on the mux link to be
			configured. Note: When the value of this parameter is 
			changed the link must be reset." 
	::= {muxLinkCfgEntry 3}

-- PreConfig Mux and Local ESI ================================================

muxOrLEsiPreConfigTable OBJECT-TYPE
	SYNTAX	SEQUENCE OF MuxOrLEsiPreConfigEntry
	ACCESS	not-accessible
	STATUS	mandatory
	DESCRIPTION	"Table to pre-configure the data rate of a Mux or Local ESI (LIL)
			Link prior to configuring the port as a Mux or LIL link. By 
			using this table to 'preset' the data rate, only 1 node reset 
			is needed following the port link assignment to complete the 
			configuration." 
	::= {mux-link 2}

muxOrLEsiPreConfigEntry OBJECT-TYPE
	SYNTAX	MuxOrLEsiPreConfigEntry
	ACCESS	not-accessible
	STATUS	mandatory
	DESCRIPTION	"Entry within the table to specify a particular port for Mux or
			LIL pre-configuration on a specific module/card." 
	INDEX		{muxOrLEsiPreConfigCardNumber, muxOrLEsiPreConfigChannelNumber}
	::= {muxOrLEsiPreConfigTable 1} 

MuxOrLEsiPreConfigEntry ::= SEQUENCE {
	muxOrLEsiPreConfigCardNumber		INTEGER,
	muxOrLEsiPreConfigChannelNumber	INTEGER,
	muxOrLEsiPreConfigDataRate		INTEGER
	}

muxOrLEsiPreConfigCardNumber OBJECT-TYPE
	SYNTAX	INTEGER (1..5)
	ACCESS	read-only
	STATUS	mandatory
	DESCRIPTION	"Identifies the module/card for Mux or LIL link pre-configuration." 
	::= {muxOrLEsiPreConfigEntry 1}

muxOrLEsiPreConfigChannelNumber OBJECT-TYPE
	SYNTAX	INTEGER (1..6)
	ACCESS	read-only
	STATUS	mandatory
	DESCRIPTION	"Identifies the port number for Mux or LIL link pre-configuration." 
	::= {muxOrLEsiPreConfigEntry 2}

muxOrLEsiPreConfigDataRate OBJECT-TYPE
	SYNTAX	INTEGER {
		muxOrLEsiExternal (1),
		muxRate2400Sync (2),
		muxRate4800Sync (3),
		muxRate9600Sync (4),
		muxRate12000Sync (5),
		muxRate14400Sync (6),
		muxRate16800Sync (7),
		muxRate19200Sync (8),
		muxRate9600Async (9),
		muxRate1800Async (10),
		muxRate1200Async (11),
		lEsiRate64000 (12),
		lEsiRate126000 (13),
		lEsiRate192000 (14),
		lEsiRate252000 (15)
		}
	ACCESS	write-only
	STATUS	mandatory
	DESCRIPTION	"Sets the data rate in bits per second for Mux and 
			LIL link pre-configurations." 
	::= {muxOrLEsiPreConfigEntry 3}


esiLinkCfgTable OBJECT-TYPE
	SYNTAX	SEQUENCE OF EsiLinkCfgEntry
	ACCESS	not-accessible
	STATUS	mandatory
	DESCRIPTION	"Table for configuring the data rate of an ESI (aka  
			Interconnect) link." 
	::= {esi-link 1}

esiLinkCfgEntry OBJECT-TYPE
	SYNTAX	EsiLinkCfgEntry
	ACCESS	not-accessible
	STATUS	mandatory
	DESCRIPTION	"Entry into the table pertaining to a specific ESI link on a
			specific module/card." 
	INDEX		{esiLinkCfgCardNumber, esiLinkCfgChannelNumber}
	::= {esiLinkCfgTable 1} 

EsiLinkCfgEntry ::= SEQUENCE {
	esiLinkCfgCardNumber		INTEGER,
	esiLinkCfgChannelNumber	INTEGER,
	esiLinkCfgDataRate		INTEGER
	}

esiLinkCfgCardNumber OBJECT-TYPE
	SYNTAX	INTEGER (1..5)
	ACCESS	read-only
	STATUS	mandatory
	DESCRIPTION	"Identifies the module/card number specific to the ESI link
			for data rate configuration." 
	::= {esiLinkCfgEntry 1}

esiLinkCfgChannelNumber OBJECT-TYPE
	SYNTAX	INTEGER (1..6)
	ACCESS	read-only
	STATUS	mandatory
	DESCRIPTION	"Identifies the ESI link port specific to the data rate 
			configuration." 
	::= {esiLinkCfgEntry 2}

esiLinkCfgDataRate OBJECT-TYPE
	SYNTAX	INTEGER {
		external (1),
		rate2400Sync (2),
		rate4800Sync (3),
		rate9600Sync (4),
		rate12000Sync (5),
		rate14400Sync (6),
		rate16800Sync (7),
		rate19200Sync (8),
		rate38400Sync (9),
		rate56000Sync (10),
		rate64000Sync (11)
		}
	ACCESS	read-write
	STATUS	mandatory
	DESCRIPTION	"Sets the link clocking method to external, or if internal, the
			data rate. Note: When the value of this parameter is changed,
			the link must be reset." 
	::= {esiLinkCfgEntry 3}

-- Pre-Configuration for Esi and ESI-Sec Link =========================================

esiOrSecLinkPreConfigTable OBJECT-TYPE
	SYNTAX	SEQUENCE OF EsiOrSecLinkPreConfigEntry
	ACCESS	not-accessible
	STATUS	mandatory
	DESCRIPTION	"Table to pre-configure the data rate of an ESI (aka Interconnect)
			Link (or secondary link) prior to configuring the link port.  By 
			using this table to 'preset' the data rate, only 1 node reset 
			is needed following the port link assignment to complete the 
			configuration." 
	::= {esi-link 2}

esiOrSecLinkPreConfigEntry OBJECT-TYPE
	SYNTAX	EsiOrSecLinkPreConfigEntry
	ACCESS	not-accessible
	STATUS	mandatory
	DESCRIPTION	"Entry within the table to specify a particular port for ESI or
			secondary link pre-configuration on a specific module/card." 
	INDEX		{esiOrSecLinkPreConfigCardNumber, esiOrSecLinkPreConfigChannelNumber}
	::= {esiOrSecLinkPreConfigTable 1} 

EsiOrSecLinkPreConfigEntry ::= SEQUENCE {
	esiOrSecLinkPreConfigCardNumber	INTEGER,
	esiOrSecLinkPreConfigChannelNumber	INTEGER,
	esiOrSecLinkPreConfigDataRate		INTEGER
	}

esiOrSecLinkPreConfigCardNumber OBJECT-TYPE
	SYNTAX	INTEGER (1..5)
	ACCESS	read-only
	STATUS	mandatory
	DESCRIPTION	"Identifies the module/card for ESI or secondary link 
			pre-configuration." 
	::= {esiOrSecLinkPreConfigEntry 1}

esiOrSecLinkPreConfigChannelNumber OBJECT-TYPE
	SYNTAX	INTEGER (1..6)
	ACCESS	read-only
	STATUS	mandatory
	DESCRIPTION	"Identifies the port number for ESI or secondary link 
			pre-configuration." 
	::= {esiOrSecLinkPreConfigEntry 2}

esiOrSecLinkPreConfigDataRate OBJECT-TYPE
	SYNTAX	INTEGER {
		external (1),
		rate2400Sync (2),
		rate4800Sync (3),
		rate9600Sync (4),
		rate12000Sync (5),
		rate14400Sync (6),
		rate16800Sync (7),
		rate19200Sync (8),
		rate38400Sync (9),
		rate56000Sync (10),
		rate64000Sync (11)
		}
	ACCESS	write-only
	STATUS	mandatory
	DESCRIPTION	"Sets the data rate in bits per second for ESI and secondary 
			link pre-configurations.  Note: The only valid data rate 
			value for Secondary links is 'external (1)'.  (Secondary links 
			exclusively use external clocking.)" 
	::= {esiOrSecLinkPreConfigEntry 3}

-- N_CMOS.O_LKACTV ========================================================

esiOrSecLinkAssignCfgTable OBJECT-TYPE
	SYNTAX	SEQUENCE OF EsiOrSecLinkAssignCfgEntry
	ACCESS	not-accessible
	STATUS	mandatory
	DESCRIPTION	"Table for configuring the activation and deactivation
			of ESI (aka Interconnect) and secondary links." 
	::= {esi-link 3}

esiOrSecLinkAssignCfgEntry OBJECT-TYPE
	SYNTAX	EsiOrSecLinkAssignCfgEntry
	ACCESS	not-accessible
	STATUS	mandatory
	DESCRIPTION	"Entry into the table pertaining to a specific ESI or secondary
			link for activation/deactivation configuration on a specific 
			module/card." 
	INDEX		{esiOrSecLinkAssignCfgCardNumber,
			 esiOrSecLinkAssignCfgChannelNumber}
	::= {esiOrSecLinkAssignCfgTable 1} 

EsiOrSecLinkAssignCfgEntry ::= SEQUENCE {
	esiOrSecLinkAssignCfgCardNumber				INTEGER,
	esiOrSecLinkAssignCfgChannelNumber				INTEGER,
	esiOrSecLinkAssignCfgLinkForcedOn				INTEGER,
	esiOrSecLinkAssignCfgSecLinkBackUpOnly			INTEGER,
	esiOrSecLinkAssignCfgUtilThresholdToActivateSec			INTEGER,
	esiOrSecLinkAssignCfgUtilThresholdToDeactivateSec		INTEGER,
	esiOrSecLinkAssignCfgTimeThresholdExceedToActivateSec		INTEGER,
	esiOrSecLinkAssignCfgTimeThresholdBelowToDeactivateSec	INTEGER,
	esiOrSecLinkAssignCfgTerminateCallonDeactivation		INTEGER
	}

esiOrSecLinkAssignCfgCardNumber OBJECT-TYPE
	SYNTAX	INTEGER
	ACCESS	read-only
	STATUS	mandatory
	DESCRIPTION	"Identifies the module/card number specific to the ESI or 
			secondary link for activation/deactivation configuration." 
	 ::= {esiOrSecLinkAssignCfgEntry 1}

esiOrSecLinkAssignCfgChannelNumber OBJECT-TYPE
	SYNTAX	INTEGER
	ACCESS	read-only
	STATUS	mandatory
	DESCRIPTION	"Identifies the ESI or secondary link port specific to the 
			activation/deactivation configuration." 
	 ::= {esiOrSecLinkAssignCfgEntry 2}

esiOrSecLinkAssignCfgLinkForcedOn OBJECT-TYPE
	SYNTAX	INTEGER {
		yes (1),
		no (2)
		}
	ACCESS	read-write
	STATUS	mandatory
	DESCRIPTION	"Both the primary and secondary links can be configured 
			as Forced On.  This overrides the current time of day and 
			utilization restrictions for testing, or to provide bandwidth 
			during a normally off period without changing other 
			configuration.  The default is YES for primary links and 
			NO for secondary links." 
	 ::= {esiOrSecLinkAssignCfgEntry 3}

esiOrSecLinkAssignCfgSecLinkBackUpOnly OBJECT-TYPE
	SYNTAX	INTEGER {
		yes (1),
		no (2)
		}
	ACCESS	read-write
	STATUS	mandatory
	DESCRIPTION	"If the primary or secondary link is configured to be off, 
			according to the time of day configuration, then the secondary 
			link will not be activated upon primary link. The default value, 
			Yes, indicates the secondary link is for backup only." 
	 ::= {esiOrSecLinkAssignCfgEntry 4}

esiOrSecLinkAssignCfgUtilThresholdToActivateSec OBJECT-TYPE
	SYNTAX	INTEGER (1..99)
	ACCESS	read-write
	STATUS	mandatory
	DESCRIPTION	"This option allows utilization thresholds to be set for 
			activation of the secondary link. Utilization thresholds 
			are specified as a percentage of available bandwidth on the 
			primary link.  Secondary channels may be configured to become 
			active when the bandwidth utilization on the primary link 
			exceeds a predetermined threshold. The secondary link will 
			also be activated if primary link failure is detected. However, 
			the secondary link will not be activated if either the secondary 
			or primary link is configured to be off according to the time 
			of day configuration.  The default value is 75." 
	 ::= {esiOrSecLinkAssignCfgEntry 5}

esiOrSecLinkAssignCfgUtilThresholdToDeactivateSec OBJECT-TYPE
	SYNTAX	INTEGER (1..99)
	ACCESS	read-write
	STATUS	mandatory
	DESCRIPTION	"This option allow utilization thresholds to be set for 
			deactivation of the secondary link.  The secondary link will 
			be de-activated when the total utilization drops below a configured 
			threshold.  The de-activation threshold value must be less than 
			the activation threshold value. The default value is 50." 
	 ::= {esiOrSecLinkAssignCfgEntry 6}

esiOrSecLinkAssignCfgTimeThresholdExceedToActivateSec OBJECT-TYPE
	SYNTAX	INTEGER (1..40)
	ACCESS	read-write
	STATUS	mandatory
	DESCRIPTION	"Time (in minutes) that utilization threshold (to activate) must 
			be exceeded to activate a secondary link. The default value is 5." 
	 ::= {esiOrSecLinkAssignCfgEntry 7}

esiOrSecLinkAssignCfgTimeThresholdBelowToDeactivateSec OBJECT-TYPE
	SYNTAX	INTEGER (1..40)
	ACCESS	read-write
	STATUS	mandatory
	DESCRIPTION	"Time (in minutes) that utilization threshold (to deactivate) must 
			be below to deactivate a secondary link. The default value is 5." 
	 ::= {esiOrSecLinkAssignCfgEntry 8}

esiOrSecLinkAssignCfgTerminateCallonDeactivation OBJECT-TYPE
	SYNTAX	INTEGER {
		yes (1),
		no (2)
		}
	ACCESS	read-write
	STATUS	mandatory
	DESCRIPTION	"This parameter allows the option of leaving a link up if a 
			switched voice call is in place even if the time of day 
			configuration indicates it is time to deactivate the link. 
			Setting this parameter to NO will bring down the link only 
			when all switched voice calls have hung up. The default is NO." 
	 ::= {esiOrSecLinkAssignCfgEntry 9}

-- N_CMOS.O_TODSCH ========================================================

esiOrSecLinkTODActivationTable OBJECT-TYPE
	SYNTAX	SEQUENCE OF EsiOrSecLinkTODActivationEntry
	ACCESS	not-accessible
	STATUS	mandatory
	DESCRIPTION	"Table for configuring the Time Of Day (TOD) activation 
			and deactivation schedule of ESI (aka Interconnect) and 
			secondary links." 
	::= {esi-link 4}

esiOrSecLinkTODActivationEntry OBJECT-TYPE
	SYNTAX	EsiOrSecLinkTODActivationEntry
	ACCESS	not-accessible
	STATUS	mandatory
	DESCRIPTION	"Entry into the table pertaining to a specific module/card,
			port location, day schedule, and time schedule for setting
			ESI or secondary link activation/deactivation configurations." 
	INDEX		{esiOrSecLinkTODActivationCardNumber,
			 esiOrSecLinkTODActivationChannelNumber,
			esiOrSecLinkTODActivationSetSchedule,
			esiOrSecLinkTODActivationTenMinInterval}
	::= {esiOrSecLinkTODActivationTable 1} 

EsiOrSecLinkTODActivationEntry ::= SEQUENCE {
	esiOrSecLinkTODActivationCardNumber		INTEGER,
	esiOrSecLinkTODActivationChannelNumber	INTEGER,
	esiOrSecLinkTODActivationSetSchedule		INTEGER,
	esiOrSecLinkTODActivationTenMinInterval	INTEGER,
	esiOrSecLinkTODActivationLinkState		INTEGER
	}

esiOrSecLinkTODActivationCardNumber OBJECT-TYPE
	SYNTAX	INTEGER
	ACCESS	read-only
	STATUS	mandatory
	DESCRIPTION	"Identifies the module/card number specific to an ESI or secondary
			link for the TOD activation/deactivation schedule." 
	 ::= {esiOrSecLinkTODActivationEntry 1}

esiOrSecLinkTODActivationChannelNumber OBJECT-TYPE
	SYNTAX	INTEGER
	ACCESS	read-only
	STATUS	mandatory
	DESCRIPTION	"Identifies the port location specific to an ESI or secondary
			link for the TOD activation/deactivation schedule." 
	 ::= {esiOrSecLinkTODActivationEntry 2}

esiOrSecLinkTODActivationSetSchedule OBJECT-TYPE
	SYNTAX	INTEGER {
		sunday (1),
		weekdays (2),
		saturday (3)
		}
	ACCESS	read-only
	STATUS	mandatory
	DESCRIPTION	"Identifies the particular day(s) schedule specific to an ESI 
			or secondary link for the TOD activation/deactivation schedule." 
	 ::= {esiOrSecLinkTODActivationEntry 3}

esiOrSecLinkTODActivationTenMinInterval OBJECT-TYPE
	SYNTAX	INTEGER (1..144)
	ACCESS	read-only
	STATUS	mandatory
	DESCRIPTION	"Identifies the particular time of day (in 10 minute intervals)
			specific to an ESI or secondary link for the TOD 
			activation/deactivation schedule." 
	 ::= {esiOrSecLinkTODActivationEntry 4}

esiOrSecLinkTODActivationLinkState OBJECT-TYPE
	SYNTAX	INTEGER {
		off (1),
		on (2)
		}
	ACCESS	read-write
	STATUS	mandatory
	DESCRIPTION	"Sets the TOD link state for an ESI or secondary link.  This 
			parameter is used to configure a link to active (on) or not active 
			(off) for a particular 10 minute interval as specified by the 
			previous 4 indexing parameters contained in this table." 
	 ::= {esiOrSecLinkTODActivationEntry 5}


x21LinkCfgTable OBJECT-TYPE
	SYNTAX	SEQUENCE OF X21LinkCfgEntry
	ACCESS	not-accessible
	STATUS	mandatory
	DESCRIPTION	"Table to configure the X.21 links. It defines the X.21 parameters
			for the Integration unit and for the MICOM mux side." 
	::= {x-dot-21-link 1}

x21LinkCfgEntry OBJECT-TYPE
	SYNTAX	X21LinkCfgEntry
	ACCESS	not-accessible
	STATUS	mandatory
	DESCRIPTION	"Entry in the table for a particular X.21 link.  Note that a link 
			reset is required if any value in this table is changed." 
	INDEX		{x21LinkCfgCardNumber, x21LinkCfgChannelNumber}
	::= {x21LinkCfgTable 1} 

X21LinkCfgEntry ::= SEQUENCE {
	x21LinkCfgCardNumber			INTEGER,
	x21LinkCfgChannelNumber		INTEGER,
	x21LinkCfgLocalConnectMode		INTEGER,
	x21LinkCfgRemoteConnectMode		INTEGER,
	x21LinkCfgLocalConnectTimeout		INTEGER,
	x21LinkCfgRemoteConnectTimeout	INTEGER,
	x21LinkCfgLocalConnectRetries		INTEGER,
	x21LinkCfgRemoteConnectRetries		INTEGER
	}

x21LinkCfgCardNumber OBJECT-TYPE
	SYNTAX	INTEGER
	ACCESS	read-only
	STATUS	mandatory
	DESCRIPTION	"The card/module number of the X.21 link channel the entry pertains to." 
	::= {x21LinkCfgEntry 1}

x21LinkCfgChannelNumber OBJECT-TYPE
	SYNTAX	INTEGER
	ACCESS	read-only
	STATUS	mandatory
	DESCRIPTION	"The particular X.21 link channel on specific module to be configured." 
	::= {x21LinkCfgEntry 2}

x21LinkCfgLocalConnectMode OBJECT-TYPE
	SYNTAX	INTEGER {
		dataActivityConnect (1),
		dtrConnect (2)
		}
	ACCESS	read-write
	STATUS	mandatory
--	DEFVAL	1
	DESCRIPTION	"Configures the Integration unit side of the X.21 link.  
			In Integration units, the only connect mode for X.21 
			links is data activity connect. In this mode, the Integration
			unit will place a call over the X.21 network whenever data 
			activity is detected on any force connected channel, matrix
			connection, or port connected to a class defined with ports on 
			a MICOM mux attached to an X.21 link." 
	::= {x21LinkCfgEntry 3}

x21LinkCfgRemoteConnectMode OBJECT-TYPE
	SYNTAX	INTEGER {
		dataActivityConnect(1),
		dtrConnect (2)
		}
	ACCESS	read-write
	STATUS	mandatory
--	DEFVAL	1
	DESCRIPTION	"Configures the MICOM mux side of the X.21 link. There 
			are two options: DTR and Data Activity Connect.  DTR 
			(DTR connect) establishes the X.21 connection whenever 
			DTR is raised on any terminal connected to the MICOM mux.
			Data Activity Connect establishes the X.21 connection 
			whenever data activity is detected on any terminal connected 
			to the MICOM mux." 
	::= {x21LinkCfgEntry 4}

x21LinkCfgLocalConnectTimeout OBJECT-TYPE
	SYNTAX	INTEGER (0..20)
	ACCESS	read-write
	STATUS	mandatory
--	DEFVAL	5
	DESCRIPTION	"The value in this field specifies the amount of time that if no 
			data activity is detected, the X.21 connection will be dropped. 
			The default is 5 seconds." 
	::= {x21LinkCfgEntry 5}

x21LinkCfgRemoteConnectTimeout OBJECT-TYPE
	SYNTAX	INTEGER (0..20)
	ACCESS	read-write
	STATUS	mandatory
--	DEFVAL	5
	DESCRIPTION	"If data activity connect mode is selected for the remote MICOM 
			mux, this field specifies the amount of time that if no data 
			activity is detected on any of the MICOM mux's channels, the X.21 
			connection will be dropped. The default is 5 seconds." 
	::= {x21LinkCfgEntry 6}

x21LinkCfgLocalConnectRetries OBJECT-TYPE
	SYNTAX	INTEGER (1..64)
	ACCESS	read-write
	STATUS	mandatory
--	DEFVAL	20
	DESCRIPTION	"Configures the number of attempts the Integration unit will make to
			place a call over the X.21 network." 
	::= {x21LinkCfgEntry 7}

x21LinkCfgRemoteConnectRetries OBJECT-TYPE
	SYNTAX	INTEGER (1..64)
	ACCESS	read-write
	STATUS	mandatory
--	DEFVAL	20
	DESCRIPTION	"Configures the number of attempts the MICOM mux will 
			make to place a call over the X.21 network." 
	::= {x21LinkCfgEntry 8}

-- PreConfig x.21 ==============================================================

x21LinkPreConfigTable OBJECT-TYPE
	SYNTAX	SEQUENCE OF X21LinkPreConfigEntry
	ACCESS	not-accessible
	STATUS	mandatory
	DESCRIPTION	"Table to configure an X.21 link prior to configuring
			a port as an X.21 link. By using this table to 'preset' the X.21
			link parameters, only 1 node reset is needed following the X.21
			assignment to complete the configuration."
	::= {x-dot-21-link 2}

x21LinkPreConfigEntry OBJECT-TYPE
	SYNTAX	X21LinkPreConfigEntry
	ACCESS	not-accessible
	STATUS	mandatory
	DESCRIPTION	"Entry within the table to specify a particular port number for
			pre-configuration of an X.21 link on a specific module/card." 
	INDEX		{x21LinkPreConfigCardNumber, x21LinkPreConfigChannelNumber}
	::= {x21LinkPreConfigTable 1} 

X21LinkPreConfigEntry ::= SEQUENCE {
	x21LinkPreConfigCardNumber			INTEGER,
	x21LinkPreConfigChannelNumber			INTEGER,
	x21LinkPreConfigLocalConnectMode		INTEGER,
	x21LinkPreConfigRemoteConnectMode		INTEGER,
	x21LinkPreConfigLocalConnectTimeout		INTEGER,
	x21LinkPreConfigRemoteConnectTimeout	INTEGER,
	x21LinkPreConfigLocalConnectRetries		INTEGER,
	x21LinkPreConfigRemoteConnectRetries		INTEGER
	}

x21LinkPreConfigCardNumber OBJECT-TYPE
	SYNTAX	INTEGER (1..5)
	ACCESS	read-only
	STATUS	mandatory
	DESCRIPTION	"The card/module number of the X.21 link channel to be pre-configured." 
	::= {x21LinkPreConfigEntry 1}

x21LinkPreConfigChannelNumber OBJECT-TYPE
	SYNTAX	INTEGER (1..6)
	ACCESS	read-only
	STATUS	mandatory
	DESCRIPTION	"The particular X.21 link channel on specific module to be 
			pre-configured." 
	::= {x21LinkPreConfigEntry 2}

x21LinkPreConfigLocalConnectMode OBJECT-TYPE
	SYNTAX	INTEGER {
		dataActivityConnect (1),
		dtrConnect (2)
		}
	ACCESS	write-only 
	STATUS	mandatory
	DESCRIPTION	"Pre-configures the Integration unit side of the X.21 link.  
			In Integration units, the only connect mode for X.21 
			links is data activity connect. In this mode, the Integration
			unit will place a call over the X.21 network whenever data 
			activity is detected on any force connected channel, matrix
			connection, or port connected to a class defined with ports on 
			a MICOM mux attached to an X.21 link." 
	::= {x21LinkPreConfigEntry 3}

x21LinkPreConfigRemoteConnectMode OBJECT-TYPE
	SYNTAX	INTEGER {
		dataActivityConnect(1),
		dtrConnect (2)
		}
	ACCESS	write-only 
	STATUS	mandatory
	DESCRIPTION	"Pre-configures the MICOM mux side of the X.21 link. There 
			are two options: DTR and Data Activity Connect.  DTR 
			(DTR connect) establishes the X.21 connection whenever 
			DTR is raised on any terminal connected to the MICOM mux.
			Data Activity Connect establishes the X.21 connection 
			whenever data activity is detected on any terminal connected 
			to the MICOM mux." 
	::= {x21LinkPreConfigEntry 4}

x21LinkPreConfigLocalConnectTimeout OBJECT-TYPE
	SYNTAX	INTEGER (0..20)
	ACCESS	write-only 
	STATUS	mandatory
	DESCRIPTION	"Pre-configuration of this field specifies the amount of time that  
			if no data activity is detected, the X.21 connection will be dropped." 
--	DEFVAL	5
	::= {x21LinkPreConfigEntry 5}

x21LinkPreConfigRemoteConnectTimeout OBJECT-TYPE
	SYNTAX	INTEGER (0..20)
	ACCESS	write-only 
	STATUS	mandatory
--	DEFVAL	5
	DESCRIPTION	"If data activity connect mode is selected for the remote MICOM 
			mux, pre-configuration of this field specifies the amount of time 
			that if no data activity is detected on any of the MICOM mux's 
			channels, the X.21 connection will be dropped." 
	::= {x21LinkPreConfigEntry 6}

x21LinkPreConfigLocalConnectRetries OBJECT-TYPE
	SYNTAX	INTEGER (1..64)
	ACCESS	write-only 
	STATUS	mandatory
--	DEFVAL	20
	DESCRIPTION	"Pre-configures the number of attempts the Integration unit will 
			make to place a call over the X.21 network." 
	::= {x21LinkPreConfigEntry 7}

x21LinkPreConfigRemoteConnectRetries OBJECT-TYPE
	SYNTAX	INTEGER (1..64)
	ACCESS	write-only 
	STATUS	mandatory
--	DEFVAL	20
	DESCRIPTION	"Pre-configures the number of attempts the MICOM mux will 
			make to place a call over the X.21 network." 
	::= {x21LinkPreConfigEntry 8}


localESILinkCfgTable OBJECT-TYPE
	SYNTAX	SEQUENCE OF LocalESILinkCfgEntry
	ACCESS	not-accessible
	STATUS	mandatory
	DESCRIPTION	"Table to configure the data rate for a local ESI link
			(aka Local Interconnect Link or LIL)." 
	::= {local-esi-link 1}

localESILinkCfgEntry OBJECT-TYPE
	SYNTAX	LocalESILinkCfgEntry
	ACCESS	not-accessible
	STATUS	mandatory
	DESCRIPTION	"Entry within the table to specify a particular port number
			on a specific module/card for an LIL configuration." 
	INDEX		{localESILinkCfgCardNumber, localESILinkCfgChannelNumber}
	::= {localESILinkCfgTable 1} 

LocalESILinkCfgEntry ::= SEQUENCE {
	localESILinkCfgCardNumber	INTEGER,
	localESILinkCfgChannelNumber	INTEGER,
	localESILinkCfgDataRate		INTEGER
	}

localESILinkCfgCardNumber OBJECT-TYPE
	SYNTAX	INTEGER (1..5)
	ACCESS	read-only
	STATUS	mandatory
	DESCRIPTION	"Identifies the specific module/card number for an LIL
			configuration." 
	::= {localESILinkCfgEntry 1}

localESILinkCfgChannelNumber OBJECT-TYPE
	SYNTAX	INTEGER (1..6)
	ACCESS	read-only
	STATUS	mandatory
	DESCRIPTION	"Identifies the specific port number for an LIL configuration." 
	::= {localESILinkCfgEntry 2}

localESILinkCfgDataRate OBJECT-TYPE
	SYNTAX	INTEGER {
		external (1),
		rate64000 (2),
		rate126000 (3),
		rate192000 (4),
		rate252000 (5)
		}
	ACCESS	read-write
	STATUS	mandatory
--	DEFVAL	1
	DESCRIPTION	"Sets the link clocking method to external, or if internal, the
			data rate for an LIL. Note: When the value of this parameter is 
			changed, the link must be reset." 
	::= {localESILinkCfgEntry 3}


esiSecLinkCfgTable OBJECT-TYPE
	SYNTAX	SEQUENCE OF EsiSecLinkCfgEntry
	ACCESS	not-accessible
	STATUS	mandatory
	DESCRIPTION	"Table to configure the data rate for a secondary ESI link." 
	::= {esi-secondary-link 1}

esiSecLinkCfgEntry OBJECT-TYPE
	SYNTAX	EsiSecLinkCfgEntry
	ACCESS	not-accessible
	STATUS	mandatory
	DESCRIPTION	"Entry within the table to specify a particular port number
			on a specific module/card for a secondary ESI link configuration." 
	INDEX		{esiSecLinkCfgCardNumber, esiSecLinkCfgChannelNumber}
	::= {esiSecLinkCfgTable 1} 

EsiSecLinkCfgEntry ::= SEQUENCE {
	esiSecLinkCfgCardNumber	INTEGER,
	esiSecLinkCfgChannelNumber	INTEGER,
	esiSecLinkCfgDataRate		INTEGER
	}

esiSecLinkCfgCardNumber OBJECT-TYPE
	SYNTAX	INTEGER (1..5)
	ACCESS	read-only
	STATUS	mandatory
	DESCRIPTION	"Identifies the specific module/card number for a secondary
			ESI link configuration." 
	::= {esiSecLinkCfgEntry 1}

esiSecLinkCfgChannelNumber OBJECT-TYPE
	SYNTAX	INTEGER (1..6)
	ACCESS	read-only
	STATUS	mandatory
	DESCRIPTION	"Identifies the specific port number for a secondary ESI link
			configuration." 
	::= {esiSecLinkCfgEntry 2}

esiSecLinkCfgDataRate OBJECT-TYPE
	SYNTAX	INTEGER {
		external (1),
		rate2400Sync (2),
		rate4800Sync (3),
		rate9600Sync (4),
		rate12000Sync (5),
		rate14400Sync (6),
		rate16800Sync (7),
		rate19200Sync (8),
		rate38400Sync (9),
		rate56000Sync (10),
		rate64000Sync (11)
		}
	ACCESS	read-write
	STATUS	mandatory
	DESCRIPTION	"Sets the link clocking method to external, or if internal, the
			data rate for a secondary ESI link. Note: When the value of this
			parameter is changed, the link must be reset." 
	::= {esiSecLinkCfgEntry 3}

-- N_CMOS.O_ESI2L ========================================================

esiSecLinkAssignmentTable OBJECT-TYPE
	SYNTAX	SEQUENCE OF EsiSecLinkAssignmentEntry
	ACCESS	not-accessible
	STATUS	mandatory
	DESCRIPTION	"Table to assign a secondary link channel to a primary 
			ESI link." 
	::= {esi-secondary-link 2}

esiSecLinkAssignmentEntry OBJECT-TYPE
	SYNTAX	EsiSecLinkAssignmentEntry
	ACCESS	not-accessible
	STATUS	mandatory
	DESCRIPTION	"Entry within the table to specify a particular link/port
			on a specific module/card for a secondary assignment to a
			primary link." 
	INDEX		{esiSecLinkAssignmentSecCardNumber,
			 esiSecLinkAssignmentSecChannelNumber}
	::= {esiSecLinkAssignmentTable 1} 

EsiSecLinkAssignmentEntry ::= SEQUENCE {
	esiSecLinkAssignmentSecCardNumber	INTEGER,
	esiSecLinkAssignmentSecChannelNumber	INTEGER,
	esiSecLinkAssignmentEntryAction		INTEGER,
	esiSecLinkAssignmentPriCardNumber	INTEGER,
	esiSecLinkAssignmentPriChannelNumber	INTEGER
	}

esiSecLinkAssignmentSecCardNumber OBJECT-TYPE
	SYNTAX	INTEGER
	ACCESS	read-only
	STATUS	mandatory
	DESCRIPTION	"Identifies the specific module/card number of the link
			to be assigned as the secondary link." 
	 ::= {esiSecLinkAssignmentEntry 1}

esiSecLinkAssignmentSecChannelNumber OBJECT-TYPE
	SYNTAX	INTEGER
	ACCESS	read-only
	STATUS	mandatory
	DESCRIPTION	"Identifies the specific link/port number of the link
			to be assigned as the secondary link." 
	 ::= {esiSecLinkAssignmentEntry 2}

esiSecLinkAssignmentEntryAction OBJECT-TYPE
	SYNTAX	INTEGER {
		active (1)
		}
	ACCESS	write-only
	STATUS	mandatory
	DESCRIPTION	"This is the command to perform the secondary link assignment. 
			Selecting 'active' following the successful setting of 
			esiSecLinkAssignmentPriCardNumber & esiSecLinkAssignmentPriChannelNumber
			will complete the assignment." 
	::= {esiSecLinkAssignmentEntry 3}

esiSecLinkAssignmentPriCardNumber OBJECT-TYPE
	SYNTAX	INTEGER
	ACCESS	read-write
	STATUS	mandatory
	DESCRIPTION	"Indicates the card number where the primary link channel is residing. 
			A GET value of FFh indicates that no secondary link assignment 
			currently exists.  A SET with a value of zero (0)
			with zero (0) as the channel number de-assigns the link." 
	 ::= {esiSecLinkAssignmentEntry 4}

esiSecLinkAssignmentPriChannelNumber OBJECT-TYPE
	SYNTAX	INTEGER
	ACCESS	read-write
	STATUS	mandatory
	DESCRIPTION	"Indicates the channel number where the primary channel is residing. 
			A read value of FFh indicates that no secondary link assignment 
			currently exists.  A SET with a value of zero (0)
			with zero (0) as the card number de-assigns the link. " 
	 ::= {esiSecLinkAssignmentEntry 5}



-- FRAME RELAY

frameRelayLinkCfgTable OBJECT-TYPE
	SYNTAX	SEQUENCE OF FrameRelayLinkEntry
	ACCESS	not-accessible
	STATUS	mandatory
	DESCRIPTION	"Table to configure a Frame Relay link." 
	::= {frame-relay-link 1}

frameRelayLinkCfgEntry OBJECT-TYPE
	SYNTAX	FrameRelayLinkEntry
	ACCESS	not-accessible
	STATUS	mandatory
	DESCRIPTION	"Entry within the table to specify a particular port number
			on a specific module/card for a Frame Relay link configuration." 
	INDEX		{frameRelayLinkCfgCardNumber, frameRelayLinkCfgChannelNumber}
	::= {frameRelayLinkCfgTable 1} 

FrameRelayLinkEntry ::= SEQUENCE {
	frameRelayLinkCfgCardNumber			INTEGER,
	frameRelayLinkCfgChannelNumber		INTEGER,
	frameRelayLinkCfgDataRate			INTEGER,
	frameRelayLinkCfgLocalMgmtProtocol		INTEGER,
	frameRelayLinkCfgFullStatusPollingCounter	INTEGER,
	frameRelayLinkCfgErrorThreshold			INTEGER,
	frameRelayLinkCfgEventCount			INTEGER,
	frameRelayLinkCfgLinkIntegrityVerificationTimer	INTEGER,
	frameRelayLinkCfgPollingVerificationTimer	INTEGER,
	frameRelayLinkCfgMaxFrameSize			INTEGER,
	frameRelayLinkCfgRxClockingSource		INTEGER,
	frameRelayLinkCfgTxClockingSource		INTEGER,
	frameRelayLinkCfgNetworkAddress		OCTET STRING,
	frameRelayLinkCfgAccessLinkMode 		INTEGER
	}

frameRelayLinkCfgCardNumber OBJECT-TYPE
	SYNTAX	INTEGER
	ACCESS	read-only
	STATUS	mandatory
	DESCRIPTION	"Identifies the specific module/card number for a Frame Relay
			link configuration." 
	 ::= {frameRelayLinkCfgEntry 1}

frameRelayLinkCfgChannelNumber OBJECT-TYPE
	SYNTAX	INTEGER
	ACCESS	read-only
	STATUS	mandatory
	DESCRIPTION	"Identifies the specific port number for a Frame Relay link
			configuration." 
	 ::= {frameRelayLinkCfgEntry 2}

frameRelayLinkCfgDataRate OBJECT-TYPE
	SYNTAX	INTEGER {
		rate9600 (1),
		rate19200 (2),
		rate64000 (3),
		rate126000 (4),
		rate126400 (5),
		rate128000 (6),
		rate189500 (7),
		rate192000 (8),
		rate246400 (9),
		rate252000 (10),
		rate256000 (11),
		rate308000 (12),
		rate310200 (13),
		rate336000 (14),
		rate366500 (15),
		rate379100 (16),
		rate384000 (17),
		rate448000 (18),
		rate492800 (19),
		rate504000 (20),
		rate537600 (21)
		}
	ACCESS	read-write
	STATUS	mandatory
--	DEFVAL	3
	DESCRIPTION	"Sets the data rate for a Frame Relay link.  Note: If the 
			frame relay access link is externally clocked, no configuration
			of this paramter is necessary." 
	::= { frameRelayLinkCfgEntry 3}

frameRelayLinkCfgLocalMgmtProtocol OBJECT-TYPE
	SYNTAX	INTEGER {
		none (1),
		annexD (2),
		lmi (3)
		}
	ACCESS	read-write
	STATUS	mandatory
--	DEFVAL	2
	DESCRIPTION	"Sets the frame relay access link local management protocol." 
	::= { frameRelayLinkCfgEntry 4}

frameRelayLinkCfgFullStatusPollingCounter OBJECT-TYPE
	SYNTAX	INTEGER (1..255)
	ACCESS	read-write
	STATUS	mandatory
--	DEFVAL	6
	DESCRIPTION	"Sets the frame relay access link full status poll counter." 
	::= { frameRelayLinkCfgEntry 5}

frameRelayLinkCfgErrorThreshold OBJECT-TYPE
	SYNTAX	INTEGER (1..10)
	ACCESS	read-write
	STATUS	mandatory
--	DEFVAL	4
	DESCRIPTION	"Sets the frame relay access link error threshold." 
	::= { frameRelayLinkCfgEntry 6}

frameRelayLinkCfgEventCount OBJECT-TYPE
	SYNTAX	INTEGER (1..10)
	ACCESS	read-write
	STATUS	mandatory
--	DEFVAL	4
	DESCRIPTION	"Sets the frame relay access link monitored events count." 
	::= { frameRelayLinkCfgEntry 7}

frameRelayLinkCfgLinkIntegrityVerificationTimer OBJECT-TYPE
	SYNTAX	INTEGER (5..30)
	ACCESS	read-write
	STATUS	mandatory
--	DEFVAL	10
	DESCRIPTION	"Sets the frame relay access link integrity verification
			timer." 
	::= { frameRelayLinkCfgEntry 8}

frameRelayLinkCfgPollingVerificationTimer OBJECT-TYPE
	SYNTAX	INTEGER (5..30)
	ACCESS	read-write
	STATUS	mandatory
--	DEFVAL	15
	DESCRIPTION	"Sets the frame relay access link polling verification
			timer." 
	::= { frameRelayLinkCfgEntry 9}

frameRelayLinkCfgMaxFrameSize OBJECT-TYPE
	SYNTAX	INTEGER (5..8189)
	ACCESS	read-write
	STATUS	mandatory
--	DEFVAL	4096
	DESCRIPTION	"Sets the maximum frame relay access link frame size. 
			The numbers are in octets." 
	::= { frameRelayLinkCfgEntry 10}

frameRelayLinkCfgRxClockingSource OBJECT-TYPE
	SYNTAX	INTEGER {
		external (1),
		internal (2)
		}
	ACCESS	read-write
	STATUS	mandatory
--	DEFVAL	1
	DESCRIPTION	"Sets the port clocking configuration for receiving 
			data over the frame relay access link." 
	::= { frameRelayLinkCfgEntry 11}

frameRelayLinkCfgTxClockingSource OBJECT-TYPE
	SYNTAX	INTEGER {
		external (1),
		internal (2)
		}
	ACCESS	read-write
	STATUS	mandatory
--	DEFVAL	1
	DESCRIPTION	"Sets the port clocking configuration for transmitting
			data over the frame relay access link." 
	::= { frameRelayLinkCfgEntry 12}

frameRelayLinkCfgNetworkAddress OBJECT-TYPE
	SYNTAX	OCTET STRING (SIZE (0..16))
	ACCESS	read-write
	STATUS	mandatory
--	DEFVAL	1
	DESCRIPTION	"Sets the network address for the frame relay access link. 
			This address is assigned by the carrier provider based on 
			a standardized numbering scheme." 
	::= { frameRelayLinkCfgEntry 13}

frameRelayLinkCfgAccessLinkMode OBJECT-TYPE
	SYNTAX	INTEGER {
		userEquipmentMode (1),
		networkMode (2)
		}
	ACCESS	read-write
	STATUS	mandatory
--	DEFVAL	1
	DESCRIPTION	"Sets the access mode for the frame relay access link." 
	::= { frameRelayLinkCfgEntry 14}

-- N_CMOS.O_DLCI ======================================================

frameRelayLinkCfgDLCITable OBJECT-TYPE
	SYNTAX	SEQUENCE OF FrameRelayLinkCfgDLCIEntry
	ACCESS	not-accessible
	STATUS	mandatory
	DESCRIPTION	"Table to configure the DLCI bandwidth charactistics for a 
			frame relay link." 
	::= {frame-relay-link 2}

frameRelayLinkCfgDLCIEntry OBJECT-TYPE
	SYNTAX	FrameRelayLinkCfgDLCIEntry
	ACCESS	not-accessible
	STATUS	mandatory
	DESCRIPTION	"Entry within the table to specify a DLCI number, the FR link/port
			number, and the module/card number for setting DLCI bandwidth
			characteristics." 
	INDEX		{ frameRelayLinkCfgDLCICardNumber, frameRelayLinkCfgDLCIChannelNumber,
			frameRelayLinkCfgDLCINumber }
	::= {frameRelayLinkCfgDLCITable 1}

FrameRelayLinkCfgDLCIEntry ::= SEQUENCE {
	frameRelayLinkCfgDLCICardNumber			INTEGER,
	frameRelayLinkCfgDLCIChannelNumber			INTEGER,
	frameRelayLinkCfgDLCINumber				INTEGER,
	frameRelayLinkCfgDLCIType				INTEGER,	
	frameRelayLinkCfgDLCICommittedInfoRateForward 	INTEGER,
	frameRelayLinkCfgDLCICommittedInfoRateBackward 	INTEGER,
	frameRelayLinkCfgDLCICommittedBurstSizeForward	INTEGER,
	frameRelayLinkCfgDLCICommittedBurstSizeBackward 	INTEGER,
	frameRelayLinkCfgDLCIExcessBurstSizeForward 		INTEGER,
	frameRelayLinkCfgDLCIExcessBurstSizeBackward 		INTEGER
	}

frameRelayLinkCfgDLCICardNumber OBJECT-TYPE
	SYNTAX	INTEGER
	ACCESS	read-only
	STATUS	mandatory
	DESCRIPTION	"Identifies the module/card number for a particular DLCI
			of a specific FR link for setting DLCI bandwidth characteristics." 
	::= {frameRelayLinkCfgDLCIEntry 1}

frameRelayLinkCfgDLCIChannelNumber OBJECT-TYPE
	SYNTAX	INTEGER
	ACCESS	read-only
	STATUS	mandatory
	DESCRIPTION	"Identifies the FR link/port number of a particular DLCI channel
			for setting the bandwidth characteristics." 
	::= {frameRelayLinkCfgDLCIEntry 2}

frameRelayLinkCfgDLCINumber OBJECT-TYPE
	SYNTAX	INTEGER
	ACCESS	read-only
	STATUS	mandatory
	DESCRIPTION	"Identifies a particular DLCI number for setting the bandwidth 
			characteristics." 
	::= {frameRelayLinkCfgDLCIEntry 3}

frameRelayLinkCfgDLCIType OBJECT-TYPE
	SYNTAX	INTEGER {
		undefined (1),
		annexDType (2),
		virtualLink (3),
		lmi (4),
		transparent (5),
		fragmentation (6)
		}
	ACCESS	read-only
	STATUS	mandatory
	DESCRIPTION	"Identifies the DLCI type configuration.  Note that only 
			Options (3), (5), and (6) are expected." 
	::= {frameRelayLinkCfgDLCIEntry 4}

frameRelayLinkCfgDLCICommittedInfoRateForward OBJECT-TYPE
	SYNTAX	INTEGER (0..9999999)
	ACCESS	read-write
	STATUS	mandatory
	DESCRIPTION	"Sets the value for committed information rate forward. 
			This value is available from your frame relay service provider." 
	::= {frameRelayLinkCfgDLCIEntry 5}

frameRelayLinkCfgDLCICommittedInfoRateBackward OBJECT-TYPE
	SYNTAX	INTEGER (0..9999999)
	ACCESS	read-write
	STATUS	mandatory
	DESCRIPTION	"Sets the value for committed information rate backward. 
			This value is available from your frame relay service provider." 
	::= {frameRelayLinkCfgDLCIEntry 6}

frameRelayLinkCfgDLCICommittedBurstSizeForward OBJECT-TYPE
	SYNTAX	INTEGER (0..9999999)
	ACCESS	read-write
	STATUS	mandatory
	DESCRIPTION	"Sets the value for committed burst size backward. 
			This value is available from your frame relay service provider." 
	::= {frameRelayLinkCfgDLCIEntry 7}

frameRelayLinkCfgDLCICommittedBurstSizeBackward OBJECT-TYPE
	SYNTAX	INTEGER (0..9999999)
	ACCESS	read-write
	STATUS	mandatory
	DESCRIPTION	"Sets the value for committed burst size forward. 
			This value is available from your frame relay service provider." 
	::= {frameRelayLinkCfgDLCIEntry 8}

frameRelayLinkCfgDLCIExcessBurstSizeForward OBJECT-TYPE
	SYNTAX	INTEGER (0..9999999)
	ACCESS	read-write
	STATUS	mandatory
	DESCRIPTION	"Sets the value for excess burst size backward. 
			This value is available from your frame relay service provider.
			Note: should be equal to the FR access data rate minus the 
			CIR backward." 
	::= {frameRelayLinkCfgDLCIEntry 9}

frameRelayLinkCfgDLCIExcessBurstSizeBackward OBJECT-TYPE
	SYNTAX	INTEGER (0..9999999)
	ACCESS	read-write
	STATUS	mandatory
	DESCRIPTION	"Sets the value for excess burst size forward. 
			This value is available from your frame relay service provider.
			Note: should be equal to the FR access data rate minus the 
			CIR forward." 
	::= {frameRelayLinkCfgDLCIEntry 10}


-- N_CMOS.O_FRCNTL  =====================================================

frameRelayLinkControlTable OBJECT-TYPE
	SYNTAX	SEQUENCE OF FrameRelayLinkControlEntry
	ACCESS	not-accessible
	STATUS	mandatory
	DESCRIPTION	"Table to add or delete DLCI channels for a FR link." 
	::= {frame-relay-link 3}

frameRelayLinkControlEntry OBJECT-TYPE
	SYNTAX	FrameRelayLinkControlEntry
	ACCESS	not-accessible
	STATUS	mandatory
	DESCRIPTION	"Entry within the table to specify a particular DLCI number
			for addition/deletion to a particular FR access link on a
			specific module/card." 
	INDEX		{frameRelayLinkControlLinkCardNumber, 
			frameRelayLinkControlLinkChannelNumber,
			frameRelayLinkControlDLCINumber}
	::= {frameRelayLinkControlTable 1}

FrameRelayLinkControlEntry ::= SEQUENCE {
	frameRelayLinkControlLinkCardNumber		INTEGER,
	frameRelayLinkControlLinkChannelNumber	INTEGER,
	frameRelayLinkControlDLCINumber		INTEGER,
	frameRelayLinkControlCommand			INTEGER,
	frameRelayLinkControlDLCIType 			INTEGER
	}

frameRelayLinkControlLinkCardNumber OBJECT-TYPE
	SYNTAX	INTEGER
	ACCESS	read-only
	STATUS	mandatory
	DESCRIPTION	"Identifies the module/card number of a FR access link for
			adding/deleting a DLCI channel." 
	 ::= {frameRelayLinkControlEntry 1}

frameRelayLinkControlLinkChannelNumber OBJECT-TYPE
	SYNTAX	INTEGER
	ACCESS	read-only
	STATUS	mandatory
	DESCRIPTION	"Identifies a FR access link/port number for adding/deleting
			a DLCI channel." 
	 ::= {frameRelayLinkControlEntry 2}

frameRelayLinkControlDLCINumber OBJECT-TYPE
	SYNTAX	INTEGER (16..991)
	ACCESS	write-only
	STATUS	mandatory
	DESCRIPTION	"Sets the DLCI channel number to be added or deleted." 
	 ::= {frameRelayLinkControlEntry 3}

frameRelayLinkControlCommand OBJECT-TYPE
	SYNTAX	INTEGER {
		addDLCI (1),
		deleteDLCI (2)
		}
	ACCESS	write-only
	STATUS	mandatory
	DESCRIPTION	"Command to select whether the DLCI number specified in
			frameRelayLinkControlDLCINumber is to be added or deleted.
			This command sould be sent ater the DLCI type has been sent." 
	 ::= {frameRelayLinkControlEntry 4}

frameRelayLinkControlDLCIType OBJECT-TYPE
	SYNTAX	INTEGER {
		virtualLink (1),
		transparent (2),
		fragmentation (3)
		}
	ACCESS	write-only
	STATUS	mandatory
	DESCRIPTION	"Sets the type of DLCI channel that is being added.
			This object should be set before the previous command
			object is set." 
	 ::= {frameRelayLinkControlEntry 5}



-- N_CMOS.O_DLCNTL  =====================================================

frameRelayDLCIControlTable OBJECT-TYPE
	SYNTAX	SEQUENCE OF FrameRelayDLCIControlEntry
	ACCESS	not-accessible
	STATUS	mandatory
	DESCRIPTION	"Table to configure force connections from one DLCI channel
			on a FR access link to another FR access link DLCI channel.
			Note: This will connect 2 FR access links together on a single
			Integration unit which acts like a FR switch." 
	::= {frame-relay-link 4}

frameRelayDLCIControlEntry OBJECT-TYPE
	SYNTAX	FrameRelayDLCIControlEntry
	ACCESS	not-accessible
	STATUS	mandatory
	DESCRIPTION	"Entry within the table specifying a particular DLCI channel,
			a FR access link/port number, and module/card number for a 
			force connection configuration." 
	INDEX		{frameRelayDLCIControlLinkCardNumber, 
			frameRelayDLCIControlLinkChannelNumber,
			frameRelayDLCIControlDLCINumber}
	::= {frameRelayDLCIControlTable 1}

FrameRelayDLCIControlEntry ::= SEQUENCE {
	frameRelayDLCIControlLinkCardNumber		INTEGER,
	frameRelayDLCIControlLinkChannelNumber	INTEGER,
	frameRelayDLCIControlDLCINumber		INTEGER,
	frameRelayDLCIControlCommand			INTEGER,
	frameRelayDLCIControlFconnNodeName 		DisplayString,
	frameRelayDLCIControlFconnCardNumber		INTEGER,
	frameRelayDLCIControlFconnChannelNumber	INTEGER,
	frameRelayDLCIControlFconnDLCINumber	INTEGER
	}

frameRelayDLCIControlLinkCardNumber OBJECT-TYPE
	SYNTAX	INTEGER
	ACCESS	read-only
	STATUS	mandatory
	DESCRIPTION	"Identifies the module/card number of the source FR access link
			for force connection configuration." 
	 ::= {frameRelayDLCIControlEntry 1}

frameRelayDLCIControlLinkChannelNumber OBJECT-TYPE
	SYNTAX	INTEGER
	ACCESS	read-only
	STATUS	mandatory
	DESCRIPTION	"Identifies the port/channel number of the source FR access link
			for force connection configuration." 
	 ::= {frameRelayDLCIControlEntry 2}

frameRelayDLCIControlDLCINumber OBJECT-TYPE
	SYNTAX	INTEGER (16..991)
	ACCESS	write-only
	STATUS	mandatory
	DESCRIPTION	"Identifies the DLCI channel number of the source FR access link
			for force connection configuration." 
	 ::= {frameRelayDLCIControlEntry 3}

frameRelayDLCIControlCommand OBJECT-TYPE
	SYNTAX	INTEGER {
		connectDLCI (1),
		disconnectDLCI (2)
		}
	ACCESS	write-only
	STATUS	mandatory
	DESCRIPTION	"Selects the force connection configuration between 2 FR access
			links on a single Integration unit." 
	 ::= {frameRelayDLCIControlEntry 4}

frameRelayDLCIControlFconnNodeName OBJECT-TYPE
	SYNTAX	DisplayString (SIZE(1..8))
	ACCESS	write-only
	STATUS	mandatory
	DESCRIPTION	"Selects the name of the Integration unit for the FR link force 
			connection configuration." 
	 ::= {frameRelayDLCIControlEntry 5}

frameRelayDLCIControlFconnCardNumber OBJECT-TYPE
	SYNTAX	INTEGER
	ACCESS	write-only
	STATUS	mandatory
	DESCRIPTION	"Selects the module/card number of the destination FR access link
			for force connection configuration." 
	 ::= {frameRelayDLCIControlEntry 6}

frameRelayDLCIControlFconnChannelNumber OBJECT-TYPE
	SYNTAX	INTEGER
	ACCESS	write-only
	STATUS	mandatory
	DESCRIPTION	"Selects the port/channel number of the destination FR access link
			for force connection configuration." 
	 ::= {frameRelayDLCIControlEntry 7}

frameRelayDLCIControlFconnDLCINumber OBJECT-TYPE
	SYNTAX	INTEGER
	ACCESS	write-only
	STATUS	mandatory
	DESCRIPTION	"Selects the DLCI channel number of the destination FR access link
			for force connection configuration." 
	 ::= {frameRelayDLCIControlEntry 8}

-- N_CMOS.O_FRCONS  =====================================================

frameRelayDLCIConnectsTable OBJECT-TYPE
	SYNTAX	SEQUENCE OF FrameRelayDLCIConnectsEntry
	ACCESS	not-accessible
	STATUS	mandatory
	DESCRIPTION	"Table to view DLCI connections between FR access links." 
	::= {frame-relay-link 5}

frameRelayDLCIConnectsEntry OBJECT-TYPE
	SYNTAX	FrameRelayDLCIConnectsEntry
	ACCESS	not-accessible
	STATUS	mandatory
	DESCRIPTION	"Entry within the table specific to the FR access link 
			module/card number, the port/channel number, and DLCI
			channel number for viewing DLCI connections." 
	INDEX		{frameRelayDLCIConnectsLinkCardNumber, 
			frameRelayDLCIConnectsLinkChannelNumber,
			frameRelayDLCIConnectsDLCIConnected}
	::= {frameRelayDLCIConnectsTable 1}

FrameRelayDLCIConnectsEntry ::= SEQUENCE {
	frameRelayDLCIConnectsLinkCardNumber		INTEGER,
	frameRelayDLCIConnectsLinkChannelNumber	INTEGER,
	frameRelayDLCIConnectsDLCIConnected 		INTEGER,
	frameRelayDLCIConnectsDestCardNumber		INTEGER,
	frameRelayDLCIConnectsDestChannelNumber	INTEGER,
	frameRelayDLCIConnectsDestDLCINumber	INTEGER
	}

frameRelayDLCIConnectsLinkCardNumber OBJECT-TYPE
	SYNTAX	INTEGER
	ACCESS	read-only
	STATUS	mandatory
	DESCRIPTION	"Identifies the module/card number of the source FR access link
			to view connection configurations." 
	 ::= {frameRelayDLCIConnectsEntry 1}

frameRelayDLCIConnectsLinkChannelNumber OBJECT-TYPE
	SYNTAX	INTEGER
	ACCESS	read-only
	STATUS	mandatory
	DESCRIPTION	"Identifies the port/channel number of the source FR access link
			to view connection configurations." 
	 ::= {frameRelayDLCIConnectsEntry 2}

frameRelayDLCIConnectsDLCIConnected OBJECT-TYPE
	SYNTAX	INTEGER
	ACCESS	read-only
	STATUS	mandatory
	DESCRIPTION	"Identifies the DLCI channel number of the source FR access link
			to view connection configurations." 
	 ::= {frameRelayDLCIConnectsEntry 3}

frameRelayDLCIConnectsDestCardNumber OBJECT-TYPE
	SYNTAX	INTEGER
	ACCESS	read-only
	STATUS	mandatory
	DESCRIPTION	"Identifies the module/card number of the destination FR access link
			to view connection configurations." 
	 ::= {frameRelayDLCIConnectsEntry 4}

frameRelayDLCIConnectsDestChannelNumber OBJECT-TYPE
	SYNTAX	INTEGER
	ACCESS	read-only
	STATUS	mandatory
	DESCRIPTION	"Identifies the port/channel number of the destination FR access link
			to view connection configurations." 
	 ::= {frameRelayDLCIConnectsEntry 5}

frameRelayDLCIConnectsDestDLCINumber OBJECT-TYPE
	SYNTAX	INTEGER
	ACCESS	read-only
	STATUS	mandatory
	DESCRIPTION	"Identifies the DLCI channel number of the destination FR access link
			to view connection configurations." 
	 ::= {frameRelayDLCIConnectsEntry 6}


-- Interface group

-- N_CMOS.O_NETID ======================================================

t1DS1InterfaceTable OBJECT-TYPE
	SYNTAX	SEQUENCE OF T1DS1InterfaceEntry
	ACCESS	not-accessible
	STATUS	mandatory
	DESCRIPTION	"Table for Network T1 Interface for long-haul connection to the
			telephone network." 
	::= {t1-interface 1}

t1DS1InterfaceEntry OBJECT-TYPE
	SYNTAX	T1DS1InterfaceEntry
	ACCESS	not-accessible
	STATUS	mandatory
	DESCRIPTION	"Entry within the table for specified (Network Interface) DSO 
			(1..24) channels." 
	INDEX		{ t1DS1InterfaceDS0Index}
	::= {t1DS1InterfaceTable 1}

T1DS1InterfaceEntry ::= SEQUENCE {
	t1DS1InterfaceDS0Index			INTEGER,
	t1DS1InterfaceConnectionState		INTEGER
	}

t1DS1InterfaceDS0Index OBJECT-TYPE
	SYNTAX	INTEGER (1..24)
	ACCESS	read-only
	STATUS	mandatory
	DESCRIPTION	"Indicates an instance into the table for a particular (1..24)
			DSO channel." 
	::= { t1DS1InterfaceEntry 1}

t1DS1InterfaceConnectionState OBJECT-TYPE
	SYNTAX	INTEGER {
		idle (1),
		bypassVoice (2),
		bypassData (3),
		toCCMLinkA1 (4),
		toCCMLinkA2 (5),
		toCCMLinkA3 (6),
		toCCMLinkA4 (7),
		toCCMLinkA5 (8),
		toCCMLinkA6 (9),
		toDataPort1 (10),
		toDataPort2 (11),
		toVChOnT1DVM1 (12),
		toVChOnT1DVM2 (13),
		toVChOnT1DVM3 (14),
		toVChOnT1DVM4 (15),
		toVChOnT1DVM5 (16),
		toVChOnT1DVM6 (17),
		toVChOnSlotCDVM1 (18),		
		toVChOnSlotCDVM2 (19),
		toVChOnSlotCDVM3 (20),
		toVChOnSlotCDVM4 (21),
		toVChOnSlotCDVM5 (22),
		toVChOnSlotCDVM6 (23),
		toVChOnSlotCDVM7 (24),
		toVChOnSlotCDVM8 (25),
		toVChOnSlotCDVM9 (26),
		toVChOnSlotCDVM10 (27),
		toVChOnSlotCDVM11 (28),
		toVChOnSlotCDVM12 (29),
		toVChOnSlotDDVM1 (30),		
		toVChOnSlotDDVM2 (31),
		toVChOnSlotDDVM3 (32),
		toVChOnSlotDDVM4 (33),
		toVChOnSlotDDVM5 (34),
		toVChOnSlotDDVM6 (35),
		toVChOnSlotDDVM7 (36),
		toVChOnSlotDDVM8 (37),
		toVChOnSlotDDVM9 (38),
		toVChOnSlotDDVM10 (39),
		toVChOnSlotDDVM11 (40),
		toVChOnSlotDDVM12 (41)
		}
	ACCESS	read-write
	STATUS	mandatory
	DESCRIPTION	"Defines the connection state of the specified DSO channel. This 
			defines the ability for data passed directly between the Local 
			and Network Interfaces, or for being dropped and inserted to/from
			the Integration unit resources (CCM links, Data Ports, Voice 
			Channels)." 
	::= { t1DS1InterfaceEntry 2}


-- N_CMOS.O_PBXID ======================================================

t1DSX1InterfaceTable OBJECT-TYPE
	SYNTAX	SEQUENCE OF T1DSX1InterfaceEntry
	ACCESS	not-accessible
	STATUS	mandatory
	DESCRIPTION	"Table for Local T1 Interface for connection to local digital pbx." 
	::= {t1-interface 2}

t1DSX1InterfaceEntry OBJECT-TYPE
	SYNTAX	T1DSX1InterfaceEntry
	ACCESS	not-accessible
	STATUS	mandatory
	DESCRIPTION	"Entry within the table for specified (local interface) DSO (1..24) 
			channels." 
	INDEX		{ t1DSX1InterfaceDS0Index}
	::= {t1DSX1InterfaceTable 1}

T1DSX1InterfaceEntry ::= SEQUENCE {
	t1DSX1InterfaceDS0Index		INTEGER,
	t1DSX1InterfaceConnectionState		INTEGER
	}

t1DSX1InterfaceDS0Index OBJECT-TYPE
	SYNTAX	INTEGER (1..24)
	ACCESS	read-only
	STATUS	mandatory
	DESCRIPTION	"Indicates an instance into the table for a particular (1..24) 
			DSO channel for local t1 interfaces." 
	::= { t1DSX1InterfaceEntry 1}

t1DSX1InterfaceConnectionState OBJECT-TYPE
	SYNTAX	INTEGER {
		idle (1),
		bypassVoice (2),
		bypassData (3),
		toCCMLinkA1 (4),
		toCCMLinkA2 (5),
		toCCMLinkA3 (6),
		toCCMLinkA4 (7),
		toCCMLinkA5 (8),
		toCCMLinkA6 (9),
		toDataPort1 (10),
		toDataPort2 (11),
		toVChOnT1DVM1 (12),
		toVChOnT1DVM2 (13),
		toVChOnT1DVM3 (14),
		toVChOnT1DVM4 (15),
		toVChOnT1DVM5 (16),
		toVChOnT1DVM6 (17),
		toVChOnSlotCDVM1 (18),		
		toVChOnSlotCDVM2 (19),
		toVChOnSlotCDVM3 (20),
		toVChOnSlotCDVM4 (21),
		toVChOnSlotCDVM5 (22),
		toVChOnSlotCDVM6 (23),
		toVChOnSlotCDVM7 (24),
		toVChOnSlotCDVM8 (25),
		toVChOnSlotCDVM9 (26),
		toVChOnSlotCDVM10 (27),
		toVChOnSlotCDVM11 (28),
		toVChOnSlotCDVM12 (29),
		toVChOnSlotDDVM1 (30),		
		toVChOnSlotDDVM2 (31),
		toVChOnSlotDDVM3 (32),
		toVChOnSlotDDVM4 (33),
		toVChOnSlotDDVM5 (34),
		toVChOnSlotDDVM6 (35),
		toVChOnSlotDDVM7 (36),
		toVChOnSlotDDVM8 (37),
		toVChOnSlotDDVM9 (38),
		toVChOnSlotDDVM10 (39),
		toVChOnSlotDDVM11 (40),
		toVChOnSlotDDVM12 (41)
		}
	ACCESS	read-write
	STATUS	mandatory
	DESCRIPTION	"For local t1 interfaces, this parameter defines the connection 
			state of the specified DSO channel. This defines the ability for 
			data passed directly between the Local and Network Interfaces, 
			or for being dropped and inserted to/from the Integration unit 
			resources (CCM links, Data Ports, Voice Channels)."
	::= { t1DSX1InterfaceEntry 2}

-- N_CMOS.O_SYSID ======================================================

t1CfgGroup    OBJECT IDENTIFIER ::= {t1-interface 3}

t1CfgDSX1FrameFormat OBJECT-TYPE
	SYNTAX	INTEGER {
		superFrame (1),
		extendedSuperFrame (2)
		}
	ACCESS	read-write
	STATUS	mandatory
	DESCRIPTION	"Configures the local T1 interface frame formats to either (SF)
			super frame or (ESF) extended super frame." 
--	DEFVAL	1
	::= {t1CfgGroup 1}

t1CfgDSX1LineCode OBJECT-TYPE
	SYNTAX	INTEGER {
		ami (1),
		b8zs (2)
		}
	ACCESS	read-write
	STATUS	mandatory
	DESCRIPTION	"Configures the line coding method (at the Local interface) either
			to Alternate Mark Inversion (AMI) coding or Bipolar Eight Zero 
			Suppression (B8ZS). In AMI 0's are indicated by the absence of a 
			pulse, and 1's are indicated by either a positive or negative polarity 
			pulse. In B8ZS an all 0 byte is replaced by a special code of 00011011 
			which indicate two fixed bipolar code violations. On remote end these 
			violations are ignored and the data is retrieved." 
--	DEFVAL	1
	::= {t1CfgGroup 2}

t1CfgDSX1IdleCode OBJECT-TYPE
	SYNTAX	OCTET STRING (SIZE(1))
	ACCESS	read-write
	STATUS	mandatory
	DESCRIPTION	"Configures the idle code character at the local T1 interface." 
--	DEFVAL	07F
	::= {t1CfgGroup 3}

t1CfgDSX1lineBuildout OBJECT-TYPE
	SYNTAX	INTEGER {
		lessThan110Feet (1),
		lessThan220Feet (2),
		lessThan330Feet (3),
		lessThan440Feet (4),
		externalLBO (5),
		greaterThan665Feet (6),
		lessThan550Feet (7),
		lessThan660Feet (8)
		}
	ACCESS	read-write
	STATUS	mandatory
	DESCRIPTION	"Configures a transmitter attenuation parameter based on various 
			cable lengths, reflecting the distance from the T1 Access Module 
			to the T1 service provider." 
-- 	DEFVAL	1
	::= {t1CfgGroup 4}

t1CfgDSX1NetworkInvokedLoopback OBJECT-TYPE
	SYNTAX	INTEGER {
		enable (1),
		disable (2)
		}
	ACCESS	read-write
	STATUS	mandatory
	DESCRIPTION	"Enables/Disables the DSX1 Network-invoked loopback on the T1 
			module." 
--	DEFVAL	1
	::= {t1CfgGroup 5}

t1CfgDS1FrameFormat OBJECT-TYPE
	SYNTAX	INTEGER {
		superFrame (1),
		extendedSuperFrame (2)
		}
	ACCESS	read-write
	STATUS	mandatory
	DESCRIPTION	"Configures the network T1 interface frame formats to either (SF)
			super frame or (ESF) extended super frame." 
--	DEFVAL	1
	::= {t1CfgGroup 6}

t1CfgDS1LineCode OBJECT-TYPE
	SYNTAX	INTEGER {
		ami (1),
		b8zs (2)
		}
	ACCESS	read-write
	STATUS	mandatory
	DESCRIPTION	"Configures the line coding method (at the Network interface) either
			to Alternate Mark Inversion (AMI) coding or Bipolar Eight Zero 
			Suppression (B8ZS). In AMI 0's are indicated by the absence of a 
			pulse, and 1's are indicated by either a positive or negative polarity 
			pulse. In B8ZS an all 0 byte is replaced by a special code of 00011011 
			which indicate two fixed bipolar code violations. On remote end these 
			violations are ignored and the data is retrieved."  
--	DEFVAL	1
	::= {t1CfgGroup 7}

t1CfgDS1IdleCode OBJECT-TYPE
	SYNTAX	OCTET STRING (SIZE(1))
	ACCESS	read-write
	STATUS	mandatory
	DESCRIPTION	"Configures the idle code character at the network T1 interface." 
--	DEFVAL	07F
	::= {t1CfgGroup 8}

t1CfgDS1NetworkInvokedLoopback OBJECT-TYPE
	SYNTAX	INTEGER {
		enable (1),
		disable (2)
		}
	ACCESS	read-write
	STATUS	mandatory
	DESCRIPTION	"Enables/Disables the DS1 Network-invoked loopback on the T1 
			module." 
	::= {t1CfgGroup 9}

t1CfgDataPort1Rate OBJECT-TYPE
	SYNTAX	INTEGER {
		multipleOf64kbps (1),
		multipleOf56kbps (2)
		}
	ACCESS	read-write
	STATUS	mandatory
	DESCRIPTION	"Sets the base rate of Data Port channel 1 on the T1 module.  
			The actual rate will be determined by the following formula:
			rate of the data port = (base rate)*(number of DS0 channels)." 
--	DEFVAL	1
	::= {t1CfgGroup 10}

t1CfgDataPort1Timing OBJECT-TYPE
	SYNTAX	INTEGER {
		internallySuppliedNormal (1),
		tailCircuit (2)
		}
	ACCESS	read-write
	STATUS	mandatory
	DESCRIPTION	"Sets how the clocking will be supplied for Data Port 1 on the
			T1 module." 
--	DEFVAL	1
	::= {t1CfgGroup 11}

t1CfgDataPort1DTRControl OBJECT-TYPE
	SYNTAX	INTEGER {
		dtrNormal (1),
		dtrForced (2)
		}
	ACCESS	read-write
	STATUS	mandatory
	DESCRIPTION	"Sets the DTR control for Data Port 1 on the T1 module.  Option (1),
			dtrNormal, will configure DTR control from the DTE equipment.  
			Option (2), dtrForced, will force DTR to a '1'." 
--	DEFVAL	1
	::= {t1CfgGroup 12}

t1CfgDataPort1RTSControl OBJECT-TYPE
	SYNTAX	INTEGER {
		rtsNormal (1),
		rtsForced (2)
		}
	ACCESS	read-write
	STATUS	mandatory
	DESCRIPTION	"Sets the RTS control for Data Port 1 on the T1 module.  Option (1),
			rtsNormal, will configure RTS control from the DTE equipment.  
			Option (2), rtsForced, will force RTS to a '1'." 
--	DEFVAL	1
	::= {t1CfgGroup 13}

t1CfgDataPort2Rate OBJECT-TYPE
	SYNTAX	INTEGER {
		multipleOf64kbps (1),
		multipleOf56kbps (2)
		}
	ACCESS	read-write
	STATUS	mandatory
	DESCRIPTION	"Sets the base rate of Data Port channel 2 on the T1 module.
			The actual rate will be determined by the following formula:
			rate of the data port = (base rate)*(number of DS0 channels)." 
--	DEFVAL	1
	::= {t1CfgGroup 14}

t1CfgDataPort2Timing OBJECT-TYPE
	SYNTAX	INTEGER {
		internallySupplied (1),
		tailCircuit (2)
		}
	ACCESS	read-write
	STATUS	mandatory
	DESCRIPTION	"Sets how the clocking will be supplied for Data Port 2 on the
			T1 module." 
--	DEFVAL	1
	::= {t1CfgGroup 15}

t1CfgDataPort2DTRControl OBJECT-TYPE
	SYNTAX	INTEGER {
		dtr (1),
		dtrForcedOn (2)
		}
	ACCESS	read-write
	STATUS	mandatory
	DESCRIPTION	"Sets the DTR control for Data Port 2 on the T1 module.  Option (1),
			dtr, will configure DTR control from the DTE equipment.  
			Option (2), dtrForcedOn, will force DTR to a '1'." 
--		DEFVAL	1
	::= {t1CfgGroup 16}

t1CfgDataPort2RTSControl OBJECT-TYPE
	SYNTAX	INTEGER {
		rts (1),
		rtsForcedOn (2)
		}
	ACCESS	read-write
	STATUS	mandatory
	DESCRIPTION	"Sets the RTS control for Data Port 2 on the T1 module.  Option (1),
			rts, will configure RTS control from the DTE equipment.  
			Option (2), rtsForcedOn, will force RTS to a '1'." 
--	DEFVAL	1
	::= {t1CfgGroup 17}

t1CfgCCMLinkA1Rate OBJECT-TYPE
	SYNTAX	INTEGER {
		multipleOf64kbps (1),
		multipleOf56kbps (2)
		}
	ACCESS	read-write
	STATUS	mandatory
	DESCRIPTION	"Sets the base rate of the CCM A1 channel for a T1 interface. 
			The actual rate will be determined by the following formula:
			rate of the CCM port = (base rate)*(number of DS0 channels)." 
--	DEFVAL	1
	::= {t1CfgGroup 18}

t1CfgCCMLinkA2Rate OBJECT-TYPE
	SYNTAX	INTEGER {
		multipleOf64kbps (1),
		multipleOf56kbps (2)
		}
	ACCESS	read-write
	STATUS	mandatory
	DESCRIPTION	"Sets the base rate of the CCM A2 channel for a T1 interface. 
			The actual rate will be determined by the following formula:
			rate of the CCM port = (base rate)*(number of DS0 channels)." 
--	DEFVAL	1
	::= {t1CfgGroup 19}

t1CfgCCMLinkA3Rate OBJECT-TYPE
	SYNTAX	INTEGER {
		multipleOf64kbps (1),
		multipleOf56kbps (2)
		}
	ACCESS	read-write
	STATUS	mandatory
	DESCRIPTION	"Sets the base rate of the CCM A3 channel for a T1 interface. 
			The actual rate will be determined by the following formula:
			rate of the CCM port = (base rate)*(number of DS0 channels)." 
--		DEFVAL	1
	::= {t1CfgGroup 20}

t1CfgCCMLinkA4Rate OBJECT-TYPE
	SYNTAX	INTEGER {
		multipleOf64kbps (1),
		multipleOf56kbps (2)
		}
	ACCESS	read-write
	STATUS	mandatory
	DESCRIPTION	"Sets the base rate of the CCM A4 channel for a T1 interface. 
			The actual rate will be determined by the following formula:
			rate of the CCM port = (base rate)*(number of DS0 channels)." 
--		DEFVAL	1
	::= {t1CfgGroup 21}

t1CfgCCMLinkA5Rate OBJECT-TYPE
	SYNTAX	INTEGER {
		multipleOf64kbps (1),
		multipleOf56kbps (2)
		}
	ACCESS	read-write
	STATUS	mandatory
	DESCRIPTION	"Sets the base rate of the CCM A5 channel for a T1 interface. 
			The actual rate will be determined by the following formula:
			rate of the CCM port = (base rate)*(number of DS0 channels)." 
--		DEFVAL	1
	::= {t1CfgGroup 22}

t1CfgCCMLinkA6Rate OBJECT-TYPE
	SYNTAX	INTEGER {
		multipleOf64kbps (1),
		multipleOf56kbps (2)
		}
	ACCESS	read-write
	STATUS	mandatory
	DESCRIPTION	"Sets the base rate of the CCM A6 channel for a T1 interface. 
			The actual rate will be determined by the following formula:
			rate of the CCM port = (base rate)*(number of DS0 channels)." 
--		DEFVAL	1
	::= {t1CfgGroup 23}

t1CfgSystemClockSource OBJECT-TYPE
	SYNTAX	INTEGER {
		ds1ClockDerived (1),
		dsx1Clockderived (2),
		internalClocking (3)
		}
	ACCESS	read-write
	STATUS	mandatory
	DESCRIPTION	"Configures the source of the clock used in the T1 Access 
			Module. Options include:
			- DSX-1. The clock source is from the DSX-1 interface.
			- DS-1. The clock source is from the DS-1 interface.
			- Internal. The clock is derived from a clock source internal 
				to the T1 Access Module."
--	DEFVAL	1
	::= {t1CfgGroup 24}

t1CfgDS1Config OBJECT-TYPE
	SYNTAX INTEGER {
		init (1),
		commit (2)
		}
	ACCESS write-only
	STATUS mandatory
	DESCRIPTION 	"This object is a write only object that will signal the proxy to
		start caching changes to the DS1 ds0 connection tables.  This is done to
		solve an anomaly in the marathon/t1 design. The manager must set
		this object to init before updating any of the t1DS1InterfaceTable objects.
		When all the changes have been set then this object will have to be set to
		commit (2).  The init will cause the proxy to upload the table from the marathon
		and the commit will cause the proxy to send all the changes to the marathon."
	::= {t1CfgGroup 25}

t1CfgDSX1Config OBJECT-TYPE
	SYNTAX INTEGER {
		init (1),
		commit (2)
		}
	ACCESS write-only
	STATUS mandatory
	DESCRIPTION 	"This object is a write only object that will signal the proxy to
		start caching changes to the DSX1 ds0 connection tables.  This is done to
		solve an anomaly in the marathon/t1 design. The manager must set
		this object to init before updating any of the t1DSX1InterfaceTable objects.
		When all the changes have been set then this object will have to be set to
		commit (2).  The init will cause the proxy to upload the table from the marathon
		and the commit will cause the proxy to send all the changes to the marathon."
	::= {t1CfgGroup 26}

-- N_HOUSE.O_T1FLSH ===================================================

t1FlashControlTable OBJECT-TYPE
	SYNTAX	SEQUENCE OF T1FlashControlEntry
	ACCESS	not-accessible
	STATUS	mandatory
	DESCRIPTION	"Table to control (erase) T1 flash memory in preparation for a 
			code download." 
	::= { t1-interface 4}

t1FlashControlEntry OBJECT-TYPE
	SYNTAX	T1FlashControlEntry 
	ACCESS	not-accessible
	STATUS	mandatory
	DESCRIPTION	"Entry within the table specific to a particular T1 module/card
			number for flash memory control." 
	INDEX	 	{ t1FlashControlCardNumber }
	::= { t1FlashControlTable 1}

T1FlashControlEntry ::= SEQUENCE {
	t1FlashControlCardNumber		INTEGER,
	t1FlashControlCommand		INTEGER,
	t1FlashControlFlashStatus		INTEGER
	}

t1FlashControlCardNumber OBJECT-TYPE
	SYNTAX	INTEGER (2..5)
	ACCESS	read-only
	STATUS	mandatory
	DESCRIPTION	"Identifies the T1 module/card number for flash memory control." 
	::= { t1FlashControlEntry 1}

t1FlashControlCommand OBJECT-TYPE
	SYNTAX	INTEGER {
		eraseCardFlash (1)
		}
	ACCESS	write-only
	STATUS	mandatory
	DESCRIPTION	"Controls the T1 module flash memory in preparation of a code
			download.  Perform a SET with the value eraseCardFlash to erase
			the flash memory prior to downloading new T1 flash software." 
	::= { t1FlashControlEntry 2}

t1FlashControlFlashStatus OBJECT-TYPE
	SYNTAX	INTEGER {
		bootImageCorrupt (1),
		t1FlashImageValid (2),
		t1FlashErased (3),
		t1FlashImageInvalid (4),
		securityViolation (5),
		eraseAborted (6)
		}
	ACCESS	read-only
	STATUS	mandatory
	DESCRIPTION	"Identifies the status of the T1 module/card flash memory." 
	::= { t1FlashControlEntry 3}

-- N_CMOS.O_PBXID ======================================================

-- E1 Interface Group

e1L1InterfaceTable OBJECT-TYPE
	SYNTAX	SEQUENCE OF E1L1InterfaceEntry
	ACCESS	not-accessible
	STATUS	mandatory
	DESCRIPTION	"Table to configure the DS0 connections for the L1 interface
			of an E1 module/card." 
	::= {e1-interface 1}

e1L1InterfaceEntry OBJECT-TYPE
	SYNTAX	E1L1InterfaceEntry
	ACCESS	not-accessible
	STATUS	mandatory
	DESCRIPTION	"Entry within the table specific to a particular DS0 channel
			for the L1 interface of an E1 module/card." 
	INDEX		{ e1L1InterfaceDS0Index}
	::= {e1L1InterfaceTable 1}

E1L1InterfaceEntry ::= SEQUENCE {
	e1L1InterfaceDS0Index			INTEGER,
	e1L1InterfaceConnectionState		INTEGER
	}

e1L1InterfaceDS0Index OBJECT-TYPE
	SYNTAX	INTEGER (1..30)
	ACCESS	read-only
	STATUS	mandatory
	DESCRIPTION	"Identifies the DS0 channel of the E1 module for configuration
			of the L1 interface." 
	::= { e1L1InterfaceEntry 1}

e1L1InterfaceConnectionState OBJECT-TYPE
	SYNTAX	INTEGER {
		idle (1),
		bypass (2),
		toCCMLinkA1 (3),
		toCCMLinkA2 (4),
		toCCMLinkA3 (5),
		toCCMLinkA4 (6),
		toCCMLinkA5 (7),
		toCCMLinkA6 (8),
		toDataPort1 (9),
		toDataPort2 (10),
		toVChOnE1DVM1 (11),
		toVChOnE1DVM2 (12),
		toVChOnE1DVM3 (13),
		toVChOnE1DVM4 (14),
		toVChOnE1DVM5 (15),
		toVChOnE1DVM6 (16),
		toVChOnSlotCDVM1 (17),		
		toVChOnSlotCDVM2 (18),
		toVChOnSlotCDVM3 (19),
		toVChOnSlotCDVM4 (20),
		toVChOnSlotCDVM5 (21),
		toVChOnSlotCDVM6 (22),
		toVChOnSlotCDVM7 (23),
		toVChOnSlotCDVM8 (24),
		toVChOnSlotCDVM9 (25),
		toVChOnSlotCDVM10 (26),
		toVChOnSlotCDVM11 (27),
		toVChOnSlotCDVM12 (28),
		toVChOnSlotDDVM1 (29),		
		toVChOnSlotDDVM2 (30),
		toVChOnSlotDDVM3 (31),
		toVChOnSlotDDVM4 (32),
		toVChOnSlotDDVM5 (33),
		toVChOnSlotDDVM6 (34),
		toVChOnSlotDDVM7 (35),
		toVChOnSlotDDVM8 (36),
		toVChOnSlotDDVM9 (37),
		toVChOnSlotDDVM10 (38),
		toVChOnSlotDDVM11 (39),
		toVChOnSlotDDVM12 (40)
		}
	ACCESS	read-write
	STATUS	mandatory
	DESCRIPTION	"Select the DS0 connection for DS0 configuration of the L1 
			interface.  Available DS0 connections include Idle, Bypass, 
			CCM A1-A6, Data Port 1-2, Voice B1-B6 (on e1 card), Voice C1-C12, 
			and Voice D1-D12." 
	::= { e1L1InterfaceEntry 2}


-- N_CMOS.O_NETID ======================================================

e1L2InterfaceTable OBJECT-TYPE
	SYNTAX	SEQUENCE OF E1L2InterfaceEntry
	ACCESS	not-accessible
	STATUS	mandatory
	DESCRIPTION	"Table to configure the DS0 connections for the L2 interface
			of an E1 module/card." 
	::= {e1-interface 2}

e1L2InterfaceEntry OBJECT-TYPE
	SYNTAX	E1L2InterfaceEntry
	ACCESS	not-accessible
	STATUS	mandatory
	DESCRIPTION	"Entry within the table specific to a particular DS0 channel
			for the L2 interface of an E1 module/card." 
	INDEX		{ e1L2InterfaceDS0Index}
	::= {e1L2InterfaceTable 1}

E1L2InterfaceEntry ::= SEQUENCE {
	e1L2InterfaceDS0Index		INTEGER,
	e1L2InterfaceConnectionState	INTEGER
	}

e1L2InterfaceDS0Index OBJECT-TYPE
	SYNTAX	INTEGER (1..30)
	ACCESS	read-only
	STATUS	mandatory
	DESCRIPTION	"Identifies the DS0 channel of the E1 module for configuration
			of the L2 interface."
	::= { e1L2InterfaceEntry 1}

e1L2InterfaceConnectionState OBJECT-TYPE
	SYNTAX	INTEGER {
		idle (1),
		bypass (2),
		toCCMLinkA1 (3),
		toCCMLinkA2 (4),
		toCCMLinkA3 (5),
		toCCMLinkA4 (6),
		toCCMLinkA5 (7),
		toCCMLinkA6 (8),
		toDataPort1 (9),
		toDataPort2 (10),
		toVChOnE1DVM1 (11),
		toVChOnE1DVM2 (12),
		toVChOnE1DVM3 (13),
		toVChOnE1DVM4 (14),
		toVChOnE1DVM5 (15),
		toVChOnE1DVM6 (16),
		toVChOnSlotCDVM1 (17),		
		toVChOnSlotCDVM2 (18),
		toVChOnSlotCDVM3 (19),
		toVChOnSlotCDVM4 (20),
		toVChOnSlotCDVM5 (21),
		toVChOnSlotCDVM6 (22),
		toVChOnSlotCDVM7 (23),
		toVChOnSlotCDVM8 (24),
		toVChOnSlotCDVM9 (25),
		toVChOnSlotCDVM10 (26),
		toVChOnSlotCDVM11 (27),
		toVChOnSlotCDVM12 (28),
		toVChOnSlotDDVM1 (29),		
		toVChOnSlotDDVM2 (30),
		toVChOnSlotDDVM3 (31),
		toVChOnSlotDDVM4 (32),
		toVChOnSlotDDVM5 (33),
		toVChOnSlotDDVM6 (34),
		toVChOnSlotDDVM7 (35),
		toVChOnSlotDDVM8 (36),
		toVChOnSlotDDVM9 (37),
		toVChOnSlotDDVM10 (38),
		toVChOnSlotDDVM11 (39),
		toVChOnSlotDDVM12 (40)
		}
	ACCESS	read-write
	STATUS	mandatory
	DESCRIPTION	"Select the DS0 connection for DS0 configuration of the L2 
			interface.  Available DS0 connections include Idle, Bypass, 
			CCM A1-A6, Data Port 1-2, Voice B1-B6 (on e1 card), Voice C1-C12, 
			and Voice D1-D12." 
	::= { e1L2InterfaceEntry 2}

-- N_CMOS.O_SYSID ======================================================

e1CfgGroup    OBJECT IDENTIFIER ::= {e1-interface 3}

e1CfgL1LineCode OBJECT-TYPE
	SYNTAX	INTEGER {
		ami (1),
		hdb3 (2)
		}
	ACCESS	read-write
	STATUS	mandatory
	DESCRIPTION	"Configures the L1 interface line coding method of the E1  
			module/card either to Alternate Mark Inversion (AMI) coding or 
			High Density Bipolar 3 (HDB3).  AMI indicates that HDB3 zeros 
			suppression is not enabled.  To obtain zeros suppression (bit 
			stuffing method) with AMI, you must also set the base rate of 
			the CCM and Data ports to 56Kbps. Otherwise, zeros suppression 
			will be the responsibility of the Data Terminal Equipment.  
			HDB3 does not allow more than three consecutive zeros. HDB3 
			format can be enabled only when supported by the connecting 
			equipment or the E1 service provider." 
--	DEFVAL	2
	::= {e1CfgGroup 1}

e1CfgL1IdleCode OBJECT-TYPE
	SYNTAX	OCTET STRING (SIZE(1))
	ACCESS	read-write
	STATUS	mandatory
	DESCRIPTION	"Configures the idle code character of the L1 interface for
			E1 module/card." 
--	DEFVAL	055
	::= {e1CfgGroup 2}

e1CfgL1SignallingMode OBJECT-TYPE
	SYNTAX	INTEGER {
		cas (1),
		transparentIdle (2),
		transparentTS16ToA2 (3),
		transparentTS16ToA3 (4),
		transparentTS16ToA4 (5),
		transparentTS16ToA5 (6),
		transparentTS16ToA6 (7),
		transparentTS16ToDP1 (8),
		transparentTS16ToDP2 (9),
		casTS16Bypass (10),
		ccsTS16Bypass (11)
		}
	ACCESS	read-write
	STATUS	mandatory
	DESCRIPTION	"Configures the signalling mode of the L1 interface for
			E1 module/card." 
--	DEFVAL	1
	::= {e1CfgGroup 3}

e1CfgL2LineCode OBJECT-TYPE
	SYNTAX	INTEGER {
		ami (1),
		hdb3 (2)
		}
	ACCESS	read-write
	STATUS	mandatory
	DESCRIPTION	"Configures the L2 interface line coding method of the E1  
			module/card either to Alternate Mark Inversion (AMI) coding or 
			High Density Bipolar 3 (HDB3).  AMI indicates that HDB3 zeros 
			suppression is not enabled.  To obtain zeros suppression (bit 
			stuffing method) with AMI, you must also set the base rate of 
			the CCM and Data ports to 56Kbps. Otherwise, zeros suppression 
			will be the responsibility of the Data Terminal Equipment.  
			HDB3 does not allow more than three consecutive zeros. HDB3 
			format can be enabled only when supported by the connecting 
			equipment or the E1 service provider." 
--	DEFVAL	2
	::= {e1CfgGroup 4}

e1CfgL2IdleCode OBJECT-TYPE
	SYNTAX	OCTET STRING (SIZE(1))
	ACCESS	read-write
	STATUS	mandatory
	DESCRIPTION	"Configures the idle code character of the L2 interface for
			E1 module/card." 
--	DEFVAL	055
	::= {e1CfgGroup 5}

e1CfgL2SignallingMode OBJECT-TYPE
	SYNTAX	INTEGER {
		cas (1),
		transparentIdle (2),
		transparentTS16ToA2 (3),
		transparentTS16ToA3 (4),
		transparentTS16ToA4 (5),
		transparentTS16ToA5 (6),
		transparentTS16ToA6 (7),
		transparentTS16ToDP1 (8),
		transparentTS16ToDP2 (9),
		casTS16Bypass (10),
		ccsTS16Bypass (11)
		}
	ACCESS	read-write
	STATUS	mandatory
	DESCRIPTION	"Configures the signalling mode of the L2 interface for
			E1 module/card." 
	::= {e1CfgGroup 6}

e1CfgDataPort1BaseRate OBJECT-TYPE
	SYNTAX	INTEGER {
		multipleOf64kbps (1),
		multipleOf56kbps (2)
		}
	ACCESS	read-write
	STATUS	mandatory
	DESCRIPTION	"Sets the base rate of Data Port channel 1 on the E1 module.
			The actual rate will be determined by the following formula:
			rate of the data port = (base rate)*(number of DS0 channels)." 
--	DEFVAL	1
	::= {e1CfgGroup 7}

e1CfgDataPort1Timing OBJECT-TYPE
	SYNTAX	INTEGER {
		normal (1),
		tailCircuit (2)
		}
	ACCESS	read-write
	STATUS	mandatory
	DESCRIPTION	"Sets how the clocking will be supplied for Data Port 1 on the
			E1 module." 
--	DEFVAL	1
	::= {e1CfgGroup 8}

e1CfgDataPort1DTRControl OBJECT-TYPE
	SYNTAX	INTEGER {
		dtrNormal (1),
		dtrForced (2)
		}
	ACCESS	read-write
	STATUS	mandatory
	DESCRIPTION	"Sets the DTR control for Data Port 1 on the E1 module.  Option (1),
			dtrNormal, will configure DTR control from the DTE equipment.  
			Option (2), dtrForced, will force DTR to a '1'." 
--	DEFVAL	1
	::= {e1CfgGroup 9}

e1CfgDataPort1RTSControl OBJECT-TYPE
	SYNTAX	INTEGER {
		rtsNormal (1),
		rtsForced (2)
		}
	ACCESS	read-write
	STATUS	mandatory
	DESCRIPTION	"Sets the RTS control for Data Port 1 on the E1 module.  Option (1),
			rtsNormal, will configure RTS control from the DTE equipment.  
			Option (2), rtsForced, will force RTS to a '1'." 
--	DEFVAL	1
	::= {e1CfgGroup 10}

e1CfgDataPort2BaseRate OBJECT-TYPE
	SYNTAX	INTEGER {
		multipleOf64kbps (1),
		multipleOf56kbps (2)
		}
	ACCESS	read-write
	STATUS	mandatory
	DESCRIPTION	"Sets the base rate of Data Port channel 2 on the E1 module.
			The actual rate will be determined by the following formula:
			rate of the data port = (base rate)*(number of DS0 channels)." 
--	DEFVAL	1
	::= {e1CfgGroup 11}

e1CfgDataPort2Timing OBJECT-TYPE
	SYNTAX	INTEGER {
		normal (1),
		tailCircuit (2)
		}
	ACCESS	read-write
	STATUS	mandatory
	DESCRIPTION	"Sets how the clocking will be supplied for Data Port 2 on the
			E1 module." 
--	DEFVAL	1
	::= {e1CfgGroup 12}

e1CfgDataPort2DTRControl OBJECT-TYPE
	SYNTAX	INTEGER {
		dtrNormal (1),
		dtrForced (2)
		}
	ACCESS	read-write
	STATUS	mandatory
	DESCRIPTION	"Sets the DTR control for Data Port 2 on the E1 module.  Option (1),
			dtrNormal, will configure DTR control from the DTE equipment.  
			Option (2), dtrForced, will force DTR to a '1'." 
--	DEFVAL	1
	::= {e1CfgGroup 13}

e1CfgDataPort2RTSControl OBJECT-TYPE
	SYNTAX	INTEGER {
		rtsNormal (1),
		rtsForced (2)
		}
	ACCESS	read-write
	STATUS	mandatory
	DESCRIPTION	"Sets the RTS control for Data Port 2 on the E1 module.  Option (1),
			rtsNormal, will configure RTS control from the DTE equipment.  
			Option (2), rtsForced, will force RTS to a '1'." 
--	DEFVAL	1
	::= {e1CfgGroup 14}

e1CfgCCMLinkA1Rate OBJECT-TYPE
	SYNTAX	INTEGER {
		multipleOf64kbps (1),
		multipleOf56kbps (2)
		}
	ACCESS	read-write
	STATUS	mandatory
	DESCRIPTION	"Sets the base rate of the CCM A1 channel for an E1 interface. 
			The actual rate will be determined by the following formula:
			rate of the CCM port = (base rate)*(number of DS0 channels)." 
--	DEFVAL	1
	::= {e1CfgGroup 15}

e1CfgCCMLinkA2Rate OBJECT-TYPE
	SYNTAX	INTEGER {
		multipleOf64kbps (1),
		multipleOf56kbps (2)
		}
	ACCESS	read-write
	STATUS	mandatory
	DESCRIPTION	"Sets the base rate of the CCM A2 channel for an E1 interface. 
			The actual rate will be determined by the following formula:
			rate of the CCM port = (base rate)*(number of DS0 channels." 
--	DEFVAL	1
	::= {e1CfgGroup 16}

e1CfgCCMLinkA3Rate OBJECT-TYPE
	SYNTAX	INTEGER {
		multipleOf64kbps (1),
		multipleOf56kbps (2)
		}
	ACCESS	read-write
	STATUS	mandatory
	DESCRIPTION	"Sets the base rate of the CCM A3 channel for an E1 interface. 
			The actual rate will be determined by the following formula:
			rate of the CCM port = (base rate)*(number of DS0 channels." 
--	DEFVAL	1
	::= {e1CfgGroup 17}

e1CfgCCMLinkA4Rate OBJECT-TYPE
	SYNTAX	INTEGER {
		multipleOf64kbps (1),
		multipleOf56kbps (2)
		}
	ACCESS	read-write
	STATUS	mandatory
	DESCRIPTION	"Sets the base rate of the CCM A4 channel for an E1 interface. 
			The actual rate will be determined by the following formula:
			rate of the CCM port = (base rate)*(number of DS0 channels." 
--	DEFVAL	1
	::= {e1CfgGroup 18}

e1CfgCCMLinkA5Rate OBJECT-TYPE
	SYNTAX	INTEGER {
		multipleOf64kbps (1),
		multipleOf56kbps (2)
		}
	ACCESS	read-write
	STATUS	mandatory
	DESCRIPTION	"Sets the base rate of the CCM A5 channel for an E1 interface. 
			The actual rate will be determined by the following formula:
			rate of the CCM port = (base rate)*(number of DS0 channels."
--	DEFVAL	1
	::= {e1CfgGroup 19}

e1CfgCCMLinkA6Rate OBJECT-TYPE
	SYNTAX	INTEGER {
		multipleOf64kbps (1),
		multipleOf56kbps (2)
		}
	ACCESS	read-write
	STATUS	mandatory
	DESCRIPTION	"Sets the base rate of the CCM A6 channel for an E1 interface. 
			The actual rate will be determined by the following formula:
			rate of the CCM port = (base rate)*(number of DS0 channels." 
--	DEFVAL	1
	::= {e1CfgGroup 20}

e1CfgSystemClockSource OBJECT-TYPE
	SYNTAX	INTEGER {
		clockDerivedL1 (1),
		clockDerivedL2 (2),
		internalClocking (3)
		}
	ACCESS	read-write
	STATUS	mandatory
	DESCRIPTION	"Configures the source of the clock used in the E1 Access 
			Module. Options include:
			- clockDerivedL1.  The clock source is from the L1 interface.
			- clockDerivedL2.  The clock source is from the L2 interface.
			- internalClocking.  The clock is derived from a clock source
				internal to the E1 Access Module." 
--	DEFVAL	1
	::= {e1CfgGroup 21}

e1CfgL1Crc4 OBJECT-TYPE
	SYNTAX	INTEGER {
		enabled (1),
		disabled (2)
		}
	ACCESS	read-write
	STATUS	mandatory
	DESCRIPTION	"Enables/Disables the CRC-4 mode for the L1 interface on the
			E1 module." 
--	DEFVAL	055
	::= {e1CfgGroup 22}

e1CfgL2Crc4 OBJECT-TYPE
	SYNTAX	INTEGER {
		enabled (1),
		disabled (2)
		}
	ACCESS	read-write
	STATUS	mandatory
	DESCRIPTION	"Enables/Disables the CRC-4 mode for the L2 interface on the
			E1 module." 
--	DEFVAL	055
	::= {e1CfgGroup 23}

e1CfgL1Config OBJECT-TYPE
	SYNTAX INTEGER {
		init (1),
		commit (2)
		}
	ACCESS write-only
	STATUS mandatory
	DESCRIPTION 	"This object is a write only object that will signal the proxy to
		start caching changes to the L1 ds0 connection tables.  This is done to
		solve an anomaly in the marathon/e1 design. The manager must set
		this object to init before updating any of the e1L1InterfaceTable objects.
		When all the changes have been set then this object will have to be set to
		commit (2).  The init will cause the proxy to upload the table from the marathon
		and the commit will cause the proxy to send all the changes to the marathon."
	::= {e1CfgGroup 24}

e1CfgL2Config OBJECT-TYPE
	SYNTAX INTEGER {
		init (1),
		commit (2)
		}
	ACCESS write-only
	STATUS mandatory
	DESCRIPTION 	"This object is a write only object that will signal the proxy to
		start caching changes to the L2 ds0 connection tables.  This is done to
		solve an anomaly in the marathon/e1 design. The manager must set
		this object to init before updating any of the e1L2InterfaceTable objects.
		When all the changes have been set then this object will have to be set to
		commit (2).  The init will cause the proxy to upload the table from the marathon
		and the commit will cause the proxy to send all the changes to the marathon."
	::= {e1CfgGroup 25}


-- N_HOUSE.O_T1FLSH ===================================================


e1FlashControlTable OBJECT-TYPE
	SYNTAX	SEQUENCE OF E1FlashControlEntry
	ACCESS	not-accessible
	STATUS	mandatory
	DESCRIPTION	"Table to control (erase) E1 flash memory in preparation for a 
			code download." 
	::= { e1-interface 4}

e1FlashControlEntry OBJECT-TYPE
	SYNTAX	E1FlashControlEntry 
	ACCESS	not-accessible
	STATUS	mandatory
	DESCRIPTION	"Entry within the table specific to a particular E1 module/card
			number for flash memory control." 
	INDEX	 	{ e1FlashControlCardNumber }
	::= { e1FlashControlTable 1}

E1FlashControlEntry ::= SEQUENCE {
	e1FlashControlCardNumber		INTEGER,
	e1FlashControlCommand		INTEGER,
	e1FlashControlFlashStatus		INTEGER
	}

e1FlashControlCardNumber OBJECT-TYPE
	SYNTAX	INTEGER (2..5)
	ACCESS	read-only
	STATUS	mandatory
	DESCRIPTION	"Identifies the E1 module/card number for flash memory control." 
	::= { e1FlashControlEntry 1}

e1FlashControlCommand OBJECT-TYPE
	SYNTAX	INTEGER {
		eraseCardFlash (1)
		}
	ACCESS	write-only
	STATUS	mandatory
	DESCRIPTION	"Controls the E1 module flash memory in preparation of a code
			download.  Perform a SET with the value eraseCardFlash to erase
			the flash memory prior to downloading new E1 flash software." 
	::= { e1FlashControlEntry 2}

e1FlashControlFlashStatus OBJECT-TYPE
	SYNTAX	INTEGER {
		bootImageCorrupt (1),
		t1FlashImageValid (2),
		t1FlashErased (3),
		t1FlashImageInvalid (4),
		securityViolation (5),
		eraseAborted (6)
		}
	ACCESS	read-only
	STATUS	mandatory
	DESCRIPTION	"Identifies the status of the E1 module/card flash memory." 
	::= { e1FlashControlEntry 3}

-- Trap Configuration group

-- N_CMOS.O_CMDRPT ======================================================

trapAlarmEventReportingGroup    OBJECT IDENTIFIER ::= {trap 1}

trapAlarmEventReportingAlarms OBJECT-TYPE
	SYNTAX	INTEGER {
		enable (1),
		disable (2)
		}
	ACCESS	read-write
	STATUS	mandatory
	DESCRIPTION	"When enabled, displays the received alarms on command facility." 
	::= {trapAlarmEventReportingGroup 1}

trapAlarmEventReportingEvents OBJECT-TYPE
	SYNTAX	INTEGER {
		enable (1),
		disable (2)
		}
	ACCESS	read-write
	STATUS	mandatory
	DESCRIPTION	"When enabled, displays the received events on command facility." 
	::= {trapAlarmEventReportingGroup 2}

-- ====================================================================

trapEventsCollectionInterval OBJECT-TYPE
	SYNTAX	INTEGER (1..15)
	ACCESS	read-write 
	STATUS	mandatory
--	DEFVAL	5
	DESCRIPTION	"Periodic interval time between event collection poll cycles 
			(in minutes)."
	::= {trap 2}

-- Trap Subscription Group

trapSubsTable OBJECT-TYPE
	SYNTAX	SEQUENCE OF TrapSubsEntry
	ACCESS	not-accessible
	STATUS	mandatory
	DESCRIPTION	"Table to configure the recipients of the traps." 
	::= {trap 3}

trapSubsEntry OBJECT-TYPE
	SYNTAX	TrapSubsEntry
	ACCESS	not-accessible
	STATUS	mandatory
	DESCRIPTION	"Entry within the table specifying each recipient." 
	INDEX		{ trapSubsIPAddress}
	::= {trapSubsTable 1}

TrapSubsEntry ::= SEQUENCE {
	trapSubsIPAddress		IpAddress,
	trapSubsCommunityString	DisplayString,
	trapSubsAction		INTEGER
	}

trapSubsIPAddress OBJECT-TYPE
	SYNTAX	IpAddress
	ACCESS	read-write
	STATUS	mandatory
	DESCRIPTION	"Configures the IP address of the recipient station (manager)."
	::= {trapSubsEntry 1}

trapSubsCommunityString OBJECT-TYPE
	SYNTAX	DisplayString
	ACCESS	read-write
	STATUS	mandatory
	DESCRIPTION	"Configures the expected community string for the trap PDU to
			be forwarded to the configured recipient." 
	::= {trapSubsEntry 2}

trapSubsAction OBJECT-TYPE
	SYNTAX	INTEGER {
		subscribe (1),
		cancelSubscription (2)
	}
	ACCESS	write-only
	STATUS	mandatory
	DESCRIPTION	"Adds a new recipient or deletes an already configured recipient
			from the subscription list." 
	::= {trapSubsEntry 3}


-- N_CMOS.O_CMDRPT =======================================================

trapCfgAlarmEventsPortGroup    OBJECT IDENTIFIER ::= {trap 4}

trapCfgTrapPort OBJECT-TYPE
	SYNTAX	INTEGER {
		localCommandPort (1),
		localLogPort (2),
		remoteNode (3),
		externalModem (4)
	}
	ACCESS	read-write
	STATUS	mandatory
	DESCRIPTION	"Configures the destination for the output of alarms and events." 
	::= { trapCfgAlarmEventsPortGroup 1}

trapCfgExtModemPriority OBJECT-TYPE
	SYNTAX	INTEGER {
		high (1),
		low (2)
	}
	ACCESS	read-write
	STATUS	mandatory
	DESCRIPTION	"Configures the priority for alarms and events sent to an external
			modem." 
	::= { trapCfgAlarmEventsPortGroup 2}


-- N_CMOS.O_CMDRPT =======================================================


trapCfgExtAlarmRelay OBJECT-TYPE
	SYNTAX	INTEGER {
		enable (1),
		disable (2)
	}
	ACCESS	read-write
	STATUS	mandatory
	DESCRIPTION	"Controls the external alarm relay on an NMS module." 
	::= {trap 5}


-- Trap identification group

trapNodeName OBJECT-TYPE
	SYNTAX	DisplayString
	ACCESS	not-accessible
	STATUS	mandatory
	DESCRIPTION	"Identifies the name of the node that generated the trap." 
	::= {trap 6}

trapCardNumber OBJECT-TYPE
	SYNTAX	INTEGER
	ACCESS	not-accessible
	STATUS	mandatory
	DESCRIPTION	"Identifies the module/card number responsible for generating
			the trap." 
	::= {trap 7}

trapChannelNumber OBJECT-TYPE
	SYNTAX	INTEGER
	ACCESS	not-accessible
	STATUS	mandatory
	DESCRIPTION	"Identifies the port/channel number responsible for generating
			the trap." 
	::= {trap 8}

trapFirstNodeName OBJECT-TYPE
	SYNTAX	DisplayString
	ACCESS	not-accessible
	STATUS	mandatory
	DESCRIPTION	"Identifies the source node name of the trap." 
	::= {trap 9}

trapFirstCardNumberOrInternalFacilityIndication OBJECT-TYPE
	SYNTAX	INTEGER
	ACCESS	not-accessible
	STATUS	mandatory
	DESCRIPTION	"This identifies the card number that has generated the trap.
			A value of  0FFh siginifies a special condition which identifies that the
			trapChannelNumberOrInternalFacility object in the varBind contains
			the type of internal facility." 
	::= {trap 10}

trapFirstChannelNumberOrInternalFacility OBJECT-TYPE
	SYNTAX	INTEGER
	ACCESS	not-accessible
	STATUS	mandatory
	DESCRIPTION	"This identifies the channel number that has generated the trap. If the
			trapCardNumberOrInternalFacilityIndication object has a value of
			0FFh then this objects identifies the internal facilities as $CMD if value
			is 0, $PPP if the value is 1, and $DLD if the value is 2."
	::= {trap 11}

trapSecondNodeName OBJECT-TYPE
	SYNTAX	DisplayString
	ACCESS	not-accessible
	STATUS	mandatory
	DESCRIPTION	"Identifies the destination node name of the trap." 
	::= {trap 12}

trapSecondCardNumberOrInternalFacilityIndication OBJECT-TYPE
	SYNTAX	INTEGER (1..5)
	ACCESS	not-accessible
	STATUS	mandatory
	DESCRIPTION	"This identifies the second card number that has generated the trap.
			A value of  0FFh siginifies a special condition which identifies that the
			trapChannelNumberOrInternalFacility object in the varBind contains
			the type of internal facility."  
	::= {trap 13}

trapSecondChannelNumberOrInternalFacility OBJECT-TYPE
	SYNTAX	INTEGER
	ACCESS	not-accessible
	STATUS	mandatory
	DESCRIPTION	"This identifies the second channel number that has generated the trap.
			If the trapCardNumberOrInternalFacilityIndication object has a value of
			0ffh then this objects identifies the internal facilities as $CMD if
			value is 0, $PPP if the value is 1, and $DLD if the value is 2."
 
	::= {trap 14}

trapClassRequestedOrMatrixRequest OBJECT-TYPE
	SYNTAX	INTEGER 
	ACCESS	not-accessible
	STATUS	mandatory
	DESCRIPTION	"This identifies either the requested class number if the values are 
			between the allowable class number range (i.e. 1 to 64) or the matrix 
			request if the object value is 0." 
	::= {trap 15}

trapLinkType OBJECT-TYPE
	SYNTAX	INTEGER {
		physicalLink (1),
		frameRelayDLCI (2)
		}
	ACCESS	not-accessible
	STATUS	mandatory
	DESCRIPTION	"Identifies the Link type associated with the trap." 
	::= {trap 16}

trapDLCINumber OBJECT-TYPE
	SYNTAX	INTEGER
	ACCESS	not-accessible
	STATUS	mandatory
	DESCRIPTION	"Identifies the DLCI number associated with the trap corresponding
			to a Frame Relay link." 
	::= {trap 17}

trapDLCIFirstLinkCardNumber OBJECT-TYPE
	SYNTAX	INTEGER
	ACCESS	not-accessible
	STATUS	mandatory
	DESCRIPTION	"Identifies the module/card number associated with the trap
			corresponding to a DLCI channel of the source Frame Relay link." 
	::= {trap 18}

trapDLCIFirstLinkChannelNumber OBJECT-TYPE
	SYNTAX	INTEGER
	ACCESS	not-accessible
	STATUS	mandatory
	DESCRIPTION	"Identifies the port/channel number associated with the trap
			corresponding to a DLCI channel of the source Frame Relay link." 
	::= {trap 19}

trapDLCIFirstLinkDLCINumber OBJECT-TYPE
	SYNTAX	INTEGER
	ACCESS	not-accessible
	STATUS	mandatory
	DESCRIPTION	"Identifies the DLCI channel number associated with the trap
			corresponding to the source Frame Relay link." 
	::= {trap 20}

trapDLCISecondLinkCardNumber OBJECT-TYPE
	SYNTAX	INTEGER
	ACCESS	not-accessible
	STATUS	mandatory
	DESCRIPTION	"Identifies the port/channel number associated with the trap
			corresponding to a DLCI channel of the destination Frame Relay link." 
	::= {trap 21}

trapDLCISecondLinkChannelNumber OBJECT-TYPE
	SYNTAX	INTEGER
	ACCESS	not-accessible
	STATUS	mandatory
	DESCRIPTION	"Identifies the port/channel number associated with the trap
			corresponding to a DLCI channel of the destination Frame Relay link." 
	::= {trap 22}

trapDLCISecondLinkDLCINumber OBJECT-TYPE
	SYNTAX	INTEGER
	ACCESS	not-accessible
	STATUS	mandatory
	DESCRIPTION	"Identifies the DLCI channel number associated with the trap
			corresponding to the destination Frame Relay link." 
	::= {trap 23}

-- Marathon Trap Messages

mcmEventConnect TRAP-TYPE
	ENTERPRISE	micom
	VARIABLES	{trapFirstNodeName, trapFirstCardNumberOrInternalFacilityIndication, 
			trapFirstChannelNumberOrInternalFacility, trapSecondNodeName,
			trapSecondCardNumberOrInternalFacilityIndication, 
			trapSecondChannelNumberOrInternalFacility}
	DESCRIPTION	"A connection has been established between the specified
				pair of unit ports."
	::= 1

mcmEventDisconnect TRAP-TYPE
	ENTERPRISE	micom
	VARIABLES	{trapFirstNodeName, trapFirstCardNumberOrInternalFacilityIndication, 
			trapFirstChannelNumberOrInternalFacility, trapSecondNodeName,
			trapSecondCardNumberOrInternalFacilityIndication, 
			trapSecondChannelNumberOrInternalFacility}
	DESCRIPTION	"The connection between the specified pair of unit ports
				has been broken."
	::= 2

mcmEventQueueEntry TRAP-TYPE
	ENTERPRISE	micom
	VARIABLES	{trapNodeName, trapChannelNumber, trapCardNumber,
			 trapClassRequestedOrMatrixRequest}
	DESCRIPTION	"A port has been placed in a first-come first-served queue
				for the next available port in the requested class."
	::= 3

mcmEventCallFail TRAP-TYPE
	ENTERPRISE	micom
	VARIABLES	{trapNodeName, trapCardNumber, trapChannelNumber, 
			 trapClassRequestedOrMatrixRequest }
	DESCRIPTION	"A matrix connection made by the local port did not complete
				successfully (for example, the password was incorrect)."
	::= 4

mcmEventDDSInService TRAP-TYPE
	ENTERPRISE	micom
	VARIABLES	{trapNodeName, trapCardNumber, trapChannelNumber}
	DESCRIPTION	"The unit's ISU module is back in service, and the associated
				link is up."
	::= 5

mcmEventDDSOutService TRAP-TYPE
	ENTERPRISE	micom
	VARIABLES	{trapNodeName, trapCardNumber, trapChannelNumber}
	DESCRIPTION	"The unit's ISU module is out of service, and the associated
				link is down."
	::= 6

mcmEventDDSLoopTest TRAP-TYPE
	ENTERPRISE	micom
	VARIABLES	{trapNodeName, trapCardNumber, trapChannelNumber}
	DESCRIPTION	"The telephone company has placed the unit's ISU module
				into a loop test mode."
	::= 7

mcmEventADBConnectMade TRAP-TYPE
	ENTERPRISE	micom
	VARIABLES	{trapNodeName, trapCardNumber, trapChannelNumber}
	DESCRIPTION	"The unit's modem module has completed a dial backup
				connection, and the associated link is up."
	::= 8

mcmEventADBConnectDrop TRAP-TYPE
	ENTERPRISE	micom
	VARIABLES	{trapNodeName, trapCardNumber, trapChannelNumber}
	DESCRIPTION	"The unit's modem module has dropped the dial line
				connection due to bad lines, Data Terminal Ready
				dropped, or Carrier Detect lost.  As a result, the
				associated link is down."
	::= 9

mcmEventForcedDialMode TRAP-TYPE
	ENTERPRISE	micom
	VARIABLES	{trapNodeName, trapCardNumber, trapChannelNumber}
	DESCRIPTION	"The unit's modem module has been placed into the forced
				dial mode.  The associated link will always be established
				over the dial lines."
	::= 10

mcmEventForcedLeaseMode TRAP-TYPE
	ENTERPRISE	micom
	VARIABLES	{trapNodeName, trapCardNumber, trapChannelNumber}
	DESCRIPTION	"The unit's modem module has been placed into the forced
				lease mode.  The associated link will always be established
				over the lease lines; no dial backup can occur."
	::= 11

mcmEventLeasedConnect TRAP-TYPE
	ENTERPRISE	micom
	VARIABLES	{trapNodeName, trapCardNumber, trapChannelNumber}
	DESCRIPTION	"The unit's modem module has established communications
				over the lease lines, and the associated link is up."
	::= 12

mcmEventLeaseLineRetry TRAP-TYPE
	ENTERPRISE	micom
	VARIABLES	{trapNodeName, trapCardNumber, trapChannelNumber}
	DESCRIPTION	"The unit's modem module has started operating on the
				lease lines while the dial line connection is still
				established."
	::= 13

mcmEventLinkRestart TRAP-TYPE
	ENTERPRISE	micom
	VARIABLES	{trapNodeName, trapCardNumber, trapChannelNumber, 
			trapLinkType, trapDLCINumber}
	DESCRIPTION	"Communications on the local side of the associated link
				have been restarted."
	::= 14

mcmEventRemoteLinkRestart TRAP-TYPE
	ENTERPRISE	micom
	VARIABLES	{trapNodeName, trapCardNumber, trapChannelNumber, 
			trapLinkType, trapDLCINumber}
	DESCRIPTION	"Communications on the remote end of the specified link
				have been restarted."
	::= 15

mcmEventNoADBNumber TRAP-TYPE
	ENTERPRISE	micom
	VARIABLES	{trapNodeName, trapCardNumber, trapChannelNumber}
	DESCRIPTION	"No number has been configured for auto dial backup
				for the specified link."
	::= 16

mcmEventADBNoRXDialTone TRAP-TYPE
	ENTERPRISE	micom
	VARIABLES	{trapNodeName, trapCardNumber, trapChannelNumber}
	DESCRIPTION	"The dial backup function on the unit's modem module
				went off-hook on the Rx line, and a dial tone was not
				detected."
	::= 17

mcmEventADBNoTxDialTone TRAP-TYPE
	ENTERPRISE	micom
	VARIABLES	{trapNodeName, trapCardNumber, trapChannelNumber}
	DESCRIPTION	"The dial backup function on the unit's modem module
				went off-hook on the Tx line, and a dial tone was not
				detected."
	::= 18

mcmEventADBRxDialing TRAP-TYPE
	ENTERPRISE	micom
	VARIABLES	{trapNodeName, trapCardNumber, trapChannelNumber}
	DESCRIPTION	"The dial backup function on the unit's modem module
				is dialing the telephone number for the Rx line."
	::= 19

mcmEventADBTxDialing TRAP-TYPE
	ENTERPRISE	micom
	VARIABLES	{trapNodeName, trapCardNumber, trapChannelNumber}
	DESCRIPTION	"The dial backup function on the unit's modem module
				is dialing the telephone number for the Tx line."
	::= 20

mcmEventADBNoAnswer TRAP-TYPE
	ENTERPRISE	micom
	VARIABLES	{trapNodeName, trapCardNumber, trapChannelNumber}
	DESCRIPTION	"The dial backup function on the unit's modem module
				did not receive an answer tone after placing a call
				on a dial line."
	::= 21

mcmEventADBRxBusy TRAP-TYPE
	ENTERPRISE	micom
	VARIABLES	{trapNodeName, trapCardNumber, trapChannelNumber}
	DESCRIPTION	"The dial backup function on the unit's modem module
				has detected a busy signal on the Rx dial line."
	::= 22

mcmEventADBTxBusy TRAP-TYPE
	ENTERPRISE	micom
	VARIABLES	{trapNodeName, trapCardNumber, trapChannelNumber}
	DESCRIPTION	"The dial backup function on the unit's modem module
				has detected a busy signal on the Tx dial line."
	::= 23

mcmEventADBRxRinging TRAP-TYPE
	ENTERPRISE	micom
	VARIABLES	{trapNodeName, trapCardNumber, trapChannelNumber}
	DESCRIPTION	"The dial backup function on the unit's modem module
				has detected an incoming call on the Rx dial line."
	::= 24

mcmEventADBTxRinging TRAP-TYPE
	ENTERPRISE	micom
	VARIABLES	{trapNodeName, trapCardNumber, trapChannelNumber}
	DESCRIPTION	"The dial backup function on the unit's modem module
				has detected an incoming call on the Tx dial line."
	::= 25

mcmEventADBRingDetect TRAP-TYPE
	ENTERPRISE	micom
	VARIABLES	{trapNodeName, trapCardNumber, trapChannelNumber}
	DESCRIPTION	"A call is being transmitted or received by the dial
				backup function of the unit's modem module."
	::= 26

mcmEventADBNoDialTone TRAP-TYPE
	ENTERPRISE	micom
	VARIABLES	{trapNodeName, trapCardNumber, trapChannelNumber}
	DESCRIPTION	"The dial backup function on the unit's modem module
				went off-hook on either the Tx or Rx dial line and
				failed to detect a dial tone."
	::= 27

mcmEventVoiceBusyOut TRAP-TYPE
	ENTERPRISE	micom
	VARIABLES	{trapNodeName, trapCardNumber, trapChannelNumber}
	DESCRIPTION	"A voice channel has been placed in the busyout state.
				This can be caused by: one, the link experiencing a loss
				of sync; two, force disable or force disconnect commands
				having been executed; or three, an operator placing the
				channel into the busyout state using a force-busy command."
	::= 28

mcmEventVoiceClearBusy TRAP-TYPE
	ENTERPRISE	micom
	VARIABLES	{trapNodeName, trapCardNumber, trapChannelNumber}
	DESCRIPTION	"The condition that caused the voice channel busyout
				has been cleared or terminated."
	::= 29

mcmEventADBRxConnect TRAP-TYPE
	ENTERPRISE	micom
	VARIABLES	{trapNodeName, trapCardNumber, trapChannelNumber}
	DESCRIPTION	"The dial backup function on the unit's modem module
				has answered a call over the Rx dial line, and the Rx
				dial backup connection is made."
	::= 30

mcmEventADBTxConnect TRAP-TYPE
	ENTERPRISE	micom
	VARIABLES	{trapNodeName, trapCardNumber, trapChannelNumber}
	DESCRIPTION	"The dial backup function on the unit's modem module
				has answered a call over the Tx dial line, and the Tx
				dial backup connection is made."
	::= 31

mcmEventADBLineBusy TRAP-TYPE
	ENTERPRISE	micom
	VARIABLES	{trapNodeName, trapCardNumber, trapChannelNumber}
	DESCRIPTION	"The dial backup function on the unit's modem module has
				encountered a busy signal over the Tx of Tx lines."
	::= 32

mcmEventADBRIDetect TRAP-TYPE
	ENTERPRISE	micom
	VARIABLES	{trapNodeName, trapCardNumber, trapChannelNumber}
	DESCRIPTION	"The dial backup function on the unit's modem module has
				detected an incoming call."
	::= 33

mcmEventADBAbort TRAP-TYPE
	ENTERPRISE	micom
	VARIABLES	{trapNodeName, trapCardNumber, trapChannelNumber}
	DESCRIPTION	"A call placed on the dial lines by the dial backup
				function of the unit's modem module has failed.  This
				message is issued by the call-originating unit."
	::= 34

mcmEventLeasedLineOOS TRAP-TYPE
	ENTERPRISE	micom
	VARIABLES	{trapNodeName, trapCardNumber, trapChannelNumber}
	DESCRIPTION	"The unit's modem module is unable to communicate with
				the remote modem over the lease lines.  It is Out Of
				Service (OOS)."
	::= 35

mcmEventNewDLCI TRAP-TYPE
	ENTERPRISE	micom
	VARIABLES	{trapNodeName, trapCardNumber, trapChannelNumber, 
			trapLinkType, trapDLCINumber}
	DESCRIPTION	"A DLCI (Data Link Connection Identifier) was added."
	::= 36

mcmEventDLCIActive TRAP-TYPE
	ENTERPRISE	micom
	VARIABLES	{trapNodeName, trapCardNumber, trapChannelNumber, 
			trapLinkType, trapDLCINumber}
	DESCRIPTION	"A DLCI (Data Link Connection Identifier) was activated."
	::= 37

mcmEventConfigurationUpdate TRAP-TYPE
	ENTERPRISE	micom
	VARIABLES	{trapNodeName}
	DESCRIPTION	"The node's configuration has been successfully written to
				the FLASH DRAM (applicable to 3K and 5KT Pro platforms)."
	::= 38

mcmEventDLCIConnect TRAP-TYPE
	ENTERPRISE	micom
	VARIABLES	{trapDLCIFirstLinkCardNumber, trapDLCIFirstLinkChannelNumber,
			trapDLCIFirstLinkDLCINumber,
			 trapDLCISecondLinkCardNumber, trapDLCISecondLinkChannelNumber,
			trapDLCISecondLinkDLCINumber}
	DESCRIPTION	"A DLCI connection has been established between a pair
				of unit ports."
	::= 39

mcmEventDLCIDisconnect TRAP-TYPE
	ENTERPRISE	micom
	VARIABLES	{trapNodeName, trapCardNumber, trapChannelNumber, 
			trapLinkType, trapDLCINumber}
	DESCRIPTION	"The DLCI connection between the specified pair of unit
				ports has been broken."
	::= 40


mcmProxyEventPollingBegin TRAP-TYPE
	ENTERPRISE	micom
	DESCRIPTION "The proxy agent has begun polling for events at the
				specified time."
	::= 600

mcmProxyEventPollingEnd TRAP-TYPE
	ENTERPRISE	micom
	DESCRIPTION "The proxy agent has completed the event poll cycle."
	::= 601

-- ALARMS

mcmAlarmSystemReset TRAP-TYPE
	ENTERPRISE	micom
	VARIABLES	{trapNodeName}
	DESCRIPTION	"The specified unit has been reset (either warm or cold start)."
	::= 101

mcmAlarmBatteryLow TRAP-TYPE
	ENTERPRISE	micom
	VARIABLES	{trapNodeName}
	DESCRIPTION	"The CMOS RAM backup battery in the specified unit is in need
				of replacement."
	::= 102

mcmAlarmCmosError TRAP-TYPE
	ENTERPRISE	micom
	VARIABLES	{trapNodeName}
	DESCRIPTION	"The specified unit encountered a problem writing to the
				configuration area (CMOS RAM)."
	::= 103

mcmAlarmSystemFlowControl TRAP-TYPE
	ENTERPRISE	micom
	VARIABLES	{trapNodeName}
	DESCRIPTION	"The specified unit is turning off data input from its ports
				to prevent buffer overflow.  This condition generally occurs
				due to insufficient data throughput across the link."
	::= 104

mcmAlarmNodeTableFull TRAP-TYPE
	ENTERPRISE	micom
	VARIABLES	{trapNodeName}
	DESCRIPTION	"There are no more available node numbers that can be
				assigned to new units on this network."
	::= 105

mcmAlarmDuplicateNodeNumber TRAP-TYPE
	ENTERPRISE	micom
	VARIABLES	{trapNodeName, trapCardNumber, trapChannelNumber, 
			trapLinkType, trapDLCINumber}
	DESCRIPTION	"Two nodes in the network have the same node ID number."
	::= 106

mcmAlarmInvalidLinkCfg TRAP-TYPE
	ENTERPRISE	micom
	VARIABLES	{trapNodeName, trapCardNumber, trapChannelNumber, 
			trapLinkType, trapDLCINumber}
	DESCRIPTION	"An attempt has been made to connect a mux link to a port
				configured other than a mux link, or vice versa."
	::= 107


mcmAlarmBufferOverFlow TRAP-TYPE
	ENTERPRISE	micom
	VARIABLES	{trapNodeName, trapCardNumber, trapChannelNumber }
	DESCRIPTION	"Data has been lost for a specific port on the specified
				unit due to an buffer overflow condition."
	::= 120

mcmAlarmLinkDown TRAP-TYPE
	ENTERPRISE	micom
	VARIABLES	{trapNodeName, trapCardNumber, trapChannelNumber, 
			trapLinkType, trapDLCINumber}
	DESCRIPTION	"The unit has timed out (40 secs) waiting for synchronization
				to be acquired on the link.  Check the cabling, modem, and
				remote unit for the source of the problem."
	::= 121

mcmAlarmSyncLoss TRAP-TYPE
	ENTERPRISE	micom
	VARIABLES	{trapNodeName, trapCardNumber, trapChannelNumber, 
			trapLinkType, trapDLCINumber}
	DESCRIPTION	"Synchronization has been lost with the remote unit attached
				to the specified link."
	::= 122

mcmAlarmSyncAcquire TRAP-TYPE
	ENTERPRISE	micom
	VARIABLES	{trapNodeName, trapCardNumber, trapChannelNumber, 
			trapLinkType, trapDLCINumber}
	DESCRIPTION	"Synchronization has been achieved with the remote unit
				attached to the specified link."
	::= 123

mcmAlarmCarrierLoss TRAP-TYPE
	ENTERPRISE	micom
	VARIABLES	{trapNodeName, trapCardNumber, trapChannelNumber, 
			trapLinkType, trapDLCINumber}
	DESCRIPTION	"The carrier signal has been lost on the specified link
				(as detected from the CD interface control signal)."
	::= 124

mcmAlarmCarrierAcquire TRAP-TYPE
	ENTERPRISE	micom
	VARIABLES	{trapNodeName, trapCardNumber, trapChannelNumber, 
			trapLinkType, trapDLCINumber}
	DESCRIPTION	"The carrier signal has been detected on the specified
				link (after the carrier had been previously lost)."
	::= 125

mcmAlarmLineAlarm TRAP-TYPE
	ENTERPRISE	micom
	VARIABLES	{trapNodeName, trapCardNumber, trapChannelNumber, 
			trapLinkType, trapDLCINumber}
	DESCRIPTION	"A high error rate is occurring on the specified link."
	::= 126

mcmAlarmSyncChannelStopped TRAP-TYPE
	ENTERPRISE	micom
	VARIABLES	{trapNodeName, trapCardNumber, trapChannelNumber }
	DESCRIPTION	"The specified synchronous port has lost its output
				clock or the input end of the frame is missing."
	::= 127

mcmAlarmLANCardUp TRAP-TYPE
	ENTERPRISE	micom
	VARIABLES	{trapNodeName, trapCardNumber}
	DESCRIPTION	"The LAN card is operating and is available for use
				(after a previous LAN card down)."
	::= 128

mcmAlarmLANCardDown TRAP-TYPE
	ENTERPRISE	micom
	VARIABLES	{trapNodeName, trapCardNumber}
	DESCRIPTION	"The LAN card is not operating or is not available
				for use."
	::= 129

mcmAlarmX21CallFail TRAP-TYPE
	ENTERPRISE	micom
	VARIABLES	{trapNodeName, trapCardNumber, trapChannelNumber, 
			trapLinkType, trapDLCINumber}
	DESCRIPTION	"The specified unit was unable to complete a call over the
				X.21 network from the port indicated."
	::= 130

mcmAlarmPrimaryESIDown TRAP-TYPE
	ENTERPRISE	micom
	VARIABLES	{trapNodeName, trapCardNumber, trapChannelNumber, 
			trapLinkType, trapDLCINumber}
	DESCRIPTION	"When secondary interconnect links are configured on
				a node, this trap is sent if the primary link has timed
				out waiting for synchronization to be acquired on the
				primary link."
	::= 131

mcmAlarmStartESISecondary TRAP-TYPE
	ENTERPRISE	micom
	VARIABLES	{trapNodeName, trapCardNumber, trapChannelNumber, 
			trapLinkType, trapDLCINumber}
	DESCRIPTION	"The primary link has been down for a preset interval,
				and now the node is attempting to bring up the secondary
				link."
	::= 132

mcmAlarmSecondaryUp TRAP-TYPE
	ENTERPRISE	micom
	VARIABLES	{trapNodeName, trapCardNumber, trapChannelNumber, 
			trapLinkType, trapDLCINumber}
	DESCRIPTION	"Synchronization has been achieved on the secondary link
				and data is now being transferred across it."
	::= 133

mcmAlarmSecondaryTerminated TRAP-TYPE
	ENTERPRISE	micom
	VARIABLES	{trapNodeName, trapCardNumber, trapChannelNumber, 
			trapLinkType, trapDLCINumber}
	DESCRIPTION	"The primary link has been back up for a preset interval
				with data being transferred across it.  The node is now
				dropping the give secondary link."
	::= 134

mcmAlarmSecondaryDown TRAP-TYPE
	ENTERPRISE	micom
	VARIABLES	{trapNodeName, trapCardNumber, trapChannelNumber, 
			trapLinkType, trapDLCINumber}
	DESCRIPTION	"The secondary interconnect link has timed out waiting
				for synchronization to be acquired, after the link had
				been established with data being transferred on it."
	::= 135

mcmAlarmSecondaryReset TRAP-TYPE
	ENTERPRISE	micom
	VARIABLES	{trapNodeName, trapCardNumber, trapChannelNumber, 
			trapLinkType, trapDLCINumber}
	DESCRIPTION	"Communications on the secondary interconnect link have
				been restarted. "
	::= 136

mcmAlarmPrimaryESIUp TRAP-TYPE
	ENTERPRISE	micom
	VARIABLES	{trapNodeName, trapCardNumber, trapChannelNumber, 
			trapLinkType, trapDLCINumber}
	DESCRIPTION	"Synchronization has been achieved on the primary link
				and data is now being transferred across it."
	::= 137

mcmAlarmDLCIDeleted TRAP-TYPE
	ENTERPRISE	micom
	VARIABLES	{trapNodeName, trapCardNumber, trapChannelNumber, 
			trapLinkType, trapDLCINumber}
	DESCRIPTION	"A DLCI has been deleted."
	::= 138

mcmAlarmDLCIInactive TRAP-TYPE
	ENTERPRISE	micom
	VARIABLES	{trapNodeName, trapCardNumber, trapChannelNumber, 
			trapLinkType, trapDLCINumber}
	DESCRIPTION	"A DLCI was inactivated."
	::= 139

mcmAlarmT1NetworkRedAlarm TRAP-TYPE
	ENTERPRISE	micom
	VARIABLES	{trapNodeName}
	DESCRIPTION "A T1 Network (DS-1) Red Alarm is generated when a
				Receive-Loss-of-Frame is detected.  Voice signaling is 
				static when this condition occurs."
	::= 140

mcmAlarmT1NetworkRedClear TRAP-TYPE
	ENTERPRISE	micom
	VARIABLES	{trapNodeName}
	DESCRIPTION "A T1 Network (DS-1) Red Alarm condition has cleared."
	::= 141

mcmAlarmT1LocalRedAlarm TRAP-TYPE
	ENTERPRISE	micom
	VARIABLES	{trapNodeName}
	DESCRIPTION "A T1 Local (DSX-1) Red Alarm is generated when a
				Receive-Loss-of-Frame is detected.  Voice signaling is 
				static when this condition occurs."
	::= 142

mcmAlarmT1LocalRedClear TRAP-TYPE
	ENTERPRISE	micom
	VARIABLES	{trapNodeName}
	DESCRIPTION "A T1 Local (DSX-1) Red Alarm condition has cleared."
	::= 143

mcmAlarmT1NetworkYellowAlarm TRAP-TYPE
	ENTERPRISE	micom
	VARIABLES	{trapNodeName}
	DESCRIPTION "A T1 Network (DS-1) Yellow Alarm is generated and
				transmitted to a remote location when a T1 DS-1 Red
				Alarm is detected."
	::= 144

mcmAlarmT1NetworkYellowClear TRAP-TYPE
	ENTERPRISE	micom
	VARIABLES	{trapNodeName}
	DESCRIPTION "A T1 Network (DS-1) Yellow Alarm condition has cleared."
	::= 145

mcmAlarmT1LocalYellowAlarm TRAP-TYPE
	ENTERPRISE	micom
	VARIABLES	{trapNodeName}
	DESCRIPTION "A T1 Local (DSX-1) Yellow Alarm is generated and
				transmitted to a remote location when a T1 DSX-1 Red
				Alarm is detected."
	::= 146

mcmAlarmT1LocalYellowClear TRAP-TYPE
	ENTERPRISE	micom
	VARIABLES	{trapNodeName}
	DESCRIPTION "A T1 Local (DSX-1) Yellow Alarm condition has cleared."
	::= 147

mcmAlarmT1NetworkAlarmInd TRAP-TYPE
	ENTERPRISE	micom
	VARIABLES	{trapNodeName}
	DESCRIPTION "A T1 Network (DS-1) Alarm Indication is generated with the
				detection of the Out-of-Frame condition and when all 1's
				are detected on the line.  The Alarm Indication Signal (AIS)
				is generated by the T1 module when the Internal Digital
				Loopback test is invoked."
	::= 148

mcmAlarmT1NetworkAlarmIndClear TRAP-TYPE
	ENTERPRISE	micom
	VARIABLES	{trapNodeName}
	DESCRIPTION "A T1 Network (DS-1) Alarm Indication condition has cleared."
	::= 149

mcmAlarmT1LocalAlarmInd TRAP-TYPE
	ENTERPRISE	micom
	VARIABLES	{trapNodeName}
	DESCRIPTION "A T1 Local (DSX-1) Alarm Indication is generated with the
				detection of the Out-of-Frame condition and when all 1's
				are detected on the line.  The Alarm Indication Signal (AIS)
				is generated by the T1 module when the Internal Digital
				Loopback test is invoked."
	::= 150

mcmAlarmT1LocalAlarmIndClear TRAP-TYPE
	ENTERPRISE	micom
	VARIABLES	{trapNodeName}
	DESCRIPTION "A T1 Local (DSX-1) Alarm Indication condition has cleared."
	::= 151

mcmAlarmCheckConfiguration TRAP-TYPE
	ENTERPRISE	micom
	VARIABLES	{trapNodeName}
	DESCRIPTION "The configuration data was not written to the FLASH DRAM,
				following a reset."
	::= 152

mcmAlarmE1L2RedAlarm TRAP-TYPE
	ENTERPRISE	micom
	VARIABLES	{trapNodeName}
	DESCRIPTION "An Out-of-Frame condition has persisted for 100 milliseconds
				on L2.  This results from a loss of signal, or loss of frame
				synchronization."
	::= 153

mcmAlarmE1L2RedAlarmClear TRAP-TYPE
	ENTERPRISE	micom
	VARIABLES	{trapNodeName}
	DESCRIPTION "The condition causing the E1 L2 Red Alarm has been cleared."
	::= 154

mcmAlarmE1L1RedAlarm TRAP-TYPE
	ENTERPRISE	micom
	VARIABLES	{trapNodeName}
	DESCRIPTION "An Out-of-Frame condition has persisted for 100 milliseconds
				on L1.  This results from a loss of signal, or loss of frame
				synchronization."
	::= 155

mcmAlarmE1L1RedAlarmClear TRAP-TYPE
	ENTERPRISE	micom
	VARIABLES	{trapNodeName}
	DESCRIPTION "The condition causing the E1 L1 Red Alarm has been cleared."
	::= 156

mcmAlarmE1L2AlarmIndication TRAP-TYPE
	ENTERPRISE	micom
	VARIABLES	{trapNodeName}
	DESCRIPTION "An Alarm Indication Signal (AIS) occurred on L2.  This
				signal occurs when an Out-of-Frame and a pattern of all
				ones is detected on L2, and persists for 100 milliseconds.
				(AIS is generated when a defined condition is required to
				be transmitted on the E1 line.  Ex.: during loopbacks.)"
	::= 157

mcmAlarmE1L2AlarmIndicationClear TRAP-TYPE
	ENTERPRISE	micom
	VARIABLES	{trapNodeName}
	DESCRIPTION "The E1 L2 Alarm Indication condition has cleared."
	::= 158

mcmAlarmE1L1AlarmIndication TRAP-TYPE
	ENTERPRISE	micom
	VARIABLES	{trapNodeName}
	DESCRIPTION "An Alarm Indication Signal (AIS) occurred on L1.  This
				signal occurs when an Out-of-Frame and a pattern of all
				ones is detected on L1, and persists for 100 milliseconds.
				(AIS is generated when a defined condition is required to
				be transmitted on the E1 line.  Ex.: during loopbacks.)"
	::= 159

mcmAlarmE1L1AlarmIndicationClear TRAP-TYPE
	ENTERPRISE	micom
	VARIABLES	{trapNodeName}
	DESCRIPTION "The E1 L1 Alarm Indication condition has cleared."
	::= 160

mcmAlarmE1L2OOCASFrame TRAP-TYPE
	ENTERPRISE	micom
	VARIABLES	{trapNodeName}
	DESCRIPTION "An Out of CAS Frame condition occurred on the Line 2 (L2)
				interface.  A Multiframe Alignment Signaling Loss indicates
				that the CAS signaling is no longer in sync,  This can be
				caused by a loss of framing, defective hardware, or improper
				generation of signaling information on time slot 16.  The
				EAM will set the 'Y' bit in time slot 16 of frame 0."
	::= 161

mcmAlarmE1L2OOCASFrameClear TRAP-TYPE
	ENTERPRISE	micom
	VARIABLES	{trapNodeName}
	DESCRIPTION "The E1 L2 Out of CAS Frame condition has cleared."
	::= 162

mcmAlarmE1L1OOCASFrame TRAP-TYPE
	ENTERPRISE	micom
	VARIABLES	{trapNodeName}
	DESCRIPTION "An Out of CAS Frame condition occurred on the Line 1 (L1)
				interface.  A Multiframe Alignment Signaling Loss indicates
				that the CAS signaling is no longer in sync,  This can be
				caused by a loss of framing, defective hardware, or improper
				generation of signaling information on time slot 16.  The
				EAM will set the 'Y' bit in time slot 16 of frame 0."
	::= 163

mcmAlarmE1L1OOCASFrameClear TRAP-TYPE
	ENTERPRISE	micom
	VARIABLES	{trapNodeName}
	DESCRIPTION "The E1 L1 Out of CAS Frame condition has cleared."
	::= 164

mcmAlarmE1L2TS16AISAlarm TRAP-TYPE
	ENTERPRISE	micom
	VARIABLES	{trapNodeName}
	DESCRIPTION "A Time Slot 16 (TS16) Alarm Indication Signal occurred on
				the Line 2 (L2) interface.  A byte containing all ones was
				received in Time Slot 16 for two consecutive frames during
				an Out of Signaling Multiframe Alignment."
	::= 165

mcmAlarmE1L2TS16AISAlarmClear TRAP-TYPE
	ENTERPRISE	micom
	VARIABLES	{trapNodeName}
	DESCRIPTION "The E1 Time Slot 16 Alarm Indication Signal condition on
				L2 has cleared."
	::= 166

mcmAlarmE1L1TS16AISAlarm TRAP-TYPE
	ENTERPRISE	micom
	VARIABLES	{trapNodeName}
	DESCRIPTION "A Time Slot 16 (TS16) Alarm Indication Signal occurred on
				the Line 1 (L1) interface.  A byte containing all ones was
				received in Time Slot 16 for two consecutive frames during
				an Out of Signaling Multiframe Alignment."
	::= 167

mcmAlarmE1L1TS16AISAlarmClear TRAP-TYPE
	ENTERPRISE	micom
	VARIABLES	{trapNodeName}
	DESCRIPTION "The E1 Time Slot 16 Alarm Indication Signal condition on
				L1 has cleared."
	::= 168

mcmAlarmE1L2RemoteYAlarm TRAP-TYPE
	ENTERPRISE	micom
	VARIABLES	{trapNodeName}
	DESCRIPTION "A Remote 'Y' Signaling Alarm condition has occurred on
				the Line 2 (L2) interface.  This is the result of the
				EAM setting the 'Y' bit in time slot 16 of frame 0.  The
				condition indicates the loss of signaling at the remote
				site."
	::= 169

mcmAlarmE1L2RemoteYAlarmClear TRAP-TYPE
	ENTERPRISE	micom
	VARIABLES	{trapNodeName}
	DESCRIPTION "The E1 Remote 'Y' Signaling Alarm condition on the L2
				interface has cleared."
	::= 170

mcmAlarmE1L1RemoteYAlarm TRAP-TYPE
	ENTERPRISE	micom
	VARIABLES	{trapNodeName}
	DESCRIPTION "A Remote 'Y' Signaling Alarm condition has occurred on
				the Line 1 (L1) interface.  This is the result of the
				EAM setting the 'Y' bit in time slot 16 of frame 0.  The
				condition indicates the loss of signaling at the remote
				site."
	::= 171

mcmAlarmE1L1RemoteYAlarmClear TRAP-TYPE
	ENTERPRISE	micom
	VARIABLES	{trapNodeName}
	DESCRIPTION "The E1 Remote 'Y' Signaling Alarm condition on the L1
				interface has cleared."
	::= 172

mcmAlarmE1L2RemoteAAlarm TRAP-TYPE
	ENTERPRISE	micom
	VARIABLES	{trapNodeName}
	DESCRIPTION "A Remote 'A' Signaling Alarm condition has occurred on
				the Line 2 (L2) interface.  This Frame Alignment Signaling
				condition occurs when the 'A' bit, received in Bit 3 of
				Time Slot 0 of the Non Frame Alignment Signal (NFAS), is
				detected.  The alarm indicates that the receiver at the
				remote is not detecting valid information; which could
				be the result of a loss of signal, loss of frame
				synchronization, or high-bit errors."
	::= 173

mcmAlarmE1L2RemoteAAlarmClear TRAP-TYPE
	ENTERPRISE	micom
	VARIABLES	{trapNodeName}
	DESCRIPTION "The E1 Remote 'A' Signaling Alarm condition on the L2
				interface has cleared."
	::= 174

mcmAlarmE1L1RemoteAAlarm TRAP-TYPE
	ENTERPRISE	micom
	VARIABLES	{trapNodeName}
	DESCRIPTION "A Remote 'A' Signaling Alarm condition has occurred on
				the Line 1 (L1) interface.  This Frame Alignment Signaling
				condition occurs when the 'A' bit, received in Bit 3 of
				Time Slot 0 of the Non Frame Alignment Signal (NFAS), is
				detected.  The alarm indicates that the receiver at the
				remote is not detecting valid information; which could
				be the result of a loss of signal, loss of frame
				synchronization, or high-bit errors."
	::= 175

mcmAlarmE1L1RemoteAAlarmClear TRAP-TYPE
	ENTERPRISE	micom
	VARIABLES	{trapNodeName}
	DESCRIPTION "The E1 Remote 'A' Signaling Alarm condition on the L1
				interface has cleared."
	::= 176

mcmProxyAlarmNodeUnreachable TRAP-TYPE
	ENTERPRISE	micom
	VARIABLES	{trapNodeName}
	DESCRIPTION "The proxy agent's event polling application could not reach 
				the intended node."
	::= 500


-- Proxy Object Group

pxyVersionNumber OBJECT-TYPE
	SYNTAX	DisplayString
	ACCESS	read-only
	STATUS	mandatory
	DESCRIPTION	"Identifies the version number of the proxy agent installed." 
	 ::= { proxy 1}

pxyCfgProxySwitch OBJECT-TYPE
	SYNTAX	INTEGER {
		enable (1),
		disable (2)
		}
	ACCESS	read-write
	STATUS	mandatory
	DESCRIPTION	"To enable or disable the proxy agent operation on the
			router module." 
	 ::= {proxy 2}

pxyAddressMapTableNumber OBJECT-TYPE
	SYNTAX	INTEGER
	ACCESS	read-only
	STATUS	mandatory
	DESCRIPTION	"The number of entries in the address map table. This will give 
			 the highest numbered entry allocated."
	::= {proxy 3}

pxyAddressMapTable OBJECT-TYPE
	SYNTAX	SEQUENCE OF PxyAddressMapEntry
	ACCESS	not-accessible
	STATUS	mandatory
	DESCRIPTION	"A table of all the MICOM Nodes this proxy is responsible for."
	::= {proxy 4}

pxyAddressMapEntry OBJECT-TYPE
	SYNTAX	PxyAddressMapEntry
	ACCESS	not-accessible
	STATUS	mandatory
	DESCRIPTION	"An entry that describes the network node which this proxy
			agent manages."
	INDEX		{ pxyAddressMapNodeNumber }
	::= {pxyAddressMapTable 1}

PxyAddressMapEntry ::= SEQUENCE {
	pxyAddressMapNodeNumber		INTEGER,
	pxyAddressMapEntryStatus		INTEGER,
	pxyAddressMapNodeNameAndCommunity	DisplayString,
	pxyAddressMapChangeNodeNumberTo	INTEGER
	}

pxyAddressMapNodeNumber OBJECT-TYPE
	SYNTAX	INTEGER 
	ACCESS	read-only
	STATUS	mandatory
	DESCRIPTION	"The node number used to communicate with the device associated 
			 with this entry."
	::= {pxyAddressMapEntry 1}

pxyAddressMapEntryStatus OBJECT-TYPE
	SYNTAX	INTEGER {
		active (1),
		notInService (2),
		notReady (3),
		createAndGo (4),
		createAndWait (5),
		destroy (6)
		}
	ACCESS	read-write
	STATUS	mandatory
	DESCRIPTION	"A code representing the current state of  the table entry. This is 
			provided to define relationship within the table entry and to delete 
			and/or add devics to the Address Table. Default is notReady "
	::= {pxyAddressMapEntry 2}


pxyAddressMapNodeNameAndCommunity OBJECT-TYPE
	SYNTAX	DisplayString  (SIZE (1..8))
	ACCESS	read-write
	STATUS	mandatory
	DESCRIPTION	"The node name used to communicate with the device associated with
			 this entry. This unique name is also used to de-multiplex the proxy 
			managed nodes."
	::= {pxyAddressMapEntry 3}

pxyAddressMapChangeNodeNumberTo OBJECT-TYPE
	SYNTAX	INTEGER 
	ACCESS	write-only
	STATUS	mandatory
	DESCRIPTION	"In order to change a node number of an existing node you must
			use this entry with the NodeNumber entry being the existing node
			number."
	::= {pxyAddressMapEntry 4}




pxySupportedVersionTable OBJECT-TYPE
	SYNTAX	SEQUENCE OF PxySupportedVersionEntry
	ACCESS	not-accessible
	STATUS	mandatory
	DESCRIPTION	"A table of sotware revision numbers this proxy agent support."
	::= { proxy 5}

pxySupportedVersionEntry OBJECT-TYPE
	SYNTAX	PxySupportedVersionEntry
	ACCESS	not-accessible
	STATUS	mandatory
	DESCRIPTION	"An entry that describes the version number of the software this 
			proxy agent supports."
	INDEX		{pxySupportedIndex}
	::= {pxySupportedVersionTable 1}

PxySupportedVersionEntry ::= SEQUENCE {
	pxySupportedIndex			INTEGER,
	pxySupportedVersionNumber 		INTEGER 
	}

pxySupportedIndex OBJECT-TYPE
	SYNTAX	INTEGER
	ACCESS	read-only
	STATUS	mandatory
	DESCRIPTION	"Identifies the instance and hence the row of the entry in this table."
	 ::= { pxySupportedVersionEntry 1}

pxySupportedVersionNumber OBJECT-TYPE
	SYNTAX	INTEGER {
		phase5dot0 (1),
		phase5dot0plus (2)
		}
	ACCESS	read-only
	STATUS	mandatory
	DESCRIPTION	"Identifies the Node Software Version number this proxy agent
			understands and supports."
	 ::= { pxySupportedVersionEntry 2}



-- Proxy Statistics Object Group
-- This group maintains statistics of the different operational and exceptional conditions occurred 
-- while communicating to the managed nodes. All the statistics are maintained since the last reboot 
-- of the system

pxyStatisticsLastNodeServed OBJECT-TYPE
	SYNTAX	INTEGER
	ACCESS	read-only
	STATUS	mandatory
	DESCRIPTION	"Represent the last successul transaction between this proxy
			agent and the foreign node."
	::= { proxy 6}

pxyStatisticsLastErrorNode OBJECT-TYPE
	SYNTAX	INTEGER
	ACCESS	read-only
	STATUS	mandatory
	DESCRIPTION	"Represent the last un-successful transaction of this proxy agent
			and the foreign node."
	::= { proxy 7}

pxyStatisticsLastSNMPError OBJECT-TYPE
	SYNTAX	INTEGER
	ACCESS	read-only
	STATUS	mandatory
	DESCRIPTION	"The SNMP error from the last transaction of this proxy agent with
			the node referenced by pxyStatisticsLastErrorNode."
	::= {proxy 8}

pxyStatisticsLastErrorReturnCode OBJECT-TYPE
	SYNTAX	INTEGER
	ACCESS	read-only
	STATUS	mandatory
	DESCRIPTION	"The specific error code from the last transaction of this proxy 
			agent with the node referenced by pxyStatisticsLastErrorNode."
	::= {proxy 9}

pxyStatisticsTotalRequests OBJECT-TYPE
	SYNTAX	Counter
	ACCESS	read-only
	STATUS	mandatory
	DESCRIPTION	"A count of requests received since the last reboot of the system."
	::= { proxy 10}

pxyStatisticsTotalInternalTraps OBJECT-TYPE
	SYNTAX	Counter
	ACCESS	read-only
	STATUS	mandatory
	DESCRIPTION	"A count of internal Traps transmitted since the last reboot of 
			the system."
	::= { proxy 11}


-- Proxy PPP Object Group
-- This group maintains the statistics for PPP protocol operations.

pxyPPPTotalCounts OBJECT-TYPE
	SYNTAX	Counter
	ACCESS	read-only
	STATUS	mandatory
	DESCRIPTION	"A count of translated PPP requests transmitted to the managed nodes 
			since last reboot of the system."
	::= {proxy 12}

pxyPPPRejectCounts OBJECT-TYPE
	SYNTAX	Counter
	ACCESS	read-only
	STATUS	mandatory
	DESCRIPTION	"A count of rejected PPP requests transmitted to the managed nodes 
			since last reboot of the system."
	::= {proxy 13}

pxyCacheUpdate OBJECT-TYPE
	SYNTAX	INTEGER {
		cdChanTable (1)
		}
	ACCESS	write-only
	STATUS	mandatory
	DESCRIPTION	"Configures to force update the cached information maintained
			in proxy agent." 
	 ::= { proxy 14}


pxyNetworkAccessNodeName OBJECT-TYPE
	SYNTAX	DisplayString  (SIZE (1..8))
	ACCESS	read-write
	STATUS	mandatory
	DESCRIPTION	"This is the name of the Integration unit that the
			proxy is physically attached to.  This node must already be
			in the proxy's Address Map in order to set it here.  This
			NodeName is stored in the FileControlFile.Data file on the
			host that the proxy is installed on."
	::= { proxy 15 }


-- Control Group

-- N_HOUSE.O_RESET ========================================================

nodeResetGroup OBJECT IDENTIFIER ::= {control 1}

nodeResetCode OBJECT-TYPE
	SYNTAX	INTEGER {
		coldRestart (1),
		warmRestart (2)
		}
	ACCESS	write-only
	STATUS	mandatory
	DESCRIPTION	"Resets the local node and configures to restart with the factory
			default values or retain the current configuration; all channels 
			connected locally are also reset." 
	 ::= {nodeResetGroup 1}

nodeResetType OBJECT-TYPE
	SYNTAX	INTEGER {
		restartCurrentSoftware (1),
		reloadSoftwareFromFlash (2)
		}
	ACCESS	write-only
	STATUS	mandatory
	DESCRIPTION	"Configures to retstart with the current operational code or restart
			and load the image from the flash." 
	 ::= {nodeResetGroup 2}


-- N_HOUSE.O_ASYNC ========================================================

asyncResetTable OBJECT-TYPE
	SYNTAX	SEQUENCE OF AsyncResetEntry
	ACCESS	not-accessible
	STATUS	mandatory
	DESCRIPTION	"Table to reset an async channel." 
	::= { control 2}

asyncResetEntry OBJECT-TYPE
	SYNTAX	AsyncResetEntry
	ACCESS	not-accessible
	STATUS	mandatory
	DESCRIPTION	"Entry within the table specifying particular channel on 
			specific module/card." 
	INDEX		{asyncResetCardNumber, asyncResetChannelNumber}
	::= {asyncResetTable 1}

AsyncResetEntry ::= SEQUENCE {
	asyncResetCardNumber		INTEGER,
	asyncResetChannelNumber	INTEGER,
	asyncResetCommand		INTEGER
	}

asyncResetCardNumber OBJECT-TYPE
	SYNTAX	INTEGER (1..5)
	ACCESS	read-only
	STATUS	mandatory
	DESCRIPTION	"Indicates the card/module number of the channel to be reset." 
	 ::= {asyncResetEntry 1}

asyncResetChannelNumber OBJECT-TYPE
	SYNTAX	INTEGER (1..6)
	ACCESS	read-only
	STATUS	mandatory
	DESCRIPTION	"Identifies the channel number to be reset." 
	 ::= {asyncResetEntry 2}

asyncResetCommand OBJECT-TYPE
	SYNTAX	INTEGER {
		resetChannel (1)
		}
	ACCESS	write-only
	STATUS	mandatory
	DESCRIPTION	"Triggers the reset operation." 
	 ::= {asyncResetEntry 3}

-- N_HOUSE.O_SYNC ========================================================

syncResetTable OBJECT-TYPE
	SYNTAX	SEQUENCE OF SyncResetEntry
	ACCESS	not-accessible
	STATUS	mandatory
	DESCRIPTION	"Table to reset a sync channel." 
	::= { control 3}

syncResetEntry OBJECT-TYPE
	SYNTAX	SyncResetEntry
	ACCESS	not-accessible
	STATUS	mandatory
	DESCRIPTION	"Entry within the table specifying particular channel on 
			specific module/card." 
	INDEX		{syncResetCardNumber, syncResetChannelNumber}
	::= {syncResetTable 1}

SyncResetEntry ::= SEQUENCE {
	syncResetCardNumber		INTEGER,
	syncResetChannelNumber		INTEGER,
	syncResetCommand		INTEGER
	}

syncResetCardNumber OBJECT-TYPE
	SYNTAX	INTEGER (1..5)
	ACCESS	read-only
	STATUS	mandatory
	DESCRIPTION	"Indicates the card/module number of the channel to be reset." 
	 ::= {syncResetEntry 1}

syncResetChannelNumber OBJECT-TYPE
	SYNTAX	INTEGER (1..6)
	ACCESS	read-only
	STATUS	mandatory
	DESCRIPTION	"Identifies the channel number to be reset." 
	 ::= {syncResetEntry 2}

syncResetCommand OBJECT-TYPE
	SYNTAX	INTEGER {
		resetChannel (1)
		}
	ACCESS	write-only
	STATUS	mandatory
	DESCRIPTION	"Triggers the reset operation." 
	 ::= {syncResetEntry 3}


-- N_HOUSE.O_VOICE ========================================================

voiceResetTable OBJECT-TYPE
	SYNTAX	SEQUENCE OF VoiceResetEntry
	ACCESS	not-accessible
	STATUS	mandatory
	DESCRIPTION	"Table to reset a voice channel." 
	::= { control 4}

voiceResetEntry OBJECT-TYPE
	SYNTAX	VoiceResetEntry
	ACCESS	not-accessible
	STATUS	mandatory
	DESCRIPTION	"Entry within the table specifying particular channel on 
			specific module/card." 
	INDEX		{voiceResetCardNumber, voiceResetChannelNumber}
	::= {voiceResetTable 1}

VoiceResetEntry ::= SEQUENCE {
	voiceResetCardNumber		INTEGER,
	voiceResetChannelNumber	INTEGER,
	voiceResetCommand		INTEGER
	}

voiceResetCardNumber OBJECT-TYPE
	SYNTAX	INTEGER (2..5)
	ACCESS	read-only
	STATUS	mandatory
	DESCRIPTION	"Indicates the card/module number of the channel to be reset." 
	 ::= {voiceResetEntry 1}

voiceResetChannelNumber OBJECT-TYPE
	SYNTAX	INTEGER
	ACCESS	read-only
	STATUS	mandatory
	DESCRIPTION	"Identifies the channel number to be reset." 
	 ::= {voiceResetEntry 2}

voiceResetCommand OBJECT-TYPE
	SYNTAX	INTEGER {
		resetVoiceChannel  (1)
		}
	ACCESS	write-only
	STATUS	mandatory
	DESCRIPTION	"Triggers the reset operation." 
	 ::= {voiceResetEntry 3}

-- N_HOUSE.O_LNKCH ========================================================

linkResetTable OBJECT-TYPE
	SYNTAX	SEQUENCE OF LinkResetEntry
	ACCESS	not-accessible
	STATUS	mandatory
	DESCRIPTION	"Table to reset the links. Resetting a link clears all information
			on the selected link." 
	::= { control 5}

linkResetEntry OBJECT-TYPE
	SYNTAX	LinkResetEntry
	ACCESS	not-accessible
	STATUS	mandatory
	DESCRIPTION	"Entry within the table for a specifying a particular link." 
	INDEX		{linkResetCardNumber, linkResetChannelNumber}
	::= {linkResetTable 1}

LinkResetEntry ::= SEQUENCE {
	linkResetCardNumber		INTEGER,
	linkResetChannelNumber		INTEGER,
	linkResetCommand		INTEGER
	}

linkResetCardNumber OBJECT-TYPE
	SYNTAX	INTEGER (1..5)
	ACCESS	read-only
	STATUS	mandatory
	DESCRIPTION	"Indicates the card/module number of the link to be reset." 
	 ::= {linkResetEntry 1}

linkResetChannelNumber OBJECT-TYPE
	SYNTAX	INTEGER (1..6)
	ACCESS	read-only
	STATUS	mandatory
	DESCRIPTION	"Identifies the link/channel number to be reset." 
	 ::= {linkResetEntry 2}

linkResetCommand OBJECT-TYPE
	SYNTAX	INTEGER {
		resetLink  (1)
		}
	ACCESS	write-only
	STATUS	mandatory
	DESCRIPTION	"Triggers the reset operation." 
	 ::= {linkResetEntry 3}


-- N_HOUSE.O_ALARM =======================================================

clearLatchedAlarms OBJECT-TYPE
	SYNTAX	INTEGER {
		clearLatchedAlarms (1)
		}
	ACCESS	write-only
	STATUS	mandatory
	DESCRIPTION	"Clears the latched alarm messages on the local node." 
	::= {control 6}


-- N_HOUSE.O_PPPLNK =======================================================

pppLinkOperationGroup OBJECT IDENTIFIER ::= {control 7}

-- Note that the PPP Link Operation Group objects are used when debugging $PPP link operations.
--    These parameters should not normally be modified by the end user. 

pppLinkOperationAction OBJECT-TYPE
	SYNTAX	INTEGER {
		resumeNormalOperation (1)
		}
	ACCESS	write-only
	STATUS	mandatory
	DESCRIPTION	"Command to resume normal operation of the $PPP link.
			(Used for $PPP link debugging purposes.)" 
	 ::= { pppLinkOperationGroup 1}

pppLinkTimeOutAction OBJECT-TYPE
	SYNTAX	INTEGER {
		disableLinkTimeout (1)
		}
	ACCESS	write-only
	STATUS	mandatory
	DESCRIPTION	"Command to disable the link timeout feature of the $PPP link.
			(Used for $PPP link debugging purposes.)" 
	 ::= { pppLinkOperationGroup 2}

pppLinkDumpAction OBJECT-TYPE
	SYNTAX	INTEGER {
		dumpRejectedNmsCmdToLogport (1)
		}
	ACCESS	write-only
	STATUS	mandatory
	DESCRIPTION	"Command to route rejected NMS commands to the log port for output.
			(Used for $PPP link debugging purposes.)" 
	 ::= { pppLinkOperationGroup 3}

-- N_HOUSE.O_FLASH =======================================================

flashEPROMCommand OBJECT-TYPE
	SYNTAX	INTEGER {
		eraseBothBanks (1),
		eraseBankOne (2),
		eraseBankTwo (3)
		}
	ACCESS	write-only
	STATUS	mandatory
	DESCRIPTION	"Command to erase flash memory on the CCM." 
	 ::= { control 8}

-- N_HOUSE.O_VFLASH =======================================================

voiceFlashEPROMTable OBJECT-TYPE
	SYNTAX	SEQUENCE OF VoiceFlashEPROMEntry
	ACCESS	not-accessible
	STATUS	mandatory
	DESCRIPTION	"Table to erase flash memory of voice modules." 
	::= { control 9}

voiceFlashEPROMEntry OBJECT-TYPE
	SYNTAX	VoiceFlashEPROMEntry
	ACCESS	not-accessible
	STATUS	mandatory
	DESCRIPTION	"Entry within the table specific to a particular voice channel
			on a particular module/card for erasing flash memory." 
	INDEX		{voiceFlashEPROMCardNumber, voiceFlashEPROMChannelNumber}
	::= {voiceFlashEPROMTable 1}

VoiceFlashEPROMEntry ::= SEQUENCE {
	voiceFlashEPROMCardNumber		INTEGER,
	voiceFlashEPROMChannelNumber	INTEGER,
	voiceFlashEPROMCommand		INTEGER
	}

voiceFlashEPROMCardNumber OBJECT-TYPE
	SYNTAX	INTEGER (2..5)
	ACCESS	read-only
	STATUS	mandatory
	DESCRIPTION	"Identifies the card number of the voice module
			for erasing the flash memory." 
	 ::= { voiceFlashEPROMEntry 1}

voiceFlashEPROMChannelNumber OBJECT-TYPE
	SYNTAX	INTEGER (1..6)
	ACCESS	read-only
	STATUS	mandatory
	DESCRIPTION	"Identifies the channel number of the voice module
			for erasing the flash memory." 
	 ::= { voiceFlashEPROMEntry 2}

voiceFlashEPROMCommand OBJECT-TYPE
	SYNTAX	INTEGER {
		eraseFlash (1)
		}
	ACCESS	write-only
	STATUS	mandatory
	DESCRIPTION	"Command to erase the flash memory of a particular voice
			channel module." 
	 ::= { voiceFlashEPROMEntry 3}


-- N_HOUSE.O_LANTYP =======================================================

lanCardResetTable OBJECT-TYPE
	SYNTAX	SEQUENCE OF LanCardResetEntry
	ACCESS	not-accessible
	STATUS	mandatory
	DESCRIPTION	"Table to reset the integral LAN module." 
	::= {control 10}

lanCardResetEntry OBJECT-TYPE
	SYNTAX	LanCardResetEntry
	ACCESS	not-accessible
	STATUS	mandatory
	DESCRIPTION	"Entry within the table to specify a particular card/module to
			be reset." 
	INDEX		{lanCardResetCardNumber}
	::= {lanCardResetTable 1}

LanCardResetEntry ::= SEQUENCE {
	lanCardResetCardNumber		INTEGER,
	lanCardResetType		INTEGER
	}

lanCardResetCardNumber	 OBJECT-TYPE
	SYNTAX	INTEGER (2..5)
	ACCESS	read-only
	STATUS	mandatory
	DESCRIPTION	"Identifies the module number to be reset." 
	 ::= { lanCardResetEntry 1}

lanCardResetType OBJECT-TYPE
	SYNTAX	INTEGER {
		resetWithCurrentValues (1),
		resetWithDefaultValues (2),
		wanToLanDownload (3),
		lanToLanDownload (4)
		}
	ACCESS	write-only
	STATUS	mandatory
	DESCRIPTION	"Commands a specific type of reset for the integral Lan module." 
	 ::= {lanCardResetEntry 2}

-- N_CMOS.O_CHCNST ========================================================

chControlTable OBJECT-TYPE
	SYNTAX	SEQUENCE OF ChControlEntry
	ACCESS	not-accessible
	STATUS	mandatory
	DESCRIPTION	"Table controls the operating condition (status) of the channels
			in the system." 
	::= {control 11}

chControlEntry OBJECT-TYPE
	SYNTAX	ChControlEntry
	ACCESS	not-accessible
	STATUS	mandatory
	DESCRIPTION	"Entry within the table specific to a particular channel on 
			specific module/card." 
	INDEX		{chControlCardNumber, chControlChannelNumber}
	::= {chControlTable 1}

ChControlEntry ::= SEQUENCE {
	chControlCardNumber		INTEGER,
	chControlChannelNumber		INTEGER,
	chControlCommand		INTEGER,
	chControlForceConnToNodeName	DisplayString,
	chControlForceConnToCard	INTEGER,
	chControlForceConnToChannel	INTEGER
	}

chControlCardNumber OBJECT-TYPE
	SYNTAX	INTEGER (1..5)
	ACCESS	read-only
	STATUS	mandatory
	DESCRIPTION	"Identifies the card/module number of channel to be configured." 
	::= {chControlEntry 1}

chControlChannelNumber OBJECT-TYPE
	SYNTAX	INTEGER
	ACCESS	read-only
	STATUS	mandatory
	DESCRIPTION	"Identifies the channel number to be configured." 
	::= {chControlEntry 2}

chControlCommand OBJECT-TYPE
	SYNTAX	INTEGER {
		enable (1),
		disable (2),
		forcedConnect (3),
		forcedDisconnect (4)
		}
	ACCESS	write-only
	STATUS	mandatory
	DESCRIPTION	"Object triggers the specified status action valid on the 
			channels. Option 1 returns a out-of-service async or voice/fax
			port to the idle state. The option 2 permits to take an async or
			voice/fax channel from idle state to out-of-service. Option 3
			causes two selected (idle or out-of-service) ports to be connected.
			The ports must be of like kind.  An attempt to SET this Option
			without first SET'ing the other required information
			(chControlForceConnToNodeName, chControlForceConnToCard,
			and chControlForceConnToChannel) will return an error." 
	::= {chControlEntry 3}

chControlForceConnToNodeName OBJECT-TYPE
	SYNTAX	DisplayString (SIZE(1..8))
	ACCESS	write-only
	STATUS	mandatory
	DESCRIPTION	"The node number of the other end of the channel to be 
			connected." 
	::= {chControlEntry 4}

chControlForceConnToCard OBJECT-TYPE
	SYNTAX	INTEGER (1..5)
	ACCESS	write-only
	STATUS	mandatory
	DESCRIPTION	"The module/card number of the other end of the channel 
			to be connected." 
	::= {chControlEntry 5}

chControlForceConnToChannel OBJECT-TYPE
	SYNTAX	INTEGER
	ACCESS	write-only
	STATUS	mandatory
	DESCRIPTION	"The channel number of the other end of the channel to be 
			connected." 
	::= {chControlEntry 6}


frameRelayDLCIResetTable OBJECT-TYPE
	SYNTAX	SEQUENCE OF FrameRelayDLCIResetEntry
	ACCESS	not-accessible
	STATUS	mandatory
	DESCRIPTION	"Table to reset the frame relay DLCI." 
	::= { control 12}

frameRelayDLCIResetEntry OBJECT-TYPE
	SYNTAX	FrameRelayDLCIResetEntry
	ACCESS	not-accessible
	STATUS	mandatory
	DESCRIPTION	"Entry within the table to specifying a particular DLCI on a
			specific module and specific channel." 
	INDEX		{frameRelayDLCIResetCardNumber, frameRelayDLCIResetChannelNumber}
	::= {frameRelayDLCIResetTable 1}

FrameRelayDLCIResetEntry ::= SEQUENCE {
	frameRelayDLCIResetCardNumber	INTEGER,
	frameRelayDLCIResetChannelNumber	INTEGER,
	frameRelayDLCIResetDLCINumber	INTEGER
	}

frameRelayDLCIResetCardNumber OBJECT-TYPE
	SYNTAX	INTEGER (1..5)
	ACCESS	read-only
	STATUS	mandatory
	DESCRIPTION	"Identifies the card/module for the channel and associated DLCI." 
	 ::= {frameRelayDLCIResetEntry 1}

frameRelayDLCIResetChannelNumber OBJECT-TYPE
	SYNTAX	INTEGER (1..6)
	ACCESS	read-only
	STATUS	mandatory
	DESCRIPTION	"Identifies the channel number for the DLCI to be reset." 
	 ::= {frameRelayDLCIResetEntry 2}

frameRelayDLCIResetDLCINumber OBJECT-TYPE
	SYNTAX	INTEGER 
	ACCESS	write-only
	STATUS	mandatory
	DESCRIPTION	"This write-only object signfies the DLCI which is intended to 
			be reset. The card number and the channel number objects 
			identifies the proper instance of the particular link" 
	 ::= {frameRelayDLCIResetEntry 3}


frameRelayAllDLCIResetTable OBJECT-TYPE
	SYNTAX	SEQUENCE OF FrameRelayAllDLCIResetEntry
	ACCESS	not-accessible
	STATUS	mandatory
	DESCRIPTION	"Table to reset all the configured DLCI on a particular frame 
			relay link." 
	::= { control 13}

frameRelayAllDLCIResetEntry OBJECT-TYPE
	SYNTAX	FrameRelayAllDLCIResetEntry
	ACCESS	not-accessible
	STATUS	mandatory
	DESCRIPTION	"Entry within the table specifying a particular channel/link." 
	INDEX	 	{frameRelayAllDLCIResetCardNumber, 
			frameRelayAllDLCIResetChannelNumber}
	::= {frameRelayAllDLCIResetTable 1}

FrameRelayAllDLCIResetEntry ::= SEQUENCE {
	frameRelayAllDLCIResetCardNumber	INTEGER,
	frameRelayAllDLCIResetChannelNumber	INTEGER,
	frameRelayAllDLCIResetCommand	INTEGER
	}

frameRelayAllDLCIResetCardNumber OBJECT-TYPE
	SYNTAX	INTEGER (1..5)
	ACCESS	read-only
	STATUS	mandatory
	DESCRIPTION	"Identifies the card/module for all the DLCIs to be reset." 
	 ::= {frameRelayAllDLCIResetEntry 1}

frameRelayAllDLCIResetChannelNumber OBJECT-TYPE
	SYNTAX	INTEGER (1..6)
	ACCESS	read-only
	STATUS	mandatory
	DESCRIPTION	"Identifies the channel/link for all the DLCIs to be reset." 
	 ::= {frameRelayAllDLCIResetEntry 2}

frameRelayAllDLCIResetCommand OBJECT-TYPE
	SYNTAX	INTEGER {
		resetAllDLCI (1)
		}
	ACCESS	write-only
	STATUS	mandatory
	DESCRIPTION	"Resets all the configured DLCI on a specific link/channel." 
	 ::= {frameRelayAllDLCIResetEntry 3}


-- N_HOUSE.O_T1RST ===================================================

t1e1CardResetTable OBJECT-TYPE
	SYNTAX	SEQUENCE OF T1e1CardResetEntry
	ACCESS	not-accessible
	STATUS	mandatory
	DESCRIPTION	"Table to reset the T1/E1 module." 
	::= { control 14}

t1e1CardResetEntry OBJECT-TYPE
	SYNTAX	T1e1CardResetEntry 
	ACCESS	not-accessible
	STATUS	mandatory
	DESCRIPTION	"Entry within the table specifying particular T1/E1 modle." 
	INDEX	 	{ t1e1CardResetCardNumber }
	::= { t1e1CardResetTable 1}

T1e1CardResetEntry ::= SEQUENCE {
	t1e1CardResetCardNumber	INTEGER,
	t1e1CardResetCommand		INTEGER
	}

t1e1CardResetCardNumber OBJECT-TYPE
	SYNTAX	INTEGER (2..5)
	ACCESS	read-only
	STATUS	mandatory
	DESCRIPTION	"Identifies the card/module number to be reset." 
	::= { t1e1CardResetEntry 1}

t1e1CardResetCommand OBJECT-TYPE
	SYNTAX	INTEGER {
		warmReset (1),
		coldReset (2)
		}
	ACCESS	write-only
	STATUS	mandatory
	DESCRIPTION	"Resets the module to either the current configuration (option 1)
			or factory default values (option 2) ." 
	::= { t1e1CardResetEntry 2}

-- N_HOUSE.O_NVFLSH ====================================================

nvflashUpdate OBJECT-TYPE
	SYNTAX	INTEGER {
		writeToFlash (1)
		}
	ACCESS	write-only
	STATUS	mandatory
	DESCRIPTION	"This object is for platforms which use flash instead of CMOS for
			configuration storage. These platforms update the configuration in
			flash on a periodic basis rather than after each change. This object
			will force an immediate configuration storage update." 
	::= { control 15}


-- Status Group

-- N_STATUS.O_CDCHAN ===================================================

portTypeStatusTable OBJECT-TYPE
	SYNTAX	SEQUENCE OF PortTypeStatusEntry
	ACCESS	not-accessible
	STATUS	mandatory
	DESCRIPTION	"Identifies the type of all the channels/ports/links on a node." 
	::= {status 1}

portTypeStatusEntry OBJECT-TYPE
	SYNTAX	PortTypeStatusEntry
	ACCESS	not-accessible
	STATUS	mandatory
	DESCRIPTION	"Entry within the table specifying a particular channel." 
	INDEX		{portTypeStatusCardNumber, portTypeStatusChannelNumber }
	::= {portTypeStatusTable 1}

PortTypeStatusEntry ::= SEQUENCE {
	portTypeStatusCardNumber		INTEGER,
	portTypeStatusChannelNumber 		INTEGER,
	portTypeStatusChannelType 		INTEGER
	}

portTypeStatusCardNumber OBJECT-TYPE
	SYNTAX	INTEGER
	ACCESS	read-only
	STATUS	mandatory
	DESCRIPTION	"Identifies the card/module number of the intended channel." 
	::= {portTypeStatusEntry 1}

portTypeStatusChannelNumber OBJECT-TYPE
	SYNTAX	INTEGER
	ACCESS	read-only
	STATUS	mandatory
	DESCRIPTION	"Identifies the channel number." 
	::= {portTypeStatusEntry 2}

portTypeStatusChannelType OBJECT-TYPE
	SYNTAX	INTEGER {
		mux (1),
		async (2),
		sync (3),
		voice (4),
		esi (5),
		badChannel (6),
		x21 (7),
		localEsi (8),
		esiSecondary (9),
		frameRelay (10),
		disabledViaConfig (11),
		digitalVoice (12)
		}
	ACCESS	read-only
	STATUS	mandatory
	DESCRIPTION	"Identifies the channel/port/link type of the specified channel." 
	::= {portTypeStatusEntry 3}

-- N_STATUS.O_ASYNC ========================================================

asyncChStatusTable OBJECT-TYPE
	SYNTAX	SEQUENCE OF AsyncChStatusEntry
	ACCESS	not-accessible
	STATUS	mandatory
	DESCRIPTION	"Table of EIA status for async channels." 
	 ::= {status 2}

asyncChStatusEntry OBJECT-TYPE
	SYNTAX	AsyncChStatusEntry
	ACCESS	not-accessible
	STATUS	mandatory
	DESCRIPTION	"Entry within the table specific to a particular async channel
			on a module/card for EIA status." 
	INDEX		{asyncChStatusCardNumber, asyncChStatusChannelNumber}
	 ::= {asyncChStatusTable 1}

AsyncChStatusEntry ::= SEQUENCE {
	asyncChStatusCardNumber		INTEGER,
	asyncChStatusChannelNumber		INTEGER,
	asyncChStatusEiaInputsRTSStatus		INTEGER,
	asyncChStatusEiaInputsDTRStatus		INTEGER,
	asyncChStatusEiaInputsUAStatus		INTEGER,
	asyncChStatusEiaInputsBUSYStatus	INTEGER,
	asyncChStatusEiaOutputsRIStatus		INTEGER,
	asyncChStatusEiaOutputsRLSDStatus	INTEGER,
	asyncChStatusEiaOutputsCTSStatus	INTEGER,
	asyncChStatusEiaOutputsDSRStatus	INTEGER
	}

asyncChStatusCardNumber OBJECT-TYPE
	SYNTAX	INTEGER (1..5)
	ACCESS	read-only
	STATUS	mandatory
	DESCRIPTION	"Identifies the module/card number for EIA status of the async 
			channel." 
	 ::= {asyncChStatusEntry 1}

asyncChStatusChannelNumber OBJECT-TYPE
	SYNTAX	INTEGER (1..32)
	ACCESS	read-only
	STATUS	mandatory
	DESCRIPTION	"Identifies the async channel for EIA status." 
	 ::= {asyncChStatusEntry 2}

asyncChStatusEiaInputsRTSStatus OBJECT-TYPE
	SYNTAX	INTEGER {
		on (1),
		off (2)
		}
	ACCESS	read-only
	STATUS	mandatory
	DESCRIPTION	"Indicates the async channel EIA input status of the RTS signal." 
	 ::= {asyncChStatusEntry 3}

asyncChStatusEiaInputsDTRStatus OBJECT-TYPE
	SYNTAX	INTEGER {
		on (1),
		off (2)
		}
	ACCESS	read-only
	STATUS	mandatory
	DESCRIPTION	"Indicates the async channel EIA input status of the DTR signal." 
	 ::= {asyncChStatusEntry 4}

asyncChStatusEiaInputsUAStatus OBJECT-TYPE
	SYNTAX	INTEGER {
		on (1),
		off (2)
		}
	ACCESS	read-only
	STATUS	mandatory
	DESCRIPTION	"Indicates the async channel EIA input status of the UA signal." 
	 ::= {asyncChStatusEntry 5}

asyncChStatusEiaInputsBUSYStatus OBJECT-TYPE
	SYNTAX	INTEGER {
		on (1),
		off (2)
		}
	ACCESS	read-only
	STATUS	mandatory
	DESCRIPTION	"Indicates the async channel EIA input status of the Busy signal." 
	 ::= {asyncChStatusEntry 6}

asyncChStatusEiaOutputsRIStatus OBJECT-TYPE
	SYNTAX	INTEGER {
		on (1),
		off (2)
		}
	ACCESS	read-only
	STATUS	mandatory
	DESCRIPTION	"Indicates the async channel EIA output status of the RI signal." 
	 ::= {asyncChStatusEntry 7}

asyncChStatusEiaOutputsRLSDStatus OBJECT-TYPE
	SYNTAX	INTEGER {
		on (1),
		off (2)
		}
	ACCESS	read-only
	STATUS	mandatory
	DESCRIPTION	"Indicates the async channel EIA output status of the RLSD signal." 
	 ::= {asyncChStatusEntry 8}

asyncChStatusEiaOutputsCTSStatus OBJECT-TYPE
	SYNTAX	INTEGER {
		on (1),
		off (2)
		}
	ACCESS	read-only
	STATUS	mandatory
	DESCRIPTION	"Indicates the async channel EIA output status of the CTS signal." 
	 ::= {asyncChStatusEntry 9}

asyncChStatusEiaOutputsDSRStatus OBJECT-TYPE
	SYNTAX	INTEGER {
		on (1),
		off (2)
		}
	ACCESS	read-only
	STATUS	mandatory
	DESCRIPTION	"Indicates the async channel EIA output status of the DSR signal." 
	 ::= {asyncChStatusEntry 10}


-- N_STATUS.O_SYNC =========================================================

syncChStatusTable OBJECT-TYPE
	SYNTAX	SEQUENCE OF SyncChStatusEntry
	ACCESS	not-accessible
	STATUS	mandatory
	DESCRIPTION	"Table of EIA status for sync channels." 
	 ::= {status 3}

syncChStatusEntry OBJECT-TYPE
	SYNTAX	SyncChStatusEntry 
	ACCESS	not-accessible
	STATUS	mandatory
	DESCRIPTION	"Entry within the table specific to a particular sync channel
			on a module/card for EIA status." 
	INDEX		{syncChStatusCardNumber, syncChStatusChannelNumber}
	 ::= {syncChStatusTable 1}

SyncChStatusEntry ::= SEQUENCE {
	syncChStatusCardNumber			INTEGER,
	syncChStatusChannelNumber		INTEGER,
	syncChStatusEiaInputsRTSStatus		INTEGER,
	syncChStatusEiaInputsDTRStatus		INTEGER,
	syncChStatusEiaInputsUAStatus		INTEGER,
	syncChStatusEiaInputsBUSYStatus		INTEGER,
	syncChStatusEiaOutputsRIStatus		INTEGER,
	syncChStatusEiaOutputsRLSDStatus	INTEGER,
	syncChStatusEiaOutputsCTSStatus		INTEGER,
	syncChStatusEiaOutputsDSRStatus		INTEGER
	}

syncChStatusCardNumber OBJECT-TYPE
	SYNTAX	INTEGER (1..5)
	ACCESS	read-only
	STATUS	mandatory
	DESCRIPTION	"Identifies the module/card number for EIA status of the sync 
			channel." 
	 ::= {syncChStatusEntry 1}

syncChStatusChannelNumber OBJECT-TYPE
	SYNTAX	INTEGER (1..6)
	ACCESS	read-only
	STATUS	mandatory
	DESCRIPTION	"Identifies the sync channel for EIA status." 
	 ::= {syncChStatusEntry 2}

syncChStatusEiaInputsRTSStatus OBJECT-TYPE
	SYNTAX	INTEGER {
		on (1),
		off (2)
		}
	ACCESS	read-only
	STATUS	mandatory
	DESCRIPTION	"Indicates the sync channel EIA input status of the RTS signal." 
	 ::= {syncChStatusEntry 3}

syncChStatusEiaInputsDTRStatus OBJECT-TYPE
	SYNTAX	INTEGER {
		on (1),
		off (2)
		}
	ACCESS	read-only
	STATUS	mandatory
	DESCRIPTION	"Indicates the sync channel EIA input status of the DTR signal." 
	 ::= {syncChStatusEntry 4}

syncChStatusEiaInputsUAStatus OBJECT-TYPE
	SYNTAX	INTEGER {
		on (1),
		off (2)
		}
	ACCESS	read-only
	STATUS	mandatory
	DESCRIPTION	"Indicates the sync channel EIA input status of the UA signal." 
	 ::= {syncChStatusEntry 5}

syncChStatusEiaInputsBUSYStatus OBJECT-TYPE
	SYNTAX	INTEGER {
		on (1),
		off (2)
		}
	ACCESS	read-only
	STATUS	mandatory
	DESCRIPTION	"Indicates the sync channel EIA input status of the Busy signal." 
	 ::= {syncChStatusEntry 6}

syncChStatusEiaOutputsRIStatus OBJECT-TYPE
	SYNTAX	INTEGER {
		on (1),
		off (2)
		}
	ACCESS	read-only
	STATUS	mandatory
	DESCRIPTION	"Indicates the sync channel EIA output status of the RI signal." 
	 ::= {syncChStatusEntry 7}

syncChStatusEiaOutputsRLSDStatus OBJECT-TYPE
	SYNTAX	INTEGER {
		on (1),
		off (2)
		}
	ACCESS	read-only
	STATUS	mandatory
	DESCRIPTION	"Indicates the sync channel EIA output status of the RLSD signal." 
	 ::= {syncChStatusEntry 8}

syncChStatusEiaOutputsCTSStatus OBJECT-TYPE
	SYNTAX	INTEGER {
		on (1),
		off (2)
		}
	ACCESS	read-only
	STATUS	mandatory
	DESCRIPTION	"Indicates the sync channel EIA output status of the CTS signal." 
	 ::= {syncChStatusEntry 9}

syncChStatusEiaOutputsDSRStatus OBJECT-TYPE
	SYNTAX	INTEGER {
		on (1),
		off (2)
		}
	ACCESS	read-only
	STATUS	mandatory
	DESCRIPTION	"Indicates the sync channel EIA output status of the DSR signal." 
	 ::= {syncChStatusEntry 10}


-- N_STATUS.O_VOICE =======================================================

voiceChStatusTable OBJECT-TYPE
	SYNTAX	SEQUENCE OF VoiceChStatusEntry
	ACCESS	not-accessible
	STATUS	mandatory
	DESCRIPTION	"Table of voice channel status indicators." 
	::= {status 4}

voiceChStatusEntry OBJECT-TYPE
	SYNTAX	VoiceChStatusEntry
	ACCESS	not-accessible
	STATUS	mandatory
	DESCRIPTION	"Entry within the table specific to a particular voice channel
			on a module/card for status indicators." 
	INDEX		{voiceChStatusCardNumber, voiceChStatusChannelNumber}
	::= {voiceChStatusTable 1}

VoiceChStatusEntry ::= SEQUENCE {
	voiceChStatusCardNumber		INTEGER,
	voiceChStatusChannelNumber		INTEGER,
	voiceChStatusInputLevel			INTEGER,
	voiceChStatusStatus			INTEGER, 
	voiceChStatusPromID			DisplayString, 
	voiceChStatusSoftwareRevision		DisplayString, 
	voiceChStatusTestMode			INTEGER, 
	voiceChStatusTestDSPResult		INTEGER,
	voiceChStatusTestDataRAMResult		INTEGER,
	voiceChStatusTestCodeRAMResult	INTEGER,
	voiceChStatusTestAnalogHwResult	INTEGER,
	voiceChStatusTestDeviceCfgResult		INTEGER,
	voiceChStatusFlashState			INTEGER,
	voiceChStatusEPROMStatus		INTEGER
	}

voiceChStatusCardNumber  OBJECT-TYPE
	SYNTAX	INTEGER (1..5)
	ACCESS	read-only
	STATUS	mandatory
	DESCRIPTION	"Identifies the module/card number of the voice channel
			for status indications." 
	  ::= {voiceChStatusEntry 1}

voiceChStatusChannelNumber OBJECT-TYPE
	SYNTAX	INTEGER
	ACCESS	read-only
	STATUS	mandatory
	DESCRIPTION	"Identifies the voice channel number for status indications." 
	  ::= {voiceChStatusEntry 2}

voiceChStatusInputLevel  OBJECT-TYPE
	SYNTAX	INTEGER {
		levelLessThanNeg25dBm (1),
		levelNeg24dBm (2),
		levelNeg21dBm (3),
		levelNeg18dBm (4),
		levelNeg15dBm (5),
		levelNeg12dBm (6),
		levelNeg10dBm (7),
		levelNeg8dBm (8),
		levelNeg6dBm (9),
		levelNeg5dBm (10),
		levelNeg4dBm (11),
		levelNeg3dBm (12),
		levelNeg2dBm (13),
		levelNeg1dBm (14),
		level0dBm (15),
		levelgreaterThan0dBm (16),
		levelNotAvailable (17)
		}
	ACCESS	read-only
	STATUS	mandatory
	DESCRIPTION	"Indicates the level of the input signal monitored, in dBm." 
	::= {voiceChStatusEntry 3}

voiceChStatusStatus  OBJECT-TYPE
	SYNTAX	INTEGER {
		onHook (1),
		offHook (2),
		busy (3)
		}
	ACCESS	read-only
	STATUS	mandatory
	DESCRIPTION	"Indicates the mode of the current voice channel operation." 
	::= {voiceChStatusEntry 4}

voiceChStatusPromID OBJECT-TYPE
	SYNTAX	DisplayString  (SIZE (0..4))
	ACCESS	read-only
	STATUS	mandatory
	DESCRIPTION	"Indicates the Prom ID of the voice channel." 
	::= {voiceChStatusEntry 5}

voiceChStatusSoftwareRevision OBJECT-TYPE
	SYNTAX	DisplayString  (SIZE (0..3))
	ACCESS	read-only
	STATUS	mandatory
	DESCRIPTION	"Indicates the software revision of the voice channel." 
	::= {voiceChStatusEntry 6}

voiceChStatusTestMode  OBJECT-TYPE
	SYNTAX	INTEGER {
		none (1),
		levelDisplay(2),
		localSelfTest (3),
		localLoopback (4),
		remoteSelfTest (5),
		remoteLoopback (6)
		}
	ACCESS	read-only
	STATUS	mandatory
	DESCRIPTION	"Indicates the type of test that is currently running, if testing." 
	::= {voiceChStatusEntry 7}

voiceChStatusTestDSPResult  OBJECT-TYPE
	SYNTAX	INTEGER {
		ok (1),
		failed (2)
		}
	ACCESS	read-only
	STATUS	mandatory
	DESCRIPTION	"Indicates the DSP test results of the voice channel following 
			initiation of a voice channel self test." 
	::= {voiceChStatusEntry 8}

voiceChStatusTestDataRAMResult  OBJECT-TYPE
	SYNTAX	INTEGER {
		ok (1),
		failed (2)
		}
	ACCESS	read-only
	STATUS	mandatory
	DESCRIPTION	"Indicates the data RAM test results of the voice channel following 
			initiation of a voice channel self test." 
	::= {voiceChStatusEntry 9}

voiceChStatusTestCodeRAMResult  OBJECT-TYPE
	SYNTAX	INTEGER {
		ok (1),
		failed (2)
		}
	ACCESS	read-only
	STATUS	mandatory
	DESCRIPTION	"Indicates the code RAM test results of the voice channel following 
			initiation of a voice channel self test." 
	::= {voiceChStatusEntry 10}

voiceChStatusTestAnalogHwResult  OBJECT-TYPE
	SYNTAX	INTEGER {
		ok (1),
		failed (2)
		}
	ACCESS	read-only
	STATUS	mandatory
	DESCRIPTION	"Indicates the Analog Hardware test results of the voice channel 
			following initiation of a voice channel self test." 
	::= {voiceChStatusEntry 11}

voiceChStatusTestDeviceCfgResult  OBJECT-TYPE
	SYNTAX	INTEGER {
		ok (1),
		failed (2)
		}
	ACCESS	read-only
	STATUS	mandatory
	DESCRIPTION	"Indicates the device configuration test results of the voice channel 
			following initiation of a voice channel self test." 
	::= {voiceChStatusEntry 12}

voiceChStatusFlashState OBJECT-TYPE
	SYNTAX	INTEGER {
		notInstalled (1),
		valid (2),
		erased (3),
		invalidChecksum (4),
		noAnalogDriver (5),
		securityViolation (6)
		}
	ACCESS	read-only
	STATUS	mandatory
	DESCRIPTION	"Indicates the state of the flash memory residing on the voice 
			channel." 
	::= {voiceChStatusEntry 13}

voiceChStatusEPROMStatus OBJECT-TYPE
	SYNTAX	INTEGER {
		notInstalled (1),
		currentlyOperating (2),
		presentButNotOperating (3)
		}
	ACCESS	read-only
	STATUS	mandatory
	DESCRIPTION	"Indicates the status of the EPROM memory residing on the voice 
			channel." 
	::= {voiceChStatusEntry 14}


-- N_STATUS.O_LNKCH =====================================================

linkStatusTable OBJECT-TYPE
	SYNTAX	SEQUENCE OF LinkStatusEntry
	ACCESS	not-accessible
	STATUS	mandatory
	DESCRIPTION	"Table of link channel status of the Integration unit." 
	::= {status 5}

linkStatusEntry OBJECT-TYPE
	SYNTAX	LinkStatusEntry
	ACCESS	not-accessible
	STATUS	mandatory
	DESCRIPTION	"Entry within the table specific to a particular channel
			number on a module/card for status of the links." 
	INDEX		{linkStatusCardNumber,  linkStatusChannelNumber}
	::= {linkStatusTable 1} 

LinkStatusEntry ::= SEQUENCE {
	linkStatusCardNumber			INTEGER,
	linkStatusChannelNumber			INTEGER,
	linkStatusLinkType			INTEGER,
	linkStatusIntegralDevType		INTEGER,
	linkStatusIntegralDevSlotNumber		INTEGER,
	linkStatusIntegralDeviceNumber		INTEGER,
	linkStatusStatus				INTEGER,
	linkStatusNodeNumber			INTEGER,
	linkStatusRemoteChannelNumber		INTEGER,
	linkStatusRemoteCardNumber		INTEGER,
	linkStatusEiaOutputsRTSStatus		INTEGER,
	linkStatusEiaOutputsDTRStatus		INTEGER,
	linkStatusEiaOutputsBUSYStatus		INTEGER,
	linkStatusEiaOutputsUAStatus		INTEGER,
	linkStatusEiaInputsRLSDStatus		INTEGER,
	linkStatusEiaInputsDSRStatus		INTEGER,
	linkStatusEiaInputsRIStatus		INTEGER,
	linkStatusEiaInputsCTSStatus		INTEGER
	}

linkStatusCardNumber OBJECT-TYPE
	SYNTAX	INTEGER (1..5)
	ACCESS	read-only
	STATUS	mandatory
	DESCRIPTION	"Identifies the module/card number for link status." 
	::= {linkStatusEntry 1}

linkStatusChannelNumber OBJECT-TYPE
	SYNTAX	INTEGER
	ACCESS	read-only
	STATUS	mandatory
	DESCRIPTION	"Identifies the port/channel number for link status." 
	::= {linkStatusEntry 2}

linkStatusLinkType OBJECT-TYPE
	SYNTAX	INTEGER {
		muxLink (1),
		esi (2),
		x21MuxLink (3),
		localESI (4),
		esiSecondary (5),
		frameRelay (6)
		}
	ACCESS	read-only
	STATUS	mandatory
	DESCRIPTION	"Indicates the type of link configured on the Integration unit." 
	::= {linkStatusEntry 3}

linkStatusIntegralDevType OBJECT-TYPE
	SYNTAX	INTEGER {
		none (1),
		isu56K (2)
		}
	ACCESS	read-only
	STATUS	mandatory
	DESCRIPTION	"Indicates the presence of an integral device on the Integration unit." 
	::= {linkStatusEntry 4}

linkStatusIntegralDevSlotNumber OBJECT-TYPE
	SYNTAX	INTEGER {
		slotA (1),
		slotB (2),
		slotC (3),
		slotD (4),
		slotE (5)
		}
	ACCESS	read-only
	STATUS	mandatory
	DESCRIPTION	"Indicates the location slot of the integral device, if present." 
	::= {linkStatusEntry 5}

linkStatusIntegralDeviceNumber OBJECT-TYPE
	SYNTAX	INTEGER {
		channel1 (1),
		channel2 (2)
		}
	ACCESS	read-only
	STATUS	mandatory
	DESCRIPTION	"Indicates the channel location of the integral device, if present." 
	::= {linkStatusEntry 6}

linkStatusStatus OBJECT-TYPE
	SYNTAX	INTEGER {
		down (1),
		up (2),
		loopback (3)
		}
	ACCESS	read-only
	STATUS	mandatory
	DESCRIPTION	"Indicates the status of the link." 
	::= {linkStatusEntry 7}

linkStatusNodeNumber OBJECT-TYPE
	SYNTAX	INTEGER
	ACCESS	read-only
	STATUS	mandatory
	DESCRIPTION	"Indicates the ID number of the remote linked Integration unit." 
	::= {linkStatusEntry 8}

linkStatusRemoteChannelNumber OBJECT-TYPE
	SYNTAX	INTEGER
	ACCESS	read-only
	STATUS	mandatory
	DESCRIPTION	"Indicates the channel number of the remote linked Integration
			unit." 
	::= {linkStatusEntry 9}

linkStatusRemoteCardNumber OBJECT-TYPE
	SYNTAX	INTEGER
	ACCESS	read-only
	STATUS	mandatory
	DESCRIPTION	"Indicates the module/card number of the remote linked Integration
			unit." 
	::= {linkStatusEntry 10}

linkStatusEiaOutputsRTSStatus OBJECT-TYPE
	SYNTAX	INTEGER {
		on (1),
		off (2)
		}
	ACCESS	read-only
	STATUS	mandatory
	DESCRIPTION	"Indicates the link channel EIA output status of the RTS signal." 
	::= {linkStatusEntry 11}

linkStatusEiaOutputsDTRStatus OBJECT-TYPE
	SYNTAX	INTEGER {
		on (1),
		off (2)
		}
	ACCESS	read-only
	STATUS	mandatory
	DESCRIPTION	"Indicates the link channel EIA output status of the DTR signal." 
	::= {linkStatusEntry 12}

linkStatusEiaOutputsBUSYStatus OBJECT-TYPE
	SYNTAX	INTEGER {
		on (1),
		off (2)
		}
	ACCESS	read-only
	STATUS	mandatory
	DESCRIPTION	"Indicates the link channel EIA output status of the Busy signal." 
	::= {linkStatusEntry 13}

linkStatusEiaOutputsUAStatus OBJECT-TYPE
	SYNTAX	INTEGER {
		on (1),
		off (2)
		}
	ACCESS	read-only
	STATUS	mandatory
	DESCRIPTION	"Indicates the link channel EIA output status of the UA signal." 
	::= {linkStatusEntry 14}

linkStatusEiaInputsRLSDStatus OBJECT-TYPE
	SYNTAX	INTEGER {
		on (1),
		off (2)
		}
	ACCESS	read-only
	STATUS	mandatory
	DESCRIPTION	"Indicates the link channel EIA output status of the RLSD signal." 
	::= {linkStatusEntry 15}

linkStatusEiaInputsDSRStatus OBJECT-TYPE
	SYNTAX	INTEGER {
		on (1),
		off (2)
		}
	ACCESS	read-only
	STATUS	mandatory
	DESCRIPTION	"Indicates the link channel EIA input status of the DSR signal." 
	::= {linkStatusEntry 16}

linkStatusEiaInputsRIStatus OBJECT-TYPE
	SYNTAX	INTEGER {
		on (1),
		off (2)
		}
	ACCESS	read-only
	STATUS	mandatory
	DESCRIPTION	"Indicates the link channel EIA input status of the RI signal." 
	::= {linkStatusEntry 17}

linkStatusEiaInputsCTSStatus OBJECT-TYPE
	SYNTAX	INTEGER {
		on (1),
		off (2)
		}
	ACCESS	read-only
	STATUS	mandatory
	DESCRIPTION	"Indicates the link channel EIA input status of the CTS signal." 
	::= {linkStatusEntry 18}


-- N_STATUS.O_DLCI ========================================================

frameRelayLinkDLCIStatusTable OBJECT-TYPE
	SYNTAX  SEQUENCE OF FrameRelayLinkDLCIStatusEntry
	ACCESS  not-accessible
	STATUS  mandatory
	DESCRIPTION	"Table of Frame Relay link status of DLCI channels." 
	::= {status 6}

frameRelayLinkDLCIStatusEntry OBJECT-TYPE
	SYNTAX  FrameRelayLinkDLCIStatusEntry
	ACCESS  not-accessible
	STATUS  mandatory
	DESCRIPTION	"Entry within the table specific to a particular DLCI channel,
			FR access port/channel, and module/card number for FR link status." 
	INDEX   {frameRelayLinkDLCIStatusCardNumber, 
			frameRelayLinkDLCIStatusChannelNumber,
			frameRelayLinkDLCIStatusDLCINumber}
	::= { frameRelayLinkDLCIStatusTable 1} 

FrameRelayLinkDLCIStatusEntry ::= SEQUENCE {
	frameRelayLinkDLCIStatusCardNumber                      	INTEGER, 
	frameRelayLinkDLCIStatusChannelNumber                   	INTEGER,
	frameRelayLinkDLCIStatusDLCINumber          			INTEGER,
	frameRelayLinkDLCIStatusNumberOfDLCIs				INTEGER,
	frameRelayLinkDLCIStatusConfOnMarathon          		INTEGER,
	frameRelayLinkDLCIStatusReportedByPBX           		INTEGER,
	frameRelayLinkDLCIStatusActive                          	INTEGER,
	frameRelayLinkDLCIStatusLinkStatus                      	INTEGER,
	frameRelayLinkDLCIStatusUpConnectedNodeNumber			INTEGER,
	frameRelayLinkDLCIStatusUpConnectedChannelNumber  		INTEGER,
	frameRelayLinkDLCIStatusUpConnectedCardNumber            	INTEGER,
	frameRelayLinkDLCIStatusUpRemoteDLCINumber               	INTEGER
	}

frameRelayLinkDLCIStatusCardNumber OBJECT-TYPE
	SYNTAX  INTEGER
	ACCESS  read-only
	STATUS  mandatory
	DESCRIPTION	"Identifies the module/card number for FR link status of DLCI 
			channels." 
	::= {frameRelayLinkDLCIStatusEntry 1}

frameRelayLinkDLCIStatusChannelNumber OBJECT-TYPE
	SYNTAX  INTEGER
	ACCESS  read-only
	STATUS  mandatory
	DESCRIPTION	"Identifies the port/channel number of the FR access link for 
			DLCI channel status." 
	::= {frameRelayLinkDLCIStatusEntry 2}

frameRelayLinkDLCIStatusDLCINumber OBJECT-TYPE
	SYNTAX  INTEGER
	ACCESS  read-only
	STATUS  mandatory
	DESCRIPTION	"Identifies the DLCI channel number for FR link status." 
	::= {frameRelayLinkDLCIStatusEntry 3}

frameRelayLinkDLCIStatusNumberOfDLCIs OBJECT-TYPE
	SYNTAX  INTEGER
	ACCESS  read-only
	STATUS  mandatory
	DESCRIPTION	"Indicates the number of DLCIs for a particular FR access link." 
	::= { frameRelayLinkDLCIStatusEntry 4}
	
frameRelayLinkDLCIStatusConfOnMarathon OBJECT-TYPE
	SYNTAX  INTEGER {
		yes (1),
		no (2)
		}
	ACCESS  read-only
	STATUS  mandatory
	DESCRIPTION	"Indicates whether or not the DLCI channel is configured by
			the Integration unit." 
	::= {frameRelayLinkDLCIStatusEntry 5}

frameRelayLinkDLCIStatusReportedByPBX  OBJECT-TYPE
	SYNTAX  INTEGER {
		yes (1),
		no (2)
		}
	ACCESS  read-only
	STATUS  mandatory
	DESCRIPTION	"Indicates whether or not the DLCI channel is reported  by
			a PBX system." 
	::= {frameRelayLinkDLCIStatusEntry 6}

frameRelayLinkDLCIStatusActive OBJECT-TYPE
	SYNTAX  INTEGER {
		yes (1),
		no (2)
		}
	ACCESS  read-only
	STATUS  mandatory
	DESCRIPTION	"Indicates the status of the DLCI channel; active or not." 
	::= {frameRelayLinkDLCIStatusEntry 7}

frameRelayLinkDLCIStatusLinkStatus OBJECT-TYPE
	SYNTAX  INTEGER {
		down (1),
		up (2)
		}
	ACCESS  read-only
	STATUS  mandatory
	DESCRIPTION	"Indicates the status of the FR link for the specific DLCI channel.
			Note: Transparent and Fragmented DLCI channel types will indicate
			'down'." 
	::= {frameRelayLinkDLCIStatusEntry 8}

frameRelayLinkDLCIStatusUpConnectedNodeNumber OBJECT-TYPE
	SYNTAX  INTEGER
	ACCESS  read-only
	STATUS  mandatory
	DESCRIPTION	"Indicates the node ID # of the remote linked Integration unit." 
	::= {frameRelayLinkDLCIStatusEntry 9}

frameRelayLinkDLCIStatusUpConnectedChannelNumber OBJECT-TYPE
	SYNTAX  INTEGER
	ACCESS  read-only
	STATUS  mandatory
	DESCRIPTION	"Indicates the port/channel number of the FR access link of the 
			remote linked Integration unit." 
	::= {frameRelayLinkDLCIStatusEntry 10}

frameRelayLinkDLCIStatusUpConnectedCardNumber OBJECT-TYPE
	SYNTAX  INTEGER
	ACCESS  read-only
	STATUS  mandatory
	DESCRIPTION	"Indicates the module/card number of the FR access link of the 
			remote linked Integration unit." 
	::= {frameRelayLinkDLCIStatusEntry 11}

frameRelayLinkDLCIStatusUpRemoteDLCINumber OBJECT-TYPE
	SYNTAX  INTEGER
	ACCESS  read-only
	STATUS  mandatory
	DESCRIPTION	"Indicates the DLCI number of the remote linked Integration unit." 
	::= {frameRelayLinkDLCIStatusEntry 12}


-- N_STATUS.O_CHCNST =======================================================

chConnectionStatusTable OBJECT-TYPE
	SYNTAX	SEQUENCE OF ChConnectionStatusEntry
	ACCESS	not-accessible
	STATUS	mandatory
	DESCRIPTION	"Table of channel connection status indications." 
	 ::= {status 7}

chConnectionStatusEntry OBJECT-TYPE
	SYNTAX	ChConnectionStatusEntry
	ACCESS	not-accessible
	STATUS	mandatory
	DESCRIPTION	"Entry within the table specific to a particular channel number
			on a module/card for connection status indications." 
	INDEX		{chConnectionStatusCardNumber, chConnectionStatusChannelNumber}
	 ::= {chConnectionStatusTable 1}

ChConnectionStatusEntry ::= SEQUENCE {
	chConnectionStatusCardNumber			INTEGER,
	chConnectionStatusChannelNumber		INTEGER,
	chConnectionStatusChannelStatus			INTEGER,
	chConnectionStatusConnectedToNode		INTEGER,
	chConnectionStatusConnectedToChannel		INTEGER,
	chConnectionStatusConnectedToCard		INTEGER,
	chConnectionStatusConnectedToInternalFacility	INTEGER
	}

chConnectionStatusCardNumber	 OBJECT-TYPE
	SYNTAX	INTEGER (1..5)
	ACCESS	read-only
	STATUS	mandatory
	DESCRIPTION	"Identifies the module/card number of the channel for connection
			status indication." 
	  ::= {chConnectionStatusEntry 1}

chConnectionStatusChannelNumber OBJECT-TYPE
	SYNTAX	INTEGER
	ACCESS	read-only
	STATUS	mandatory
	DESCRIPTION	"Identifies the channel number for connection status indication." 
	  ::= {chConnectionStatusEntry 2}

chConnectionStatusChannelStatus OBJECT-TYPE
	SYNTAX	INTEGER {
		idle (1),
		connectInProgress (2),
		fconnInProgress (3),
		queued (4),
		connected (5),
 		forceConnected (6),
		disconnectInProgress (7),
		outOfService (8)
		}
	ACCESS	read-only
	STATUS	mandatory
	DESCRIPTION	"Indicates the connection status of the channel." 
	  ::= {chConnectionStatusEntry 3}

chConnectionStatusConnectedToNode OBJECT-TYPE
	SYNTAX	INTEGER 
	ACCESS	read-only
	STATUS	mandatory
	DESCRIPTION	"Indicates the node ID # of the destination channel connection, if any." 
	  ::= {chConnectionStatusEntry 4}

chConnectionStatusConnectedToChannel OBJECT-TYPE
	SYNTAX	INTEGER
	ACCESS	read-only
	STATUS	mandatory
	DESCRIPTION	"Indicates the destination channel number of the connection, if any." 
	  ::= {chConnectionStatusEntry 5}

chConnectionStatusConnectedToCard OBJECT-TYPE
	SYNTAX	INTEGER
	ACCESS	read-only
	STATUS	mandatory
	DESCRIPTION	"Indicates the destination module/card number of the connection, if any." 
	  ::= {chConnectionStatusEntry 6}

chConnectionStatusConnectedToInternalFacility OBJECT-TYPE
	SYNTAX	INTEGER {
		notApplicable (1),
		dollarCMDFacility (2),
		dollarPPPFacility (3)
		}
	ACCESS	read-only
	STATUS	mandatory
	DESCRIPTION	"Indicates a channel connection to an internal facility ($CMD or $PPP),
			if any." 
	  ::= {chConnectionStatusEntry 7}

-- N_STATUS.O_RMTNOD =====================================================

remoteNodeStatusTable OBJECT-TYPE
	SYNTAX	SEQUENCE OF RemoteNodeStatusEntry
	ACCESS	not-accessible
	STATUS	mandatory
	DESCRIPTION	"Table of remote nodes in the MICOM Integration unit network." 
	::= {status 8}

remoteNodeStatusEntry OBJECT-TYPE
	SYNTAX	RemoteNodeStatusEntry
	ACCESS	not-accessible
	STATUS	mandatory
	DESCRIPTION	"Entry within the table specific to each indexed node in the
			MICOM Integration unit network." 
	INDEX	{remoteNodeStatusIndex}
	::= {remoteNodeStatusTable 1}

RemoteNodeStatusEntry ::= SEQUENCE {
	remoteNodeStatusIndex		INTEGER,
	remoteNodeStatusName		DisplayString,
	remoteNodeStatusType		INTEGER,
	remoteNodeStatusNumber		INTEGER
	}

remoteNodeStatusIndex OBJECT-TYPE
	SYNTAX	INTEGER
	ACCESS	read-only
	STATUS	mandatory
	DESCRIPTION	"Identifies the index for the table of remote nodes
			in the MICOM Integration unit network." 
	::= {remoteNodeStatusEntry 1}

remoteNodeStatusName OBJECT-TYPE
	SYNTAX	DisplayString  (SIZE (1..8))
	ACCESS	read-only
	STATUS	mandatory
	DESCRIPTION	"Indicates the remote node name in the MICOM Integration 
			unit network." 
	::= {remoteNodeStatusEntry 2}

remoteNodeStatusType OBJECT-TYPE
	SYNTAX	INTEGER {
		marathonNode (1),
		feederMux (2)
		}
	ACCESS	read-only
	STATUS	mandatory
	DESCRIPTION	"Indicates the type of remote node in the MICOM Integration 
			unit network." 
	::= {remoteNodeStatusEntry 3}

remoteNodeStatusNumber OBJECT-TYPE
	SYNTAX	INTEGER
	ACCESS	read-only
	STATUS	mandatory
	DESCRIPTION	"Indicates the node ID # of the remote node in the MICOM Integration 
			unit network." 
	::= {remoteNodeStatusEntry 4}


-- N_STATUS.O_RCLASS ======================================================

classStatusTable OBJECT-TYPE
	SYNTAX	SEQUENCE OF ClassStatusEntry
	ACCESS	not-accessible
	STATUS	mandatory
	DESCRIPTION	"Table of switching classes defined for the Integration unit." 
	::= {status 9}

classStatusEntry OBJECT-TYPE
	SYNTAX	ClassStatusEntry
	ACCESS	not-accessible
	STATUS	mandatory
	DESCRIPTION	"Entry within the table specific to each indexed class defined for
			the Integration unit." 
	INDEX		{classStatusCfgClassIndex }
	 ::= {classStatusTable 1}

ClassStatusEntry ::= SEQUENCE {
	classStatusCfgClassIndex		INTEGER,
	classStatusCfgClassNumber		INTEGER
	}

classStatusCfgClassIndex OBJECT-TYPE
	SYNTAX	INTEGER
	ACCESS	read-only
	STATUS	mandatory
	DESCRIPTION	"Identifies the index for the table of defined switching classes
			for the Integration unit." 
	 ::= {classStatusEntry 1}

classStatusCfgClassNumber  OBJECT-TYPE
	SYNTAX	INTEGER
	ACCESS	read-only
	STATUS	mandatory
	DESCRIPTION	"Indicates the switching class numbers defined for the Integration
			unit." 
	 ::= {classStatusEntry 2}


-- N_STATUS.O_QCOUNT ======================================================

classQueueStatusTable OBJECT-TYPE
	SYNTAX	SEQUENCE OF ClassQueueStatusEntry
	ACCESS	not-accessible
	STATUS	mandatory
	DESCRIPTION	"Table of connection class queue channels defined for the Integration
			unit." 
	::= {status 10}

classQueueStatusEntry OBJECT-TYPE
	SYNTAX	ClassQueueStatusEntry
	ACCESS	not-accessible
	STATUS	mandatory
	DESCRIPTION	"Entry within the table specific to a particular class number 
			defined for the Integration unit." 
	INDEX		{classQueueStatusClassNum}
	 ::= {classQueueStatusTable 1}

ClassQueueStatusEntry ::= SEQUENCE {
	classQueueStatusClassNum	INTEGER,
	classQueueStatusChCount		INTEGER
	}

classQueueStatusClassNum OBJECT-TYPE
	SYNTAX	INTEGER (1..64)
	ACCESS	read-only
	STATUS	mandatory
	DESCRIPTION	"Identifies the class number to index connection queue channels
			for the Integration unit." 
	 ::= {classQueueStatusEntry 1}

classQueueStatusChCount OBJECT-TYPE
	SYNTAX	INTEGER
	ACCESS	read-only
	STATUS	mandatory
	DESCRIPTION	"Indicates the number of queue channels defined for a particular
			class connection for the Integration unit." 
	 ::= {classQueueStatusEntry 2}


-- N_STATUS.O_QSTAT ======================================================

classChannelStatusTable OBJECT-TYPE
	SYNTAX	SEQUENCE OF ClassChannelStatusEntry
	ACCESS	not-accessible
	STATUS	mandatory
	DESCRIPTION	"Table to indicate current queue status of the configured classes.
			Should all the class channels be busy when the channel request
			a class, that channel is put in waiting queue on first-come,
			first-serve basis." 
	::= {status 11}

classChannelStatusEntry OBJECT-TYPE
	SYNTAX	ClassChannelStatusEntry
	ACCESS	not-accessible
	STATUS	mandatory
	DESCRIPTION	"An entry for a specified class number that indicates the current
			location in the queue." 
	INDEX		{classQueueStatusClassNum, classQueueStatusChannelIndex}
	 ::= {classChannelStatusTable 1}

ClassChannelStatusEntry ::= SEQUENCE {
	classChannelStatusClassNum	INTEGER,
	classQueueStatusChannelIndex	INTEGER,
	classChannelStatusNode		INTEGER,
	classChannelStatusChannel	INTEGER,
	classChannelStatusCard		INTEGER
	}

classChannelStatusClassNum OBJECT-TYPE
	SYNTAX	INTEGER (1..64)
	ACCESS	read-only
	STATUS	mandatory
	DESCRIPTION	"Identifies the class number for which the channels are in queue." 
	 ::= {classChannelStatusEntry 1}

classQueueStatusChannelIndex OBJECT-TYPE
	SYNTAX	INTEGER
	ACCESS	read-only
	STATUS	mandatory
	DESCRIPTION	"Identifies all the channels in the queue for a particular class." 
	 ::= {classChannelStatusEntry 2}

classChannelStatusNode OBJECT-TYPE
	SYNTAX	INTEGER
	ACCESS	read-only
	STATUS	mandatory
	DESCRIPTION	"The node number of the channel waiting in the queue." 
	 ::= {classChannelStatusEntry 3}

classChannelStatusChannel OBJECT-TYPE
	SYNTAX	INTEGER
	ACCESS	read-only
	STATUS	mandatory
	DESCRIPTION	"The port number of the channel waiting in the queue." 
	 ::= {classChannelStatusEntry 4}

classChannelStatusCard OBJECT-TYPE
	SYNTAX	INTEGER
	ACCESS	read-only
	STATUS	mandatory
	DESCRIPTION	"The module/card number of the channel waiting in the queue." 
	 ::= {classChannelStatusEntry 5}

-- N_STATUS.O_FLASH ==================================================

flashMemoryStatusTable OBJECT-TYPE
	SYNTAX	SEQUENCE OF FlashMemoryStatusEntry
	ACCESS	not-accessible
	STATUS	mandatory
	DESCRIPTION	"Table of CCM flash memory status." 
	::= {status 12}

flashMemoryStatusEntry OBJECT-TYPE
	SYNTAX	FlashMemoryStatusEntry
	ACCESS	not-accessible
	STATUS	mandatory
	DESCRIPTION	"Entry within the table specific to a particular flash bank
			(1 or 2) for flash memory status." 
	INDEX		{flashMemoryStatusFlashNumber}
	 ::= {flashMemoryStatusTable 1}

FlashMemoryStatusEntry ::= SEQUENCE {
	flashMemoryStatusFlashNumber		INTEGER,
	flashMemoryStatusFileHeaderSize		INTEGER,
	flashMemoryStatusFileType		INTEGER,
	flashMemoryStatusMarathonImageSize	INTEGER,
	flashMemoryStatusCreationHours		INTEGER,
	flashMemoryStatusCreationMinutes	INTEGER,
	flashMemoryStatusCreationSeconds	INTEGER,
	flashMemoryStatusCreationYear		INTEGER,
	flashMemoryStatusCreationMonth		INTEGER,
	flashMemoryStatusCreationDay		INTEGER,
	flashMemoryStatusImageChecksum		INTEGER,
	flashMemoryStatusPromID			DisplayString 
	}

flashMemoryStatusFlashNumber OBJECT-TYPE
	SYNTAX	INTEGER (1..2)
	ACCESS	read-only
	STATUS	mandatory
	DESCRIPTION	"Identifies the flash memory bank for status; 1 or 2." 
	 ::= {flashMemoryStatusEntry 1}

flashMemoryStatusFileHeaderSize OBJECT-TYPE
	SYNTAX	INTEGER
	ACCESS	read-only
	STATUS	mandatory
	DESCRIPTION	"Indicates the size of the file header in flash memory." 
	 ::= {flashMemoryStatusEntry 2}

flashMemoryStatusFileType OBJECT-TYPE
	SYNTAX	INTEGER {
		compressed (1),
		uncompressed (2),
		erased (3)
		}
	ACCESS	read-only
	STATUS	mandatory
	DESCRIPTION	"Indicates the type of data stored in the flash memory bank." 
	 ::= {flashMemoryStatusEntry 3}

flashMemoryStatusMarathonImageSize OBJECT-TYPE
	SYNTAX	INTEGER
	ACCESS	read-only
	STATUS	mandatory
	DESCRIPTION	"Indicates the size of the Integration unit file image (following
			the header)." 
	 ::= {flashMemoryStatusEntry 4}

flashMemoryStatusCreationHours OBJECT-TYPE
	SYNTAX	INTEGER
	ACCESS	read-only
	STATUS	mandatory
	DESCRIPTION	"Indicates the Hours portion of the creation date/time of the 
			Integration unit binary image file." 
	 ::= {flashMemoryStatusEntry 5}

flashMemoryStatusCreationMinutes OBJECT-TYPE
	SYNTAX	INTEGER
	ACCESS	read-only
	STATUS	mandatory
	DESCRIPTION	"Indicates the Minutes portion of the creation date/time of the 
			Integration unit binary image file." 
	 ::= {flashMemoryStatusEntry 6}

flashMemoryStatusCreationSeconds OBJECT-TYPE
	SYNTAX	INTEGER
	ACCESS	read-only
	STATUS	mandatory
	DESCRIPTION	"Indicates the Seconds portion of the creation date/time of the 
			Integration unit binary image file." 
	 ::= {flashMemoryStatusEntry 7}

flashMemoryStatusCreationYear OBJECT-TYPE
	SYNTAX	INTEGER
	ACCESS	read-only
	STATUS	mandatory
	DESCRIPTION	"Indicates the Year portion of the creation date/time of the 
			Integration unit binary image file." 
	 ::= {flashMemoryStatusEntry 8}

flashMemoryStatusCreationMonth OBJECT-TYPE
	SYNTAX	INTEGER
	ACCESS	read-only
	STATUS	mandatory
	DESCRIPTION	"Indicates the Month portion of the creation date/time of the 
			Integration unit binary image file." 
	 ::= {flashMemoryStatusEntry 9}

flashMemoryStatusCreationDay OBJECT-TYPE
	SYNTAX	INTEGER
	ACCESS	read-only
	STATUS	mandatory
	DESCRIPTION	"Indicates the Day portion of the creation date/time of the 
			Integration unit binary image file." 
	 ::= {flashMemoryStatusEntry 10}

flashMemoryStatusImageChecksum OBJECT-TYPE
	SYNTAX	INTEGER
	ACCESS	read-only
	STATUS	mandatory
	DESCRIPTION	"Indicates the image checksum of the Integration unit image
			file." 
	 ::= {flashMemoryStatusEntry 11}

flashMemoryStatusPromID OBJECT-TYPE
	SYNTAX	DisplayString  (SIZE (0..19))
	ACCESS	read-only
	STATUS	mandatory
	DESCRIPTION	"Indicates the Prom ID file identifier of the Integration unit
			image file." 
	 ::= {flashMemoryStatusEntry 12}

-- N_CMOS.O_FCONNS  =====================================================

chForceConnStatusTable OBJECT-TYPE
	SYNTAX	SEQUENCE OF ChForceConnStatusEntry
	ACCESS	not-accessible
	STATUS	mandatory
	DESCRIPTION	"Table of channel force connects status.  Note that the
		table will be incomplete for Digital Voice modules (DVM) if the
		modules are not contiguous on the T1, E1, or Digital Voice Expansion
		modules. (Ex. - B1, B2, B5; table will only show B1 and B2, not B5.)" 
	::= {status 13}

chForceConnStatusEntry OBJECT-TYPE
	SYNTAX	ChForceConnStatusEntry
	ACCESS	not-accessible
	STATUS	mandatory
	DESCRIPTION	"Entry within the table specific to a particular channel number
			and module/card number for channel force connection status." 
	INDEX		{chForceConnStatusCardNumber, chForceConnStatusChannelNumber}
	::= {chForceConnStatusTable 1}

ChForceConnStatusEntry ::= SEQUENCE {
	chForceConnStatusCardNumber		INTEGER,
	chForceConnStatusChannelNumber	INTEGER,
	chForceConnStatusNodeNumber		INTEGER,
	chForceConnStatusToNodeNumber	INTEGER,
	chForceConnStatusToCardNumber		INTEGER,
	chForceConnStatusToChannelNumber	INTEGER
	}

chForceConnStatusCardNumber OBJECT-TYPE
	SYNTAX	INTEGER (1..5)
	ACCESS	read-only
	STATUS	mandatory
	DESCRIPTION	"Identifies the module/card number of the source channel for
			channel force connection status." 
	::= {chForceConnStatusEntry 1}

chForceConnStatusChannelNumber OBJECT-TYPE
	SYNTAX	INTEGER (1..32)
	ACCESS	read-only
	STATUS	mandatory
	DESCRIPTION	"Identifies the source channel number for channel force 
			connection status." 
	::= {chForceConnStatusEntry 2}

chForceConnStatusNodeNumber OBJECT-TYPE
	SYNTAX	INTEGER (1..255)
	ACCESS	read-only
	STATUS	mandatory
	DESCRIPTION	"Indicates the Node ID # of the source channel for
			channel force connection status." 
	::= {chForceConnStatusEntry 3}

chForceConnStatusToNodeNumber OBJECT-TYPE
	SYNTAX	INTEGER (1..255)
	ACCESS	read-only
	STATUS	mandatory
	DESCRIPTION	"Indicates the Node ID # of the destination channel for
			channel force connection status." 
	::= {chForceConnStatusEntry 4}

chForceConnStatusToCardNumber OBJECT-TYPE
	SYNTAX	INTEGER (1..5)
	ACCESS	read-only
	STATUS	mandatory
	DESCRIPTION	"Identifies the module/card number of the destination channel
			for channel force connection status." 
	::= {chForceConnStatusEntry 5}

chForceConnStatusToChannelNumber OBJECT-TYPE
	SYNTAX	INTEGER (1..32)
	ACCESS	read-only
	STATUS	mandatory
	DESCRIPTION	"Identifies the destination channel number for channel force 
			connection status." 
	::= {chForceConnStatusEntry 6}


-- Statistics Group

-- N_CMOS.O_CMDRPT ==================================================

sysPeriodicStatisticsReportGroup    OBJECT IDENTIFIER ::= {statistics-configuration 1}

sysPeriodicStatisticsReportInterval	 OBJECT-TYPE
	SYNTAX	INTEGER {
		zero (1),
		ten (2),
		twenty (3),
		thirty (4),
		sixty (5)
		}
	ACCESS	read-write
	STATUS	mandatory
	DESCRIPTION	"Time interval (in minutes) to collect
			data for a periodic statistics report." 
	::= { sysPeriodicStatisticsReportGroup 1}

sysReportDestination OBJECT-TYPE
	SYNTAX	INTEGER {
		localCommandPort (1),
		localLogPort (2),
		remoteNode (3)
		}
	ACCESS	read-write
	STATUS	mandatory
	DESCRIPTION	"Destination for statistics reports to be routed." 
	::= { sysPeriodicStatisticsReportGroup 2}


-- N_CMOS.O_LOGDST ==================================================

sysRemoteLogNodeName OBJECT-TYPE
	SYNTAX	DisplayString  (SIZE (0..8))
	ACCESS	read-write
	STATUS	mandatory
	DESCRIPTION	"Remote Marathon Node name for log output and
			periodic statistics reports to be routed." 
	::= { statistics-configuration 2}


-- N_STATUS.O_PERTIM ==================================================

lastPeriodicStatisticsTimeGroup OBJECT IDENTIFIER ::= {statistics-configuration 3}

lastPeriodicStatisticsTimeMonth OBJECT-TYPE
	SYNTAX	INTEGER (1..12)
	ACCESS	read-only
	STATUS	mandatory
	DESCRIPTION	"Month portion of time stamp of last periodic
			report stored by the Marathon Node." 
	::= {lastPeriodicStatisticsTimeGroup 1}

lastPeriodicStatisticsTimeDay OBJECT-TYPE
	SYNTAX	INTEGER (1..31)
	ACCESS	read-only
	STATUS	mandatory
	DESCRIPTION	"Day portion of time stamp of last periodic
			report stored by the Marathon Node." 
	::= {lastPeriodicStatisticsTimeGroup 2}

lastPeriodicStatisticsTimeHours OBJECT-TYPE
	SYNTAX	INTEGER (0..23)
	ACCESS	read-only
	STATUS	mandatory
	DESCRIPTION	"Hours portion of time stamp of last periodic
			report stored by the Marathon Node." 
	::= {lastPeriodicStatisticsTimeGroup 3}

lastPeriodicStatisticsTimeMinutes OBJECT-TYPE
	SYNTAX	INTEGER (0..59)
	ACCESS	read-only
	STATUS	mandatory
	DESCRIPTION	"Minutes portion of time stamp of last periodic
			report stored by the Marathon Node." 
	::= {lastPeriodicStatisticsTimeGroup 4}

lastPeriodicStatisticsTimeSeconds OBJECT-TYPE
	SYNTAX	INTEGER (0..59)
	ACCESS	read-only
	STATUS	mandatory
	DESCRIPTION	"Seconds portion of time stamp of last periodic
			report stored by the Marathon Node." 
	::= {lastPeriodicStatisticsTimeGroup 5}


-- N_CMOS.O_CMDRPT ==================================================

switchStatistics OBJECT-TYPE
	SYNTAX	INTEGER {
		enable (1),
		disable (2)
		}
	ACCESS	read-write
	STATUS	mandatory
	DESCRIPTION	"Enable/disable Switch statistics as part of the 
			system statistics periodic report.  Switch statistics
			are class number, name, number of connects, connect
			failures, and max number in queue." 
	::= {statistics-configuration 4}

-- N_STATUS.O_SYSPER ==================================================

chPeriodicStatisticsTable OBJECT-TYPE
	SYNTAX	SEQUENCE OF ChPeriodicStatisticsEntry
	ACCESS	not-accessible
	STATUS	mandatory
	DESCRIPTION	"Table of channel statistics for periodic 
			statistics reports. (Sync & Async channels)" 
	::= {statistics-periodic 1}

chPeriodicStatisticsEntry OBJECT-TYPE
	SYNTAX	ChPeriodicStatisticsEntry
	ACCESS	not-accessible
	STATUS	mandatory
	DESCRIPTION	"Entry within the table to specify a particular
			channel on specific module/card." 
	INDEX		{chPeriodicStatisticsCardNumber, chPeriodicStatisticsChannelNumber}
	::= {chPeriodicStatisticsTable 1}

ChPeriodicStatisticsEntry ::= SEQUENCE {
	chPeriodicStatisticsCardNumber		INTEGER,
	chPeriodicStatisticsChannelNumber	INTEGER,
	chPeriodicStatisticsMonth		INTEGER,
	chPeriodicStatisticsDay			INTEGER,
	chPeriodicStatisticsHours		INTEGER,
	chPeriodicStatisticsMinutes		INTEGER,
	chPeriodicStatisticsSeconds		INTEGER,
	chPeriodicStatisticsBuffUtilization	Gauge,
	chPeriodicStatisticsChannelBusiedOut	INTEGER,
	chPeriodicStatisticsChannelInFlowControl  INTEGER
	}

chPeriodicStatisticsCardNumber OBJECT-TYPE
	SYNTAX	INTEGER (1..5)
	ACCESS	read-only
	STATUS	mandatory
	DESCRIPTION	"Identifies the module/card number for the 
			channel specific to the periodic statistics 
			report data." 
	::= {chPeriodicStatisticsEntry 1}

chPeriodicStatisticsChannelNumber OBJECT-TYPE
	SYNTAX	INTEGER 
	ACCESS	read-only
	STATUS	mandatory
	DESCRIPTION	"Identifies the channel number specific to the
			 periodic statistics report data." 
	::= {chPeriodicStatisticsEntry 2}

chPeriodicStatisticsMonth OBJECT-TYPE
	SYNTAX	INTEGER (1..12)
	ACCESS	read-only
	STATUS	mandatory
	DESCRIPTION	"Month portion of the time stamp for the channel
			periodic statistics report." 
	::= {chPeriodicStatisticsEntry 3}

chPeriodicStatisticsDay OBJECT-TYPE
	SYNTAX	INTEGER (1..31)
	ACCESS	read-only
	STATUS	mandatory
	DESCRIPTION	"Day portion of the time stamp for the channel
			periodic statistics report." 
	::= {chPeriodicStatisticsEntry 4}

chPeriodicStatisticsHours OBJECT-TYPE
	SYNTAX	INTEGER (0..23)
	ACCESS	read-only
	STATUS	mandatory
	DESCRIPTION	"Hours portion of the time stamp for the channel
			periodic statistics report." 
	::= {chPeriodicStatisticsEntry 5}

chPeriodicStatisticsMinutes OBJECT-TYPE
	SYNTAX	INTEGER (0..59)
	ACCESS	read-only
	STATUS	mandatory
	DESCRIPTION	"Minutes portion of the time stamp for the channel
			periodic statistics report." 
	::= {chPeriodicStatisticsEntry 6}

chPeriodicStatisticsSeconds OBJECT-TYPE
	SYNTAX	INTEGER (0..59)
	ACCESS	read-only
	STATUS	mandatory
	DESCRIPTION	"Seconds portion of the time stamp for the channel
			periodic statistics report." 
	::= {chPeriodicStatisticsEntry 7}

chPeriodicStatisticsBuffUtilization OBJECT-TYPE
	SYNTAX	Gauge
	ACCESS	read-only
	STATUS	mandatory
	DESCRIPTION	"The buffer utilization (percentage) of the specified
			channel in the periodic statistics report. Valid only for
			Async channels, always 0 for Sync channels" 
	::= {chPeriodicStatisticsEntry 8}

chPeriodicStatisticsChannelBusiedOut OBJECT-TYPE
	SYNTAX	INTEGER {
		yes (1),
		no (2)
		}
	ACCESS	read-only
	STATUS	mandatory
	DESCRIPTION	"The busied-out condition (yes/no) of the specified
			channel in the periodic statistics report." 
	::= {chPeriodicStatisticsEntry 9}

chPeriodicStatisticsChannelInFlowControl OBJECT-TYPE
	SYNTAX	INTEGER {
		yes (1),
		no (2)
		}
	ACCESS	read-only
	STATUS	mandatory
	DESCRIPTION	"The flow control condition (yes/no = fcn of buffer utilizaton)
			of the specified channel in the periodic statistics report." 
	::= {chPeriodicStatisticsEntry 10}

-- VOICE CHANNEL PERIODIC REPORT

chVPeriodicStatisticsTable OBJECT-TYPE
	SYNTAX	SEQUENCE OF ChVPeriodicStatisticsEntry
	ACCESS	not-accessible
	STATUS	mandatory
	DESCRIPTION	"Table of voice channel statistics for periodic 
			statistics reports." 
	::= {statistics-periodic 2}

chVPeriodicStatisticsEntry OBJECT-TYPE
	SYNTAX	ChVPeriodicStatisticsEntry
	ACCESS	not-accessible
	STATUS	mandatory
	DESCRIPTION	"Entry within the table to specify a particular voice
			channel on specific voice module/card." 
	INDEX		{chVPeriodicStatisticsCardNumber, chVPeriodicStatisticsChannelNumber}
	::= {chVPeriodicStatisticsTable 1}

ChVPeriodicStatisticsEntry ::= SEQUENCE {
	chVPeriodicStatisticsCardNumber			INTEGER,
	chVPeriodicStatisticsChannelNumber		INTEGER,
	chVPeriodicStatisticsMonth			INTEGER,
	chVPeriodicStatisticsDay			INTEGER,
	chVPeriodicStatisticsHours			INTEGER,
	chVPeriodicStatisticsMinutes			INTEGER,
	chVPeriodicStatisticsSeconds			INTEGER,
	chVPeriodicStatisticsConnectTime		INTEGER,
	chVPeriodicStatisticsTotalCalls			Counter,
	chVPeriodicStatisticsAvgCallDuration		INTEGER,
	chVPeriodicStatisticsBusyOutTime		INTEGER,
	chVPeriodicStatisticsNumOfCallAttempts		Counter,
	chVPeriodicStatisticsDiscardedFrameCounts	Counter,
	chVPeriodicStatisticsTimeInFaxMode		INTEGER,
	chVPeriodicStatisticsPercentInFaxMode		Gauge
	}

chVPeriodicStatisticsCardNumber OBJECT-TYPE
	SYNTAX	INTEGER (2..5)
	ACCESS	read-only
	STATUS	mandatory
	DESCRIPTION	"Identifies the voice module/card number for the 
			voice channel specific to the periodic statistics 
			report data." 
	::= {chVPeriodicStatisticsEntry 1}

chVPeriodicStatisticsChannelNumber OBJECT-TYPE
	SYNTAX	INTEGER
	ACCESS	read-only
	STATUS	mandatory
	DESCRIPTION	"Identifies the voice channel number specific to
			 the periodic statistics report data." 
	::= {chVPeriodicStatisticsEntry 2}

chVPeriodicStatisticsMonth OBJECT-TYPE
	SYNTAX	INTEGER (1..12)
	ACCESS	read-only
	STATUS	mandatory
	DESCRIPTION	"Month portion of the time stamp for the voice 
			channel periodic statistics report." 
	::= {chVPeriodicStatisticsEntry 3}

chVPeriodicStatisticsDay OBJECT-TYPE
	SYNTAX	INTEGER (1..31)
	ACCESS	read-only
	STATUS	mandatory
	DESCRIPTION	"Day portion of the time stamp for the voice 
			channel periodic statistics report." 
	::= {chVPeriodicStatisticsEntry 4}

chVPeriodicStatisticsHours OBJECT-TYPE
	SYNTAX	INTEGER (0..23)
	ACCESS	read-only
	STATUS	mandatory
	DESCRIPTION	"Hours portion of the time stamp for the voice 
			channel periodic statistics report." 
	::= {chVPeriodicStatisticsEntry 5}

chVPeriodicStatisticsMinutes OBJECT-TYPE
	SYNTAX	INTEGER (0..59)
	ACCESS	read-only
	STATUS	mandatory
	DESCRIPTION	"Minutes portion of the time stamp for the voice 
			channel periodic statistics report." 
	::= {chVPeriodicStatisticsEntry 6}

chVPeriodicStatisticsSeconds OBJECT-TYPE
	SYNTAX	INTEGER (0..59)
	ACCESS	read-only
	STATUS	mandatory
	DESCRIPTION	"Seconds portion of the time stamp for the voice 
			channel periodic statistics report." 
	::= {chVPeriodicStatisticsEntry 7}

chVPeriodicStatisticsConnectTime OBJECT-TYPE
	SYNTAX	INTEGER
	ACCESS	read-only
	STATUS	mandatory
	DESCRIPTION	"Connect time of the specified voice channel in 
			the periodic statistics report." 
	::= {chVPeriodicStatisticsEntry 8}

chVPeriodicStatisticsTotalCalls OBJECT-TYPE
	SYNTAX	Counter
	ACCESS	read-only
	STATUS	mandatory
	DESCRIPTION	"Total calls recorded on the specified voice channel in 
			the periodic statistics report." 
	::= {chVPeriodicStatisticsEntry 9}

chVPeriodicStatisticsAvgCallDuration OBJECT-TYPE
	SYNTAX	INTEGER
	ACCESS	read-only
	STATUS	mandatory
	DESCRIPTION	"Average call duration of the specified voice channel in 
			the periodic statistics report." 
	::= {chVPeriodicStatisticsEntry 10}

chVPeriodicStatisticsBusyOutTime OBJECT-TYPE
	SYNTAX	INTEGER
	ACCESS	read-only
	STATUS	mandatory
	DESCRIPTION	"Busy Out time of the specified voice channel in 
			the periodic statistics report." 
	::= {chVPeriodicStatisticsEntry 11}

chVPeriodicStatisticsNumOfCallAttempts OBJECT-TYPE
	SYNTAX	Counter
	ACCESS	read-only
	STATUS	mandatory
	DESCRIPTION	"Number of call attempts of the specified voice
			channel in the periodic statistics report." 
	::= {chVPeriodicStatisticsEntry 12}

chVPeriodicStatisticsDiscardedFrameCounts OBJECT-TYPE
	SYNTAX	Counter
	ACCESS	read-only
	STATUS	mandatory
	DESCRIPTION	"Number of times voice frames were discarded on
			the specified voice channel in the periodic 
			statistics report." 
	::= {chVPeriodicStatisticsEntry 13}

chVPeriodicStatisticsTimeInFaxMode OBJECT-TYPE
	SYNTAX	INTEGER
	ACCESS	read-only
	STATUS	mandatory
	DESCRIPTION	"The time spent in Fax mode of the specified voice
			channel in the periodic statistics report." 
	::= {chVPeriodicStatisticsEntry 14}

chVPeriodicStatisticsPercentInFaxMode OBJECT-TYPE
	SYNTAX	Gauge
	ACCESS	read-only
	STATUS	mandatory
	DESCRIPTION	"The percentage of time spent in Fax mode of the
			specified voice	channel in the periodic statistics
			report." 
	::= {chVPeriodicStatisticsEntry 15}

-- LINK STATISTICS

linkPeriodicStatisticsTable OBJECT-TYPE
	SYNTAX	SEQUENCE OF LinkPeriodicStatisticsEntry
	ACCESS	not-accessible
	STATUS	mandatory
	DESCRIPTION	"Table of link statistics for periodic statistics 
			reports. (all link types except Frame Relay)" 
	::= {statistics-periodic 3}

linkPeriodicStatisticsEntry OBJECT-TYPE
	SYNTAX	LinkPeriodicStatisticsEntry
	ACCESS	not-accessible
	STATUS	mandatory
	DESCRIPTION	"Entry within the table to specify a particular link
			channel on specific module/card." 
	INDEX		{linkPeriodicStatisticsCardNumber, linkPeriodicStatisticsChannelNumber }
	::= {linkPeriodicStatisticsTable 1}

LinkPeriodicStatisticsEntry ::= SEQUENCE {
	linkPeriodicStatisticsCardNumber			INTEGER,
	linkPeriodicStatisticsChannelNumber			INTEGER,
	linkPeriodicStatisticsMonth				INTEGER,
	linkPeriodicStatisticsDay				INTEGER,
	linkPeriodicStatisticsHours				INTEGER,
	linkPeriodicStatisticsMinutes				INTEGER,
	linkPeriodicStatisticsSeconds				INTEGER,
	linkPeriodicStatisticsLinkType				INTEGER,
	linkPeriodicStatisticsTxFrames				Counter,
	linkPeriodicStatisticsRxFrames				Counter,
	linkPeriodicStatisticsLocCompositeUtil			Gauge,
	linkPeriodicStatisticsRemCompositeUtil			Gauge,
	linkPeriodicStatisticsLocBufferUtil			Gauge,
	linkPeriodicStatisticsRemBufferUtil			Gauge,
	linkPeriodicStatisticsLocRetransmits			Counter,
	linkPeriodicStatisticsRemRetransmits			Counter,
	linkPeriodicStatisticsLocLineAlarms			INTEGER,
	linkPeriodicStatisticsRemLineAlarms			INTEGER,
	linkPeriodicStatisticsLocTimeInSysFlowCtrl		INTEGER,
	linkPeriodicStatisticsRemTimeInSysFlowCtrl		INTEGER,
	linkPeriodicStatisticsLocTimeInSyncLossOrX21Connect	INTEGER,
	linkPeriodicStatisticsRemTimeInSyncLoss			INTEGER,
	linkPeriodicStatisticsLocTimeInCarrierLoss		INTEGER,
	linkPeriodicStatisticsRemTimeInCarrierLoss		INTEGER
	}


linkPeriodicStatisticsCardNumber OBJECT-TYPE
	SYNTAX	INTEGER (1..5)
	ACCESS	read-only
	STATUS	mandatory
	DESCRIPTION	"Identifies the module/card number for the 
			link channel specific to the periodic statistics 
			report data." 
	::= {linkPeriodicStatisticsEntry 1}

linkPeriodicStatisticsChannelNumber OBJECT-TYPE
	SYNTAX	INTEGER
	ACCESS	read-only
	STATUS	mandatory
	DESCRIPTION	"Identifies the link channel number specific to
			 the periodic statistics report data." 
	::= {linkPeriodicStatisticsEntry 2}

linkPeriodicStatisticsMonth OBJECT-TYPE
	SYNTAX	INTEGER (1..12)
	ACCESS	read-only
	STATUS	mandatory
	DESCRIPTION	"Month portion of the time stamp for the link 
			channel periodic statistics report." 
	::= {linkPeriodicStatisticsEntry 3}

linkPeriodicStatisticsDay OBJECT-TYPE
	SYNTAX	INTEGER (1..31)
	ACCESS	read-only
	STATUS	mandatory
	DESCRIPTION	"Day portion of the time stamp for the link 
			channel periodic statistics report." 
	::= {linkPeriodicStatisticsEntry 4}

linkPeriodicStatisticsHours OBJECT-TYPE
	SYNTAX	INTEGER (0..23)
	ACCESS	read-only
	STATUS	mandatory
	DESCRIPTION	"Hours portion of the time stamp for the link 
			channel periodic statistics report." 
	::= {linkPeriodicStatisticsEntry 5}

linkPeriodicStatisticsMinutes OBJECT-TYPE
	SYNTAX	INTEGER (0..59)
	ACCESS	read-only
	STATUS	mandatory
	DESCRIPTION	"Minutes portion of the time stamp for the link 
			channel periodic statistics report." 
	::= {linkPeriodicStatisticsEntry 6}

linkPeriodicStatisticsSeconds OBJECT-TYPE
	SYNTAX	INTEGER (0..59)
	ACCESS	read-only
	STATUS	mandatory
	DESCRIPTION	"Seconds portion of the time stamp for the link 
			channel periodic statistics report." 
	::= {linkPeriodicStatisticsEntry 7}

linkPeriodicStatisticsLinkType OBJECT-TYPE
	SYNTAX	INTEGER {
		esm (1),
		esi (2),
		xDot21 (3),
		localEsi (4),
		esiSecondary (5),
		frameRelay (6)
		}
	ACCESS	read-only
	STATUS	mandatory
	DESCRIPTION	"Link type of the specified link channel in 
			the periodic statistics report." 
	::= {linkPeriodicStatisticsEntry 8}

linkPeriodicStatisticsTxFrames OBJECT-TYPE
	SYNTAX	Counter
	ACCESS	read-only
	STATUS	mandatory
	DESCRIPTION	"Transmitted frames (x100) of the specified link
			channel in the periodic statistics report." 
	::= {linkPeriodicStatisticsEntry 9}

linkPeriodicStatisticsRxFrames OBJECT-TYPE
	SYNTAX	Counter
	ACCESS	read-only
	STATUS	mandatory
	DESCRIPTION	"Received frames (x100) of the specified link
			channel in the periodic statistics report." 
	::= {linkPeriodicStatisticsEntry 10}

linkPeriodicStatisticsLocCompositeUtil OBJECT-TYPE
	SYNTAX	Gauge
	ACCESS	read-only
	STATUS	mandatory
	DESCRIPTION	"Local composite utilization (percentage) of the
			specified link channel in the periodic statistics
			report." 
	::= {linkPeriodicStatisticsEntry 11}

linkPeriodicStatisticsRemCompositeUtil OBJECT-TYPE
	SYNTAX	Gauge
	ACCESS	read-only
	STATUS	mandatory
	DESCRIPTION	"Remote composite utilization (percentage) of the
			specified link channel in the periodic statistics
			report." 
	::= {linkPeriodicStatisticsEntry 12}

linkPeriodicStatisticsLocBufferUtil OBJECT-TYPE
	SYNTAX	Gauge
	ACCESS	read-only
	STATUS	mandatory
	DESCRIPTION	"Local buffer utilization (percentage) of the
			specified link channel in the periodic statistics
			report." 
	::= {linkPeriodicStatisticsEntry 13}

linkPeriodicStatisticsRemBufferUtil OBJECT-TYPE
	SYNTAX	Gauge
	ACCESS	read-only
	STATUS	mandatory
	DESCRIPTION	"Remote buffer utilization (percentage) of the
			specified link channel in the periodic statistics
			report." 
	::= {linkPeriodicStatisticsEntry 14}

linkPeriodicStatisticsLocRetransmits OBJECT-TYPE
	SYNTAX	Counter
	ACCESS	read-only
	STATUS	mandatory
	DESCRIPTION	"Local retransmits of the specified link channel 
			in the periodic statistics report." 
	::= {linkPeriodicStatisticsEntry 15}

linkPeriodicStatisticsRemRetransmits OBJECT-TYPE
	SYNTAX	Counter
	ACCESS	read-only
	STATUS	mandatory
	DESCRIPTION	"Remote retransmits of the specified link channel 
			in the periodic statistics report." 
	::= {linkPeriodicStatisticsEntry 16}

linkPeriodicStatisticsLocLineAlarms OBJECT-TYPE
	SYNTAX	INTEGER
	ACCESS	read-only
	STATUS	mandatory
	DESCRIPTION	"Local line alarms of the specified link channel 
			in the periodic statistics report." 
	::= {linkPeriodicStatisticsEntry 17}

linkPeriodicStatisticsRemLineAlarms OBJECT-TYPE
	SYNTAX	INTEGER
	ACCESS	read-only
	STATUS	mandatory
	DESCRIPTION	"Remote line alarms of the specified link channel 
			in the periodic statistics report." 
	::= {linkPeriodicStatisticsEntry 18}

linkPeriodicStatisticsLocTimeInSysFlowCtrl OBJECT-TYPE
	SYNTAX	INTEGER
	ACCESS	read-only
	STATUS	mandatory
	DESCRIPTION	"Local time (seconds) in system flow control of the 
			specified link channel in the periodic statistics
			report." 
	::= {linkPeriodicStatisticsEntry 19}

linkPeriodicStatisticsRemTimeInSysFlowCtrl OBJECT-TYPE
	SYNTAX	INTEGER
	ACCESS	read-only
	STATUS	mandatory
	DESCRIPTION	"Remote time (seconds) in system flow control of the 
			specified link channel in the periodic statistics
			report." 
	::= {linkPeriodicStatisticsEntry 20}

linkPeriodicStatisticsLocTimeInSyncLossOrX21Connect OBJECT-TYPE
	SYNTAX	INTEGER
	ACCESS	read-only
	STATUS	mandatory
	DESCRIPTION	"Local time (seconds) in sync loss of the 
			specified link channel in the periodic statistics
			report. (not used on X.21 links)" 
	::= {linkPeriodicStatisticsEntry 21}

linkPeriodicStatisticsRemTimeInSyncLoss OBJECT-TYPE
	SYNTAX	INTEGER
	ACCESS	read-only
	STATUS	mandatory
	DESCRIPTION	"Remote time (seconds) in sync loss of the 
			specified link channel in the periodic statistics
			report. (not used on X.21 links)" 
	::= {linkPeriodicStatisticsEntry 22}

linkPeriodicStatisticsLocTimeInCarrierLoss OBJECT-TYPE
	SYNTAX	INTEGER
	ACCESS	read-only
	STATUS	mandatory
	DESCRIPTION	"Local time (seconds) in carrier loss of the 
			specified link channel in the periodic statistics
			report. (not used on X.21 links)" 
	::= {linkPeriodicStatisticsEntry 23}

linkPeriodicStatisticsRemTimeInCarrierLoss OBJECT-TYPE
	SYNTAX	INTEGER
	ACCESS	read-only
	STATUS	mandatory
	DESCRIPTION	"Remote time (seconds) in carrier loss of the 
			specified link channel in the periodic statistics
			report. (not used on X.21 links)" 
	::= {linkPeriodicStatisticsEntry 24}

-- FRAME RELAY LINK STATISTICS

linkFRPeriodicStatisticsTable OBJECT-TYPE
	SYNTAX	SEQUENCE OF LinkFRPeriodicStatisticsEntry
	ACCESS	not-accessible
	STATUS	mandatory
	DESCRIPTION	"Table of Frame Relay link statistics for periodic 
			statistics reports. (Note: More periodic FR link stats
			are contained in table linkFRAccLnkPeriodicStatisticsTable.)" 
	::= {statistics-periodic 4}

linkFRPeriodicStatisticsEntry OBJECT-TYPE
	SYNTAX	LinkFRPeriodicStatisticsEntry
	ACCESS	not-accessible
	STATUS	mandatory
	DESCRIPTION	"Entry within the table to specify a particular FR link
			channel on specific module/card." 
	INDEX		{linkFRPeriodicStatisticsCardNumber, linkFRPeriodicStatisticsChannelNumber }
	::= {linkFRPeriodicStatisticsTable 1}

LinkFRPeriodicStatisticsEntry ::= SEQUENCE {
	linkFRPeriodicStatisticsCardNumber		INTEGER,
	linkFRPeriodicStatisticsChannelNumber		INTEGER,
	linkFRPeriodicStatisticsMonth			INTEGER,
	linkFRPeriodicStatisticsDay			INTEGER,
	linkFRPeriodicStatisticsHours			INTEGER,
	linkFRPeriodicStatisticsMinutes			INTEGER,
	linkFRPeriodicStatisticsSeconds			INTEGER,
	linkFRPeriodicStatisticsCRCErrs			Counter,
	linkFRPeriodicStatisticsLostStatusMsgCounts	Counter,
	linkFRPeriodicStatisticsStatusMsgProtocolErrs	Counter,
	linkFRPeriodicStatisticsNetworkResets		Counter,
	linkFRPeriodicStatisticsLinkResets		Counter,
	linkFRPeriodicStatisticsNumOfDLCIs		INTEGER
	}

linkFRPeriodicStatisticsCardNumber OBJECT-TYPE
	SYNTAX	INTEGER (1..5)
	ACCESS	read-only
	STATUS	mandatory
	DESCRIPTION	"Identifies the module/card number for the FR
			link channel specific to the periodic statistics 
			report data." 
	::= {linkFRPeriodicStatisticsEntry 1}

linkFRPeriodicStatisticsChannelNumber OBJECT-TYPE
	SYNTAX	INTEGER
	ACCESS	read-only
	STATUS	mandatory
	DESCRIPTION	"Identifies the FR link channel number specific to
			 the periodic statistics report data." 
	::= {linkFRPeriodicStatisticsEntry 2}

linkFRPeriodicStatisticsMonth OBJECT-TYPE
	SYNTAX	INTEGER
	ACCESS	read-only
	STATUS	mandatory
	DESCRIPTION	"Month portion of the time stamp for the FR link 
			channel periodic statistics report." 
	::= {linkFRPeriodicStatisticsEntry 3}
	
linkFRPeriodicStatisticsDay OBJECT-TYPE
	SYNTAX	INTEGER
	ACCESS	read-only
	STATUS	mandatory
	DESCRIPTION	"Day portion of the time stamp for the FR link 
			channel periodic statistics report." 
	::= {linkFRPeriodicStatisticsEntry 4}

linkFRPeriodicStatisticsHours OBJECT-TYPE
	SYNTAX	INTEGER
	ACCESS	read-only
	STATUS	mandatory
	DESCRIPTION	"Hours portion of the time stamp for the FR link 
			channel periodic statistics report." 
	::= {linkFRPeriodicStatisticsEntry 5}

linkFRPeriodicStatisticsMinutes OBJECT-TYPE
	SYNTAX	INTEGER
	ACCESS	read-only
	STATUS	mandatory
	DESCRIPTION	"Minutes portion of the time stamp for the FR link 
			channel periodic statistics report." 
	::= {linkFRPeriodicStatisticsEntry 6}

linkFRPeriodicStatisticsSeconds OBJECT-TYPE
	SYNTAX	INTEGER
	ACCESS	read-only
	STATUS	mandatory
	DESCRIPTION	"Seconds portion of the time stamp for the FR link 
			channel periodic statistics report." 
	::= {linkFRPeriodicStatisticsEntry 7}

linkFRPeriodicStatisticsCRCErrs OBJECT-TYPE
	SYNTAX	Counter
	ACCESS	read-only
	STATUS	mandatory
	DESCRIPTION	"CRC errors on the specified FR link access
			channel in the periodic statistics report." 
	::= {linkFRPeriodicStatisticsEntry 8}

linkFRPeriodicStatisticsLostStatusMsgCounts OBJECT-TYPE
	SYNTAX	Counter
	ACCESS	read-only
	STATUS	mandatory
	DESCRIPTION	"Lost status messsage count of the specified FR 
			link channel in the periodic statistics report." 
	::= {linkFRPeriodicStatisticsEntry 9}

linkFRPeriodicStatisticsStatusMsgProtocolErrs OBJECT-TYPE
	SYNTAX	Counter
	ACCESS	read-only
	STATUS	mandatory
	DESCRIPTION	"Status message protocol errors of the specified FR 
			link channel in the periodic statistics report." 
	::= {linkFRPeriodicStatisticsEntry 10}

linkFRPeriodicStatisticsNetworkResets OBJECT-TYPE
	SYNTAX	Counter
	ACCESS	read-only
	STATUS	mandatory
	DESCRIPTION	"Resets initiated by the network of the specified FR 
			link channel in the periodic statistics report." 
	::= {linkFRPeriodicStatisticsEntry 11}

linkFRPeriodicStatisticsLinkResets OBJECT-TYPE
	SYNTAX	Counter
	ACCESS	read-only
	STATUS	mandatory
	DESCRIPTION	"Resets initiated by the Marathon of the specified FR 
			link channel in the periodic statistics report." 
	::= {linkFRPeriodicStatisticsEntry 12}

linkFRPeriodicStatisticsNumOfDLCIs OBJECT-TYPE
	SYNTAX	INTEGER
	ACCESS	read-only
	STATUS	mandatory
	DESCRIPTION	"Number of configured DLCIs for the specified FR 
			link channel in the periodic statistics report." 
	::= {linkFRPeriodicStatisticsEntry 13}

-- FRAME RELAY  DLCI STATISTICS

linkFRDLCIPeriodicStatisticsTable OBJECT-TYPE
	SYNTAX	SEQUENCE OF LinkFRDLCIPeriodicStatisticsEntry
	ACCESS	not-accessible
	STATUS	mandatory
	DESCRIPTION	"Table of Frame Relay link DLCI channel statistics for
			periodic statistics reports." 
	::= {statistics-periodic 5}

linkFRDLCIPeriodicStatisticsEntry OBJECT-TYPE
	SYNTAX	LinkFRDLCIPeriodicStatisticsEntry
	ACCESS	not-accessible
	STATUS	mandatory
	DESCRIPTION	"Entry within the table to specify a particular FR link
			channel on specific module/card for specific DLCI number." 
	INDEX		{ linkFRDLCIPeriodicStatisticsCardNumber, 
			linkFRDLCIPeriodicStatisticsChannelNumber,
			linkFRDLCIPeriodicStatisticsDLCINumber}
	::= {linkFRDLCIPeriodicStatisticsTable 1}

LinkFRDLCIPeriodicStatisticsEntry ::= SEQUENCE {
	linkFRDLCIPeriodicStatisticsCardNumber			INTEGER,
	linkFRDLCIPeriodicStatisticsChannelNumber		INTEGER,
	linkFRDLCIPeriodicStatisticsDLCINumber			INTEGER,
	linkFRDLCIPeriodicStatisticsMonth			INTEGER,
	linkFRDLCIPeriodicStatisticsDay				INTEGER,
	linkFRDLCIPeriodicStatisticsHours			INTEGER,
	linkFRDLCIPeriodicStatisticsMinutes			INTEGER,
	linkFRDLCIPeriodicStatisticsSeconds			INTEGER,
	linkFRDLCIPeriodicStatisticsTxCharacters		Counter,
	linkFRDLCIPeriodicStatisticsRxCharacters		Counter,
	linkFRDLCIPeriodicStatisticsTxFrames			Counter,
	linkFRDLCIPeriodicStatisticsRxFrames			Counter,
	linkFRDLCIPeriodicStatisticsTimeActive			INTEGER,
	linkFRDLCIPeriodicStatisticsTimeCongestedForward	INTEGER,
	linkFRDLCIPeriodicStatisticsTimeCongestedBackward	INTEGER
	}

linkFRDLCIPeriodicStatisticsCardNumber OBJECT-TYPE
	SYNTAX	INTEGER (1..5)
	ACCESS	read-only
	STATUS	mandatory
	DESCRIPTION	"Identifies the module/card number for the FR link 
			channel and DLCI number specific to the periodic 
			statistics report data." 
	::= {linkFRDLCIPeriodicStatisticsEntry 1}

linkFRDLCIPeriodicStatisticsChannelNumber OBJECT-TYPE
	SYNTAX	INTEGER
	ACCESS	read-only
	STATUS	mandatory
	DESCRIPTION	"Identifies the FR link channel number for the DLCI 
			number specific to the periodic statistics report data." 
	::= {linkFRDLCIPeriodicStatisticsEntry 2}

linkFRDLCIPeriodicStatisticsDLCINumber OBJECT-TYPE
	SYNTAX	INTEGER
	ACCESS	read-only
	STATUS	mandatory
	DESCRIPTION	"Identifies the DCLI number specific to
			 the periodic statistics report data." 
	::= {linkFRDLCIPeriodicStatisticsEntry 3}

linkFRDLCIPeriodicStatisticsMonth OBJECT-TYPE
	SYNTAX	INTEGER (1..12)
	ACCESS	read-only
	STATUS	mandatory
	DESCRIPTION	"Month portion of the time stamp for the FR link 
			DLCI periodic statistics report." 
	::= { linkFRDLCIPeriodicStatisticsEntry 4}

linkFRDLCIPeriodicStatisticsDay OBJECT-TYPE
	SYNTAX	INTEGER (1..31)
	ACCESS	read-only
	STATUS	mandatory
	DESCRIPTION	"Days portion of the time stamp for the FR link 
			DLCI periodic statistics report." 
	::= { linkFRDLCIPeriodicStatisticsEntry 5}

linkFRDLCIPeriodicStatisticsHours OBJECT-TYPE
	SYNTAX	INTEGER (0..23)
	ACCESS	read-only
	STATUS	mandatory
	DESCRIPTION	"Hours portion of the time stamp for the FR link 
			DLCI periodic statistics report." 
	::= { linkFRDLCIPeriodicStatisticsEntry 6}

linkFRDLCIPeriodicStatisticsMinutes OBJECT-TYPE
	SYNTAX	INTEGER (0..59)
	ACCESS	read-only
	STATUS	mandatory
	DESCRIPTION	"Minutes portion of the time stamp for the FR link 
			DLCI periodic statistics report." 
	::= { linkFRDLCIPeriodicStatisticsEntry 7}

linkFRDLCIPeriodicStatisticsSeconds OBJECT-TYPE
	SYNTAX	INTEGER (0..59)
	ACCESS	read-only
	STATUS	mandatory
	DESCRIPTION	"Seconds portion of the time stamp for the FR link 
			DLCI periodic statistics report.." 
	::= { linkFRDLCIPeriodicStatisticsEntry 8}

linkFRDLCIPeriodicStatisticsTxCharacters OBJECT-TYPE
	SYNTAX	Counter
	ACCESS	read-only
	STATUS	mandatory
	DESCRIPTION	"Transmitted character count of the specified DLCI
			in the periodic statistics report." 
	::= { linkFRDLCIPeriodicStatisticsEntry 9}

linkFRDLCIPeriodicStatisticsRxCharacters OBJECT-TYPE
	SYNTAX	Counter
	ACCESS	read-only
	STATUS	mandatory
	DESCRIPTION	"Received character count of the specified DLCI
			in the periodic statistics report." 
	::= { linkFRDLCIPeriodicStatisticsEntry 10}

linkFRDLCIPeriodicStatisticsTxFrames OBJECT-TYPE
	SYNTAX	Counter
	ACCESS	read-only
	STATUS	mandatory
	DESCRIPTION	"Transmitted frames count of the specified DLCI
			in the periodic statistics report." 
	::= { linkFRDLCIPeriodicStatisticsEntry 11}

linkFRDLCIPeriodicStatisticsRxFrames OBJECT-TYPE
	SYNTAX	Counter
	ACCESS	read-only
	STATUS	mandatory
	DESCRIPTION	"Received frames count of the specified DLCI
			in the periodic statistics report." 
	::= { linkFRDLCIPeriodicStatisticsEntry 12}

linkFRDLCIPeriodicStatisticsTimeActive OBJECT-TYPE
	SYNTAX	INTEGER
	ACCESS	read-only
	STATUS	mandatory
	DESCRIPTION	"Time active (seconds) of the specified DLCI
			in the periodic statistics report." 
	::= { linkFRDLCIPeriodicStatisticsEntry 13}

linkFRDLCIPeriodicStatisticsTimeCongestedForward OBJECT-TYPE
	SYNTAX	INTEGER
	ACCESS	read-only
	STATUS	mandatory
	DESCRIPTION	"Time congested forward (seconds) of the specified 
			DLCI in the periodic statistics report." 
	::= { linkFRDLCIPeriodicStatisticsEntry 14}

linkFRDLCIPeriodicStatisticsTimeCongestedBackward OBJECT-TYPE
	SYNTAX	INTEGER
	ACCESS	read-only
	STATUS	mandatory
	DESCRIPTION	"Time congested backward (seconds) of the specified 
			DLCI in the periodic statistics report." 
	::= { linkFRDLCIPeriodicStatisticsEntry 15}


-- SWITCH STATISTICS

swPeriodicStatisticsNumOfCurrentConnects OBJECT-TYPE
	SYNTAX	INTEGER
	ACCESS	read-only
	STATUS	mandatory
	DESCRIPTION	"Number of current connects for the periodic
			statistics report." 
	::= {statistics-periodic 6}

swPeriodicStatisticsTable OBJECT-TYPE
	SYNTAX	SEQUENCE OF SwPeriodicStatisticsEntry
	ACCESS	not-accessible
	STATUS	mandatory
	DESCRIPTION	"Table of switch statistics for periodic 
			statistics reports." 
	::= {statistics-periodic 7}

swPeriodicStatisticsEntry OBJECT-TYPE
	SYNTAX	SwPeriodicStatisticsEntry
	ACCESS	not-accessible
	STATUS	mandatory
	DESCRIPTION	"Entry within the table to specify a particular
			class number." 
	INDEX		{swPeriodicStatisticsClassNumber}
	::= {swPeriodicStatisticsTable 1}

SwPeriodicStatisticsEntry ::= SEQUENCE {
	swPeriodicStatisticsClassNumber			INTEGER,
	swPeriodicStatisticsMonth			INTEGER,
	swPeriodicStatisticsDay				INTEGER,
	swPeriodicStatisticsHours			INTEGER,
	swPeriodicStatisticsMinutes			INTEGER,
	swPeriodicStatisticsSeconds			INTEGER,
	swPeriodicStatisticsNumOfSuccessfulConnects	Counter,
	swPeriodicStatisticsNumOfUnsuccessfulAttempts	Counter,
	swPeriodicStatisticsMaxNumInQueue		INTEGER
	}

swPeriodicStatisticsClassNumber OBJECT-TYPE
	SYNTAX	INTEGER
	ACCESS	read-only
	STATUS	mandatory
	DESCRIPTION	"Identifies the class number for periodic statistics 
			report data." 
	::= {swPeriodicStatisticsEntry 1}

swPeriodicStatisticsMonth OBJECT-TYPE
	SYNTAX	INTEGER (1..12)
	ACCESS	read-only
	STATUS	mandatory
	DESCRIPTION	"Month portion of the time stamp for the switch
			statistics periodic statistics report." 
	::= {swPeriodicStatisticsEntry 2}

swPeriodicStatisticsDay OBJECT-TYPE
	SYNTAX	INTEGER (1..31)
	ACCESS	read-only
	STATUS	mandatory
	DESCRIPTION	"Day portion of the time stamp for the switch
			statistics periodic statistics report." 
	::= {swPeriodicStatisticsEntry 3}

swPeriodicStatisticsHours OBJECT-TYPE
	SYNTAX	INTEGER (0..23)
	ACCESS	read-only
	STATUS	mandatory
	DESCRIPTION	"Hours portion of the time stamp for the switch
			statistics periodic statistics report." 
	::= {swPeriodicStatisticsEntry 4}

swPeriodicStatisticsMinutes OBJECT-TYPE
	SYNTAX	INTEGER (0..59)
	ACCESS	read-only
	STATUS	mandatory
	DESCRIPTION	"Minutes portion of the time stamp for the switch
			statistics periodic statistics report." 
	::= {swPeriodicStatisticsEntry 5}

swPeriodicStatisticsSeconds OBJECT-TYPE
	SYNTAX	INTEGER (0..59)
	ACCESS	read-only
	STATUS	mandatory
	DESCRIPTION	"Seconds portion of the time stamp for the switch
			statistics periodic statistics report." 
	::= {swPeriodicStatisticsEntry 6}

swPeriodicStatisticsNumOfSuccessfulConnects OBJECT-TYPE
	SYNTAX	Counter
	ACCESS	read-only
	STATUS	mandatory
	DESCRIPTION	"Number of successful connects for the switch statistics
			periodic statistics report." 
	::= {swPeriodicStatisticsEntry 7}

swPeriodicStatisticsNumOfUnsuccessfulAttempts OBJECT-TYPE
	SYNTAX	Counter
	ACCESS	read-only
	STATUS	mandatory
	DESCRIPTION	"Number of unsuccessful connects (attempts) for the 
			switch statistics periodic statistics report." 
	::= {swPeriodicStatisticsEntry 8}

swPeriodicStatisticsMaxNumInQueue OBJECT-TYPE
	SYNTAX	INTEGER
	ACCESS	read-only
	STATUS	mandatory
	DESCRIPTION	"Maximum number in the queue during report period
			for the switch statistics periodic statistics report." 
	::= {swPeriodicStatisticsEntry 9}

-- More Frame Relay Periodic Statistics

linkFRAccLnkPeriodicStatisticsTable OBJECT-TYPE
	SYNTAX	SEQUENCE OF LinkFRPeriodicStatisticsEntry
	ACCESS	not-accessible
	STATUS	mandatory
	DESCRIPTION	"Table of Frame Relay link access channel statistics for
			periodic statistics reports. (Note: More periodic FR link
			stats are contained in table linkFRPeriodicStatisticsTable.)" 
	::= { statistics-periodic 8}

linkFRAccLnkPeriodicStatisticsEntry OBJECT-TYPE
	SYNTAX	LinkFRAccLnkPeriodicStatisticsEntry
	ACCESS	not-accessible
	STATUS	mandatory
	DESCRIPTION	"Entry within the table to specify a particular FR link
			access channel on specific module/card." 
	INDEX		{linkFRAccLnkPeriodicStatisticsCardNumber,
			linkFRAccLnkPeriodicStatisticsChannelNumber}
	::= {linkFRAccLnkPeriodicStatisticsTable 1}

LinkFRAccLnkPeriodicStatisticsEntry ::= SEQUENCE {
	linkFRAccLnkPeriodicStatisticsCardNumber			INTEGER,
	linkFRAccLnkPeriodicStatisticsChannelNumber			INTEGER,
	linkFRAccLnkPeriodicStatisticsMonth				INTEGER,
	linkFRAccLnkPeriodicStatisticsDay				INTEGER,
	linkFRAccLnkPeriodicStatisticsHours				INTEGER,
	linkFRAccLnkPeriodicStatisticsMinutes				INTEGER,
	linkFRAccLnkPeriodicStatisticsSeconds				INTEGER,
	linkFRAccLnkPeriodicStatisticsLocalCompositeUtilization		Gauge,
	linkFRAccLnkPeriodicStatisticsLocalBufferUtilization		Gauge,
	linkFRAccLnkPeriodicStatisticsLocalLineAlarms			Counter,
	linkFRAccLnkPeriodicStatisticsLocalSecInSysFlowControl		INTEGER,
	linkFRAccLnkPeriodicStatisticsLocalSecInSyncLoss		INTEGER,
	linkFRAccLnkPeriodicStatisticsLocalSecInCarrierLoss		INTEGER
	}

linkFRAccLnkPeriodicStatisticsCardNumber OBJECT-TYPE
	SYNTAX	INTEGER (1..5)
	ACCESS	read-only
	STATUS	mandatory
	DESCRIPTION	"Identifies the module/card number for the FR link
			access channel specific to the periodic statistics 
			report data." 
	::= { linkFRAccLnkPeriodicStatisticsEntry 1}

linkFRAccLnkPeriodicStatisticsChannelNumber OBJECT-TYPE
	SYNTAX	INTEGER
	ACCESS	read-only
	STATUS	mandatory
	DESCRIPTION	"Identifies the FR link access channel number specific to
			 the periodic statistics report data." 
	::= { linkFRAccLnkPeriodicStatisticsEntry 2}

linkFRAccLnkPeriodicStatisticsMonth OBJECT-TYPE
	SYNTAX	INTEGER (1..12)
	ACCESS	read-only
	STATUS	mandatory
	DESCRIPTION	"Month portion of the time stamp for the FR link 
			access channel periodic statistics report." 
	::= { linkFRAccLnkPeriodicStatisticsEntry 3}

linkFRAccLnkPeriodicStatisticsDay OBJECT-TYPE
	SYNTAX	INTEGER (1..31)
	ACCESS	read-only
	STATUS	mandatory
	DESCRIPTION	"Day portion of the time stamp for the FR link 
			access channel periodic statistics report." 
	::= { linkFRAccLnkPeriodicStatisticsEntry 4}

linkFRAccLnkPeriodicStatisticsHours OBJECT-TYPE
	SYNTAX	INTEGER (0..23)
	ACCESS	read-only
	STATUS	mandatory
	DESCRIPTION	"Hours portion of the time stamp for the FR link 
			access channel periodic statistics report." 
	::= { linkFRAccLnkPeriodicStatisticsEntry 5}

linkFRAccLnkPeriodicStatisticsMinutes OBJECT-TYPE
	SYNTAX	INTEGER (0..59)
	ACCESS	read-only
	STATUS	mandatory
	DESCRIPTION	"Minutes portion of the time stamp for the FR link 
			access channel periodic statistics report." 
	::= { linkFRAccLnkPeriodicStatisticsEntry 6}

linkFRAccLnkPeriodicStatisticsSeconds OBJECT-TYPE
	SYNTAX	INTEGER (0..59)
	ACCESS	read-only
	STATUS	mandatory
	DESCRIPTION	"Seconds portion of the time stamp for the FR link 
			access channel periodic statistics report." 
	::= { linkFRAccLnkPeriodicStatisticsEntry 7}

linkFRAccLnkPeriodicStatisticsLocalCompositeUtilization OBJECT-TYPE
	SYNTAX	Gauge
	ACCESS	read-only
	STATUS	mandatory
	DESCRIPTION	"Local composite utilization (percentage) of the specified FR 
			link access channel in the periodic statistics report." 
	::= { linkFRAccLnkPeriodicStatisticsEntry 8}

linkFRAccLnkPeriodicStatisticsLocalBufferUtilization OBJECT-TYPE
	SYNTAX	Gauge
	ACCESS	read-only
	STATUS	mandatory
	DESCRIPTION	"Local buffer utilization (percentage) of the specified FR 
			link access channel in the periodic statistics report." 
	::= { linkFRAccLnkPeriodicStatisticsEntry 9}

linkFRAccLnkPeriodicStatisticsLocalLineAlarms OBJECT-TYPE
	SYNTAX	Counter
	ACCESS	read-only
	STATUS	mandatory
	DESCRIPTION	"Local line alarms of the specified FR link access 
			channel in the periodic statistics report." 
	::= { linkFRAccLnkPeriodicStatisticsEntry 10}

linkFRAccLnkPeriodicStatisticsLocalSecInSysFlowControl OBJECT-TYPE
	SYNTAX	INTEGER
	ACCESS	read-only
	STATUS	mandatory
	DESCRIPTION	"Local seconds in system flow control of the specified
			FR link access channel in the periodic statistics report." 
	::= { linkFRAccLnkPeriodicStatisticsEntry 11}

linkFRAccLnkPeriodicStatisticsLocalSecInSyncLoss OBJECT-TYPE
	SYNTAX	INTEGER
	ACCESS	read-only
	STATUS	mandatory
	DESCRIPTION	"Local seconds in sync loss of the specified FR link
			access channel in the periodic statistics report." 
	::= { linkFRAccLnkPeriodicStatisticsEntry 12}

linkFRAccLnkPeriodicStatisticsLocalSecInCarrierLoss OBJECT-TYPE
	SYNTAX	INTEGER
	ACCESS	read-only
	STATUS	mandatory
	DESCRIPTION	"Local seconds in carrier loss of the specified
			FR link access channel in the periodic statistics report." 
	::= { linkFRAccLnkPeriodicStatisticsEntry 13}


-- N_CMOS.O_SYSIMM ==================================================

chAccumStatisticsTable OBJECT-TYPE
	SYNTAX	SEQUENCE OF ChAccumStatisticsEntry
	ACCESS	not-accessible
	STATUS	mandatory
	DESCRIPTION	"Table of channel statistics for accumlulated 
			statistics reports. (Sync & Async channels)." 
	::= {statistics-accumulated 1}

chAccumStatisticsEntry OBJECT-TYPE
	SYNTAX	ChAccumStatisticsEntry
	ACCESS	not-accessible
	STATUS	mandatory
	DESCRIPTION	"Entry within the table to specify a particular
			channel on specific module/card." 
	INDEX		{chAccumStatisticsCardNumber, chAccumStatisticsChannelNumber}
	::= {chAccumStatisticsTable 1}

ChAccumStatisticsEntry ::= SEQUENCE {
	chAccumStatisticsCardNumber		INTEGER,
	chAccumStatisticsChannelNumber		INTEGER,
	chAccumStatisticsMonth			INTEGER,
	chAccumStatisticsDay			INTEGER,
	chAccumStatisticsHours			INTEGER,
	chAccumStatisticsMinutes		INTEGER,
	chAccumStatisticsSeconds		INTEGER,
	chAccumStatisticsBuffUtilization	Gauge,
	chAccumStatisticsChannelBusiedOut	INTEGER,
	chAccumStatisticsChannelInFlowControl	INTEGER
	}

chAccumStatisticsCardNumber OBJECT-TYPE
	SYNTAX	INTEGER (1..5)
	ACCESS	read-only
	STATUS	mandatory
	DESCRIPTION	"Identifies the module/card number for the 
			channel specific to the accumulated statistics 
			report data." 
	::= {chAccumStatisticsEntry 1}

chAccumStatisticsChannelNumber OBJECT-TYPE
	SYNTAX	INTEGER
	ACCESS	read-only
	STATUS	mandatory
	DESCRIPTION	"Identifies the channel number specific to the
			 accumulated statistics report data." 
	::= {chAccumStatisticsEntry 2}

chAccumStatisticsMonth OBJECT-TYPE
	SYNTAX	INTEGER (1..12)
	ACCESS	read-only
	STATUS	mandatory
	DESCRIPTION	"Month portion of the time stamp for the channel
			accumulated statistics report." 
	::= {chAccumStatisticsEntry 3}

chAccumStatisticsDay OBJECT-TYPE
	SYNTAX	INTEGER (1..31)
	ACCESS	read-only
	STATUS	mandatory
	DESCRIPTION	"Day portion of the time stamp for the channel
			accumulated statistics report." 
	::= {chAccumStatisticsEntry 4}

chAccumStatisticsHours OBJECT-TYPE
	SYNTAX	INTEGER (0..23)
	ACCESS	read-only
	STATUS	mandatory
	DESCRIPTION	"Hours portion of the time stamp for the channel
			accumulated statistics report." 
	::= {chAccumStatisticsEntry 5}

chAccumStatisticsMinutes OBJECT-TYPE
	SYNTAX	INTEGER (0..59)
	ACCESS	read-only
	STATUS	mandatory
	DESCRIPTION	"Minutes portion of the time stamp for the channel
			accumulated statistics report." 
	::= {chAccumStatisticsEntry 6}

chAccumStatisticsSeconds OBJECT-TYPE
	SYNTAX	INTEGER (0..59)
	ACCESS	read-only
	STATUS	mandatory
	DESCRIPTION	"Seconds portion of the time stamp for the channel
			accumulated statistics report." 
	::= {chAccumStatisticsEntry 7}

chAccumStatisticsBuffUtilization OBJECT-TYPE
	SYNTAX	Gauge
	ACCESS	read-only
	STATUS	mandatory
	DESCRIPTION	"The buffer utilization (percentage) of the specified
			channel in the accumulated statistics report. Valid only for
			Async channels, always 0 for Sync channels" 
	::= {chAccumStatisticsEntry 8}

chAccumStatisticsChannelBusiedOut OBJECT-TYPE
	SYNTAX	INTEGER {
		yes (1),
		no (2)
		}
	ACCESS	read-only
	STATUS	mandatory
	DESCRIPTION	"The busied-out condition (yes/no) of the specified
			channel in the accumulated statistics report." 
	::= {chAccumStatisticsEntry 9}

chAccumStatisticsChannelInFlowControl OBJECT-TYPE
	SYNTAX	INTEGER {
		yes (1),
		no (2)
		}
	ACCESS	read-only
	STATUS	mandatory
	DESCRIPTION	"The flow control condition (yes/no = fcn of buffer utilizaton)
			of the specified channel in the accumulated statistics report." 
	::= {chAccumStatisticsEntry 10}

-- VOICE CHANNEL ACCUM REPORT

chVAccumStatisticsTable OBJECT-TYPE
	SYNTAX	SEQUENCE OF ChVAccumStatisticsEntry
	ACCESS	not-accessible
	STATUS	mandatory
	DESCRIPTION	"Table of voice channel statistics for accumulated 
			statistics reports." 
	::= {statistics-accumulated 2}

chVAccumStatisticsEntry OBJECT-TYPE
	SYNTAX	ChVAccumStatisticsEntry
	ACCESS	not-accessible
	STATUS	mandatory
	DESCRIPTION	"Entry within the table to specify a particular voice
			channel on specific voice module/card." 
	INDEX		{chVAccumStatisticsCardNumber, chVAccumStatisticsChannelNumber}
	::= {chVAccumStatisticsTable 1}

ChVAccumStatisticsEntry ::= SEQUENCE {
	chVAccumStatisticsCardNumber			INTEGER,
	chVAccumStatisticsChannelNumber			INTEGER,
	chVAccumStatisticsMonth				INTEGER,
	chVAccumStatisticsDay				INTEGER,
	chVAccumStatisticsHours				INTEGER,
	chVAccumStatisticsMinutes			INTEGER,
	chVAccumStatisticsSeconds			INTEGER,
	chVAccumStatisticsConnectTime			INTEGER,
	chVAccumStatisticsTotalCalls			Counter,
	chVAccumStatisticsAvgCallDuration		INTEGER,
	chVAccumStatisticsBusyOutTime			INTEGER,
	chVAccumStatisticsNumOfCallAttempts		Counter,
	chVAccumStatisticsDiscardedFrameCounts		Counter,
	chVAccumStatisticsTimeInFaxMode			INTEGER,
	chVAccumStatisticsPercentInFaxMode		Gauge
	}

chVAccumStatisticsCardNumber OBJECT-TYPE
	SYNTAX	INTEGER (2..5)
	ACCESS	read-only
	STATUS	mandatory
	DESCRIPTION	"Identifies the voice module/card number for the 
			voice channel specific to the accumulated statistics 
			report data." 
	::= {chVAccumStatisticsEntry 1}

chVAccumStatisticsChannelNumber OBJECT-TYPE
	SYNTAX	INTEGER
	ACCESS	read-only
	STATUS	mandatory
	DESCRIPTION	"Identifies the voice channel number specific to
			 the accumulated statistics report data." 
	::= {chVAccumStatisticsEntry 2}

chVAccumStatisticsMonth OBJECT-TYPE
	SYNTAX	INTEGER (1..12)
	ACCESS	read-only
	STATUS	mandatory
	DESCRIPTION	"Month portion of the time stamp for the voice 
			channel accumulated statistics report." 
	::= {chVAccumStatisticsEntry 3}

chVAccumStatisticsDay OBJECT-TYPE
	SYNTAX	INTEGER (1..31)
	ACCESS	read-only
	STATUS	mandatory
	DESCRIPTION	"Day portion of the time stamp for the voice 
			channel accumulated statistics report." 
	::= {chVAccumStatisticsEntry 4}

chVAccumStatisticsHours OBJECT-TYPE
	SYNTAX	INTEGER (0..23)
	ACCESS	read-only
	STATUS	mandatory
	DESCRIPTION	"Hours portion of the time stamp for the voice 
			channel accumulated statistics report." 
	::= {chVAccumStatisticsEntry 5}

chVAccumStatisticsMinutes OBJECT-TYPE
	SYNTAX	INTEGER (0..59)
	ACCESS	read-only
	STATUS	mandatory
	DESCRIPTION	"Minutes portion of the time stamp for the voice 
			channel accumulated statistics report." 
	::= {chVAccumStatisticsEntry 6}

chVAccumStatisticsSeconds OBJECT-TYPE
	SYNTAX	INTEGER (0..59)
	ACCESS	read-only
	STATUS	mandatory
	DESCRIPTION	"Seconds portion of the time stamp for the voice 
			channel accumulated statistics report." 
	::= {chVAccumStatisticsEntry 7}

chVAccumStatisticsConnectTime OBJECT-TYPE
	SYNTAX	INTEGER
	ACCESS	read-only
	STATUS	mandatory
	DESCRIPTION	"Connect time of the specified voice channel in 
			the accumulated statistics report." 
	::= {chVAccumStatisticsEntry 8}

chVAccumStatisticsTotalCalls OBJECT-TYPE
	SYNTAX	Counter
	ACCESS	read-only
	STATUS	mandatory
	DESCRIPTION	"Total calls recorded on the specified voice channel in 
			the accumulated statistics report." 
	::= {chVAccumStatisticsEntry 9}

chVAccumStatisticsAvgCallDuration OBJECT-TYPE
	SYNTAX	INTEGER
	ACCESS	read-only
	STATUS	mandatory
	DESCRIPTION	"Average call duration of the specified voice channel in 
			the accumulated statistics report." 
	::= {chVAccumStatisticsEntry 10}

chVAccumStatisticsBusyOutTime OBJECT-TYPE
	SYNTAX	INTEGER
	ACCESS	read-only
	STATUS	mandatory
	DESCRIPTION	"Busy Out time of the specified voice channel in 
			the accumulated statistics report." 
	::= {chVAccumStatisticsEntry 11}

chVAccumStatisticsNumOfCallAttempts OBJECT-TYPE
	SYNTAX	Counter
	ACCESS	read-only
	STATUS	mandatory
	DESCRIPTION	"Number of call attempts of the specified voice
			channel in the accumulated statistics report." 
	::= {chVAccumStatisticsEntry 12}

chVAccumStatisticsDiscardedFrameCounts OBJECT-TYPE
	SYNTAX	Counter
	ACCESS	read-only
	STATUS	mandatory
	DESCRIPTION	"Number of times voice frames were discarded on
			the specified voice channel in the accumulated 
			statistics report." 
	::= {chVAccumStatisticsEntry 13}

chVAccumStatisticsTimeInFaxMode OBJECT-TYPE
	SYNTAX	INTEGER
	ACCESS	read-only
	STATUS	mandatory
	DESCRIPTION	"The time spent in Fax mode of the specified voice
			channel in the accumulated statistics report." 
	::= {chVAccumStatisticsEntry 14}

chVAccumStatisticsPercentInFaxMode OBJECT-TYPE
	SYNTAX	Gauge
	ACCESS	read-only
	STATUS	mandatory
	DESCRIPTION	"The percentage of time spent in Fax mode of the
			specified voice	channel in the accumulated statistics
			report." 
	::= {chVAccumStatisticsEntry 15}

-- LINK STATISTICS

linkAccumStatisticsTable OBJECT-TYPE
	SYNTAX	SEQUENCE OF LinkAccumStatisticsEntry
	ACCESS	not-accessible
	STATUS	mandatory
	DESCRIPTION	"Table of link statistics for accumulated statistics 
			reports. (all link types except Frame Relay)." 
	::= { statistics-accumulated 3}

linkAccumStatisticsEntry OBJECT-TYPE
	SYNTAX	LinkAccumStatisticsEntry
	ACCESS	not-accessible
	STATUS	mandatory
	DESCRIPTION	"Entry within the table to specify a particular link
			channel on specific module/card." 
	INDEX		{linkAccumStatisticsCardNumber, linkAccumStatisticsChannelNumber }
	::= {linkAccumStatisticsTable 1}

LinkAccumStatisticsEntry ::= SEQUENCE {
	linkAccumStatisticsCardNumber				INTEGER,
	linkAccumStatisticsChannelNumber			INTEGER,
	linkAccumStatisticsMonth				INTEGER,
	linkAccumStatisticsDay					INTEGER,
	linkAccumStatisticsHours				INTEGER,
	linkAccumStatisticsMinutes				INTEGER,
	linkAccumStatisticsSeconds				INTEGER,
	linkAccumStatisticsLinkType				INTEGER,
	linkAccumStatisticsTxFrames				Counter,
	linkAccumStatisticsRxFrames				Counter,
	linkAccumStatisticsLocCompositeUtil			Gauge,
	linkAccumStatisticsRemCompositeUtil			Gauge,
	linkAccumStatisticsLocBufferUtil			Gauge,
	linkAccumStatisticsRemBufferUtil			Gauge,
	linkAccumStatisticsLocRetransmits			Counter,
	linkAccumStatisticsRemRetransmits			Counter,
	linkAccumStatisticsLocLineAlarms			INTEGER,
	linkAccumStatisticsRemLineAlarms			INTEGER,
	linkAccumStatisticsLocTimeInSysFlowCtrl			INTEGER,
	linkAccumStatisticsRemTimeInSysFlowCtrl			INTEGER,
	linkAccumStatisticsLocTimeInSyncLossOrX21Connect	INTEGER,
	linkAccumStatisticsRemTimeInSyncLoss			INTEGER,
	linkAccumStatisticsLocTimeInCarrierLoss			INTEGER,
	linkAccumStatisticsRemTimeInCarrierLoss			INTEGER
	}

linkAccumStatisticsCardNumber OBJECT-TYPE
	SYNTAX	INTEGER (1..5)
	ACCESS	read-only
	STATUS	mandatory
	DESCRIPTION	"Identifies the module/card number for the 
			link channel specific to the accumulated statistics 
			report data." 
	::= {linkAccumStatisticsEntry 1}

linkAccumStatisticsChannelNumber OBJECT-TYPE
	SYNTAX	INTEGER
	ACCESS	read-only
	STATUS	mandatory
	DESCRIPTION	"Identifies the link channel number specific to
			 the accumulated statistics report data." 
	::= {linkAccumStatisticsEntry 2}

linkAccumStatisticsMonth OBJECT-TYPE
	SYNTAX	INTEGER (1..12)
	ACCESS	read-only
	STATUS	mandatory
	DESCRIPTION	"Month portion of the time stamp for the link 
			channel accumulated statistics report." 
	::= {linkAccumStatisticsEntry 3}

linkAccumStatisticsDay OBJECT-TYPE
	SYNTAX	INTEGER (1..31)
	ACCESS	read-only
	STATUS	mandatory
	DESCRIPTION	"Day portion of the time stamp for the link 
			channel accumulated statistics report.." 
	::= {linkAccumStatisticsEntry 4}

linkAccumStatisticsHours OBJECT-TYPE
	SYNTAX	INTEGER (0..23)
	ACCESS	read-only
	STATUS	mandatory
	DESCRIPTION	"Hours portion of the time stamp for the link 
			channel accumulated statistics report.." 
	::= {linkAccumStatisticsEntry 5}

linkAccumStatisticsMinutes OBJECT-TYPE
	SYNTAX	INTEGER (0..59)
	ACCESS	read-only
	STATUS	mandatory
	DESCRIPTION	"Minutes portion of the time stamp for the link 
			channel accumulated statistics report.." 
	::= {linkAccumStatisticsEntry 6}

linkAccumStatisticsSeconds OBJECT-TYPE
	SYNTAX	INTEGER (0..59)
	ACCESS	read-only
	STATUS	mandatory
	DESCRIPTION	"Seconds portion of the time stamp for the link 
			channel accumulated statistics report.." 
	::= {linkAccumStatisticsEntry 7}

linkAccumStatisticsLinkType OBJECT-TYPE
	SYNTAX	INTEGER {
		esm (1),
		esi (2),
		xDot21 (3),
		localEsi (4),
		esiSecondary (5),
		frameRelay (6)
		}
	ACCESS	read-only
	STATUS	mandatory
	DESCRIPTION	"Link type of the specified link channel in 
			the accumulated statistics report." 
	::= {linkAccumStatisticsEntry 8}

linkAccumStatisticsTxFrames OBJECT-TYPE
	SYNTAX	Counter
	ACCESS	read-only
	STATUS	mandatory
	DESCRIPTION	"Transmitted frames (x100) of the specified link
			channel in the accumulated statistics report." 
	::= {linkAccumStatisticsEntry 9}

linkAccumStatisticsRxFrames OBJECT-TYPE
	SYNTAX	Counter
	ACCESS	read-only
	STATUS	mandatory
	DESCRIPTION	"Received frames (x100) of the specified link
			channel in the accumulated statistics report." 
	::= {linkAccumStatisticsEntry 10}

linkAccumStatisticsLocCompositeUtil OBJECT-TYPE
	SYNTAX	Gauge
	ACCESS	read-only
	STATUS	mandatory
	DESCRIPTION	"Local composite utilization (percentage) of the
			specified link channel in the accumulated statistics
			report." 
	::= {linkAccumStatisticsEntry 11}

linkAccumStatisticsRemCompositeUtil OBJECT-TYPE
	SYNTAX	Gauge
	ACCESS	read-only
	STATUS	mandatory
	DESCRIPTION	"Remote composite utilization (percentage) of the
			specified link channel in the accumulated statistics
			report." 
	::= {linkAccumStatisticsEntry 12}

linkAccumStatisticsLocBufferUtil OBJECT-TYPE
	SYNTAX	Gauge
	ACCESS	read-only
	STATUS	mandatory
	DESCRIPTION	"Local buffer utilization (percentage) of the
			specified link channel in the accumulated statistics
			report." 
	::= {linkAccumStatisticsEntry 13}

linkAccumStatisticsRemBufferUtil OBJECT-TYPE
	SYNTAX	Gauge
	ACCESS	read-only
	STATUS	mandatory
	DESCRIPTION	"Remote buffer utilization (percentage) of the
			specified link channel in the accumulated statistics
			report." 
	::= {linkAccumStatisticsEntry 14}

linkAccumStatisticsLocRetransmits OBJECT-TYPE
	SYNTAX	Counter
	ACCESS	read-only
	STATUS	mandatory
	DESCRIPTION	"Local retransmits of the specified link channel 
			in the accumulated statistics report." 
	::= {linkAccumStatisticsEntry 15}

linkAccumStatisticsRemRetransmits OBJECT-TYPE
	SYNTAX	Counter
	ACCESS	read-only
	STATUS	mandatory
	DESCRIPTION	"Remote retransmits of the specified link channel 
			in the accumulated statistics report." 
	::= {linkAccumStatisticsEntry 16}

linkAccumStatisticsLocLineAlarms OBJECT-TYPE
	SYNTAX	INTEGER
	ACCESS	read-only
	STATUS	mandatory
	DESCRIPTION	"Local line alarms of the specified link channel 
			in the accumulated statistics report." 
	::= {linkAccumStatisticsEntry 17}

linkAccumStatisticsRemLineAlarms OBJECT-TYPE
	SYNTAX	INTEGER
	ACCESS	read-only
	STATUS	mandatory
	DESCRIPTION	"Remote line alarms of the specified link channel 
			in the accumulated statistics report." 
	::= {linkAccumStatisticsEntry 18}

linkAccumStatisticsLocTimeInSysFlowCtrl OBJECT-TYPE
	SYNTAX	INTEGER
	ACCESS	read-only
	STATUS	mandatory
	DESCRIPTION	"Local time (seconds) in system flow control of the 
			specified link channel in the accumulated statistics
			report." 
	::= {linkAccumStatisticsEntry 19}

linkAccumStatisticsRemTimeInSysFlowCtrl OBJECT-TYPE
	SYNTAX	INTEGER
	ACCESS	read-only
	STATUS	mandatory
	DESCRIPTION	"Remote time (seconds) in system flow control of the 
			specified link channel in the accumulated statistics
			report." 
	::= {linkAccumStatisticsEntry 20}

linkAccumStatisticsLocTimeInSyncLossOrX21Connect OBJECT-TYPE
	SYNTAX	INTEGER
	ACCESS	read-only
	STATUS	mandatory
	DESCRIPTION	"Local time (seconds) in sync loss of the 
			specified link channel in the accumulated statistics
			report. (not used on X.21 links)." 
	::= {linkAccumStatisticsEntry 21}

linkAccumStatisticsRemTimeInSyncLoss OBJECT-TYPE
	SYNTAX	INTEGER
	ACCESS	read-only
	STATUS	mandatory
	DESCRIPTION	"Remote time (seconds) in sync loss of the 
			specified link channel in the accumulated statistics
			report. (not used on X.21 links)" 
	::= {linkAccumStatisticsEntry 22}

linkAccumStatisticsLocTimeInCarrierLoss OBJECT-TYPE
	SYNTAX	INTEGER
	ACCESS	read-only
	STATUS	mandatory
	DESCRIPTION	"Local time (seconds) in carrier loss of the 
			specified link channel in the accumulated statistics
			report. (not used on X.21 links)" 
	::= {linkAccumStatisticsEntry 23}

linkAccumStatisticsRemTimeInCarrierLoss OBJECT-TYPE
	SYNTAX	INTEGER
	ACCESS	read-only
	STATUS	mandatory
	DESCRIPTION	"Remote time (seconds) in carrier loss of the 
			specified link channel in the accumulated statistics
			report. (not used on X.21 links)" 
	::= {linkAccumStatisticsEntry 24}

-- FRAME RELAY LINK STATISTICS

linkFRAccumStatisticsTable OBJECT-TYPE
	SYNTAX	SEQUENCE OF LinkFRAccumStatisticsEntry
	ACCESS	not-accessible
	STATUS	mandatory
	DESCRIPTION	"Table of Frame Relay link statistics for accumulated 
			statistics reports. (Note: More accumulated FR link stats
			are contained in table linkFRAccLnkAccumStatisticsTable.)" 
	::= { statistics-accumulated 4}

linkFRAccumStatisticsEntry OBJECT-TYPE
	SYNTAX	LinkFRAccumStatisticsEntry
	ACCESS	not-accessible
	STATUS	mandatory
	DESCRIPTION	"Entry within the table to specify a particular FR link
			channel on specific module/card." 
	INDEX		{linkFRAccumStatisticsCardNumber, linkFRAccumStatisticsChannelNumber }
	::= {linkFRAccumStatisticsTable 1}

LinkFRAccumStatisticsEntry ::= SEQUENCE {
	linkFRAccumStatisticsCardNumber		INTEGER,
	linkFRAccumStatisticsChannelNumber		INTEGER,
	linkFRAccumStatisticsMonth			INTEGER,
	linkFRAccumStatisticsDay			INTEGER,
	linkFRAccumStatisticsHours			INTEGER,
	linkFRAccumStatisticsMinutes			INTEGER,
	linkFRAccumStatisticsSeconds			INTEGER,
	linkFRAccumStatisticsCRCErrs			Counter,
	linkFRAccumStatisticsLostStatusMsgCounts	Counter,
	linkFRAccumStatisticsStatusMsgProtocolErrs	Counter,
	linkFRAccumStatisticsNetworkResets		Counter,
	linkFRAccumStatisticsLinkResets			Counter,
	linkFRAccumStatisticsNumOfDLCIs		INTEGER
	}

linkFRAccumStatisticsCardNumber OBJECT-TYPE
	SYNTAX	INTEGER (1..5)
	ACCESS	read-only
	STATUS	mandatory
	DESCRIPTION	"Identifies the module/card number for the FR
			link channel specific to the accumulated statistics 
			report data." 
	::= {linkFRAccumStatisticsEntry 1}

linkFRAccumStatisticsChannelNumber	OBJECT-TYPE
	SYNTAX	INTEGER
	ACCESS	read-only
	STATUS	mandatory
	DESCRIPTION	"Identifies the FR link channel number specific to
			 the accumulated statistics report data." 
	::= {linkFRAccumStatisticsEntry 2}

linkFRAccumStatisticsMonth OBJECT-TYPE
	SYNTAX	INTEGER
	ACCESS	read-only
	STATUS	mandatory
	DESCRIPTION	"Month portion of the time stamp for the FR link 
			channel accumulated statistics report." 
	::= {linkFRAccumStatisticsEntry 3}
	
linkFRAccumStatisticsDay OBJECT-TYPE
	SYNTAX	INTEGER
	ACCESS	read-only
	STATUS	mandatory
	DESCRIPTION	"Day portion of the time stamp for the FR link 
			channel accumulated statistics report." 
	::= {linkFRAccumStatisticsEntry 4}

linkFRAccumStatisticsHours OBJECT-TYPE
	SYNTAX	INTEGER
	ACCESS	read-only
	STATUS	mandatory
	DESCRIPTION	"Hours portion of the time stamp for the FR link 
			channel accumulated statistics report." 
	::= {linkFRAccumStatisticsEntry 5}

linkFRAccumStatisticsMinutes OBJECT-TYPE
	SYNTAX	INTEGER
	ACCESS	read-only
	STATUS	mandatory
	DESCRIPTION	"Minutes portion of the time stamp for the FR link 
			channel accumulated statistics report." 
	::= {linkFRAccumStatisticsEntry 6}

linkFRAccumStatisticsSeconds OBJECT-TYPE
	SYNTAX	INTEGER
	ACCESS	read-only
	STATUS	mandatory
	DESCRIPTION	"Seconds portion of the time stamp for the FR link 
			channel accumulated statistics report." 
	::= {linkFRAccumStatisticsEntry 7}

linkFRAccumStatisticsCRCErrs OBJECT-TYPE
	SYNTAX	Counter
	ACCESS	read-only
	STATUS	mandatory
	DESCRIPTION	"CRC errors on the specified FR link access
			channel in the accumulated statistics report." 
	::= {linkFRAccumStatisticsEntry 8}

linkFRAccumStatisticsLostStatusMsgCounts OBJECT-TYPE
	SYNTAX	Counter
	ACCESS	read-only
	STATUS	mandatory
	DESCRIPTION	"Lost status messsage count of the specified FR 
			link channel in the accumulated statistics report." 
	::= {linkFRAccumStatisticsEntry 9}

linkFRAccumStatisticsStatusMsgProtocolErrs OBJECT-TYPE
	SYNTAX	Counter
	ACCESS	read-only
	STATUS	mandatory
	DESCRIPTION	"Status message protocol errors of the specified FR 
			link channel in the accumulated statistics report." 
	::= {linkFRAccumStatisticsEntry 10}

linkFRAccumStatisticsNetworkResets OBJECT-TYPE
	SYNTAX	Counter
	ACCESS	read-only
	STATUS	mandatory
	DESCRIPTION	"Resets initiated by the network of the specified FR 
			link channel in the accumulated statistics report." 
	::= {linkFRAccumStatisticsEntry 11}

linkFRAccumStatisticsLinkResets OBJECT-TYPE
	SYNTAX	Counter
	ACCESS	read-only
	STATUS	mandatory
	DESCRIPTION	"Resets initiated by the Marathon of the specified FR 
			link channel in the accumulated statistics report." 
	::= {linkFRAccumStatisticsEntry 12}

linkFRAccumStatisticsNumOfDLCIs OBJECT-TYPE
	SYNTAX	INTEGER
	ACCESS	read-only
	STATUS	mandatory
	DESCRIPTION	"Number of configured DLCIs for the specified FR 
			link channel in the accumulated statistics report." 
	::= {linkFRAccumStatisticsEntry 13}

-- FRAME RELAY  DLCI STATISTICS

linkFRDLCIAccumStatisticsTable OBJECT-TYPE
	SYNTAX	SEQUENCE OF LinkFRDLCIAccumStatisticsEntry
	ACCESS	not-accessible
	STATUS	mandatory
	DESCRIPTION	"Table of Frame Relay link DLCI channel statistics for
			accumulated statistics reports." 
	::= { statistics-accumulated  5}

linkFRDLCIAccumStatisticsEntry OBJECT-TYPE
	SYNTAX	LinkFRDLCIAccumStatisticsEntry
	ACCESS	not-accessible
	STATUS	mandatory
	DESCRIPTION	"Entry within the table to specify a particular FR link
			channel on specific module/card for specific DLCI number." 
	INDEX		{ linkFRDLCIAccumStatisticsCardNumber, 			
			linkFRDLCIAccumStatisticsChannelNumber,
			linkFRDLCIAccumStatisticsDLCINumber}
	::= {linkFRDLCIAccumStatisticsTable 1}

LinkFRDLCIAccumStatisticsEntry ::= SEQUENCE {
	linkFRDLCIAccumStatisticsCardNumber			INTEGER,
	linkFRDLCIAccumStatisticsChannelNumber			INTEGER,
	linkFRDLCIAccumStatisticsDLCINumber			INTEGER,
	linkFRDLCIAccumStatisticsMonth				INTEGER,
	linkFRDLCIAccumStatisticsDay				INTEGER,
	linkFRDLCIAccumStatisticsHours				INTEGER,
	linkFRDLCIAccumStatisticsMinutes			INTEGER,
	linkFRDLCIAccumStatisticsSeconds			INTEGER,
	linkFRDLCIAccumStatisticsTxCharacters			Counter,
	linkFRDLCIAccumStatisticsRxCharacters			Counter,
	linkFRDLCIAccumStatisticsTxFrames			Counter,
	linkFRDLCIAccumStatisticsRxFrames			Counter,
	linkFRDLCIAccumStatisticsTimeActive			INTEGER,
	linkFRDLCIAccumStatisticsTimeCongestedForward		INTEGER,
	linkFRDLCIAccumStatisticsTimeCongestedBackward		INTEGER
	}

linkFRDLCIAccumStatisticsCardNumber OBJECT-TYPE
	SYNTAX	INTEGER (1..5)
	ACCESS	read-only
	STATUS	mandatory
	DESCRIPTION	"Identifies the module/card number for the FR link 
			channel and DLCI number specific to the accumulated 
			statistics report data." 
	::= {linkFRDLCIAccumStatisticsEntry 1}

linkFRDLCIAccumStatisticsChannelNumber OBJECT-TYPE
	SYNTAX	INTEGER
	ACCESS	read-only
	STATUS	mandatory
	DESCRIPTION	"Identifies the FR link channel number for the DLCI 
			number specific to the accumulated statistics report data." 
	::= {linkFRDLCIAccumStatisticsEntry 2}

linkFRDLCIAccumStatisticsDLCINumber OBJECT-TYPE
	SYNTAX	INTEGER
	ACCESS	read-only
	STATUS	mandatory
	DESCRIPTION	"Identifies the DCLI number specific to
			 the accumulated statistics report data." 
	::= {linkFRDLCIAccumStatisticsEntry 3}

linkFRDLCIAccumStatisticsMonth OBJECT-TYPE
	SYNTAX	INTEGER (1..12)
	ACCESS	read-only
	STATUS	mandatory
	DESCRIPTION	"Month portion of the time stamp for the FR link 
			DLCI accumulated statistics report." 
	::= { linkFRDLCIAccumStatisticsEntry 4}

linkFRDLCIAccumStatisticsDay OBJECT-TYPE
	SYNTAX	INTEGER (1..31)
	ACCESS	read-only
	STATUS	mandatory
	DESCRIPTION	"Day portion of the time stamp for the FR link 
			DLCI accumulated statistics report." 
	::= { linkFRDLCIAccumStatisticsEntry 5}

linkFRDLCIAccumStatisticsHours OBJECT-TYPE
	SYNTAX	INTEGER (0..23)
	ACCESS	read-only
	STATUS	mandatory
	DESCRIPTION	"Hours portion of the time stamp for the FR link 
			DLCI accumulated statistics report." 
	::= { linkFRDLCIAccumStatisticsEntry 6}

linkFRDLCIAccumStatisticsMinutes OBJECT-TYPE
	SYNTAX	INTEGER (0..59)
	ACCESS	read-only
	STATUS	mandatory
	DESCRIPTION	"Minutes portion of the time stamp for the FR link 
			DLCI accumulated statistics report." 
	::= { linkFRDLCIAccumStatisticsEntry 7}

linkFRDLCIAccumStatisticsSeconds OBJECT-TYPE
	SYNTAX	INTEGER (0..59)
	ACCESS	read-only
	STATUS	mandatory
	DESCRIPTION	"Seconds portion of the time stamp for the FR link 
			DLCI accumulated statistics report." 
	::= { linkFRDLCIAccumStatisticsEntry 8}

linkFRDLCIAccumStatisticsTxCharacters OBJECT-TYPE
	SYNTAX	Counter
	ACCESS	read-only
	STATUS	mandatory
	DESCRIPTION	"Transmitted character count of the specified DLCI
			in the accumulated statistics report." 
	::= { linkFRDLCIAccumStatisticsEntry 9}

linkFRDLCIAccumStatisticsRxCharacters OBJECT-TYPE
	SYNTAX	Counter
	ACCESS	read-only
	STATUS	mandatory
	DESCRIPTION	"Received character count of the specified DLCI
			in the accumulated statistics report." 
	::= { linkFRDLCIAccumStatisticsEntry 10}

linkFRDLCIAccumStatisticsTxFrames OBJECT-TYPE
	SYNTAX	Counter
	ACCESS	read-only
	STATUS	mandatory
	DESCRIPTION	"Transmitted frames count of the specified DLCI
			in the accumulated statistics report." 
	::= { linkFRDLCIAccumStatisticsEntry 11}

linkFRDLCIAccumStatisticsRxFrames OBJECT-TYPE
	SYNTAX	Counter
	ACCESS	read-only
	STATUS	mandatory
	DESCRIPTION	"Received frames count of the specified DLCI
			in the accumulated statistics report." 
	::= { linkFRDLCIAccumStatisticsEntry 12}

linkFRDLCIAccumStatisticsTimeActive OBJECT-TYPE
	SYNTAX	INTEGER
	ACCESS	read-only
	STATUS	mandatory
	DESCRIPTION	"Time active (seconds) of the specified DLCI
			in the accumulated statistics report." 
	::= { linkFRDLCIAccumStatisticsEntry 13}

linkFRDLCIAccumStatisticsTimeCongestedForward OBJECT-TYPE
	SYNTAX	INTEGER
	ACCESS	read-only
	STATUS	mandatory
	DESCRIPTION	"Time congested forward (seconds) of the specified 
			DLCI in the accumulated statistics report." 
	::= { linkFRDLCIAccumStatisticsEntry 14}

linkFRDLCIAccumStatisticsTimeCongestedBackward OBJECT-TYPE
	SYNTAX	INTEGER
	ACCESS	read-only
	STATUS	mandatory
	DESCRIPTION	"Time congested backward (seconds) of the specified 
			DLCI in the accumulated statistics report." 
	::= { linkFRDLCIAccumStatisticsEntry 15}


-- SWITCH STATISTICS

swAccumStatisticsNumOfCurrentConnects OBJECT-TYPE
	SYNTAX	Counter
	ACCESS	read-only
	STATUS	mandatory
	DESCRIPTION	"Number of current connects for the accumulated
			statistics report." 
	::= { statistics-accumulated 6}

swAccumStatisticsTable OBJECT-TYPE
	SYNTAX	SEQUENCE OF SwAccumStatisticsEntry
	ACCESS	not-accessible
	STATUS	mandatory
	DESCRIPTION	"Table of switch statistics for accumulated 
			statistics reports." 
	::= { statistics-accumulated 7}

swAccumStatisticsEntry OBJECT-TYPE
	SYNTAX	SwAccumStatisticsEntry
	ACCESS	not-accessible
	STATUS	mandatory
	DESCRIPTION	"Entry within the table to specify a particular
			class number." 
	INDEX		{swAccumStatisticsClassNumber}
	::= {swAccumStatisticsTable 1}

SwAccumStatisticsEntry ::= SEQUENCE {
	swAccumStatisticsClassNumber			INTEGER,
	swAccumStatisticsMonth				INTEGER,
	swAccumStatisticsDay				INTEGER,
	swAccumStatisticsHours				INTEGER,
	swAccumStatisticsMinutes			INTEGER,
	swAccumStatisticsSeconds			INTEGER,
	swAccumStatisticsNumOfCurrentConnects 		Counter,
	swAccumStatisticsNumOfSuccessfulConnects	Counter,
	swAccumStatisticsNumOfUnsuccessfulAttempts	Counter,
	swAccumStatisticsMaxNumInQueue			INTEGER
	}

swAccumStatisticsClassNumber OBJECT-TYPE
	SYNTAX	INTEGER
	ACCESS	read-only
	STATUS	mandatory
	DESCRIPTION	"Identifies the class number for accumulated statistics 
			report data." 
	::= {swAccumStatisticsEntry 1}

swAccumStatisticsMonth OBJECT-TYPE
	SYNTAX	INTEGER (1..12)
	ACCESS	read-only
	STATUS	mandatory
	DESCRIPTION	"Month portion of the time stamp for the switch
			statistics accumulated statistics report." 
	::= {swAccumStatisticsEntry 2}

swAccumStatisticsDay OBJECT-TYPE
	SYNTAX	INTEGER (1..31)
	ACCESS	read-only
	STATUS	mandatory
	DESCRIPTION	"Day portion of the time stamp for the switch
			statistics accumulated statistics report." 
	::= {swAccumStatisticsEntry 3}

swAccumStatisticsHours OBJECT-TYPE
	SYNTAX	INTEGER (0..23)
	ACCESS	read-only
	STATUS	mandatory
	DESCRIPTION	"Hours portion of the time stamp for the switch
			statistics accumulated statistics report." 
	::= {swAccumStatisticsEntry 4}

swAccumStatisticsMinutes OBJECT-TYPE
	SYNTAX	INTEGER (0..59)
	ACCESS	read-only
	STATUS	mandatory
	DESCRIPTION	"Minutes portion of the time stamp for the switch
			statistics accumulated statistics report." 
	::= {swAccumStatisticsEntry 5}

swAccumStatisticsSeconds OBJECT-TYPE
	SYNTAX	INTEGER (0..59)
	ACCESS	read-only
	STATUS	mandatory
	DESCRIPTION	"Seconds portion of the time stamp for the switch
			statistics accumulated statistics report." 
	::= {swAccumStatisticsEntry 6}

swAccumStatisticsNumOfSuccessfulConnects OBJECT-TYPE
	SYNTAX	Counter
	ACCESS	read-only
	STATUS	mandatory
	DESCRIPTION	"Number of successful connects for the switch statistics
			accumulated statistics report." 
	::= {swAccumStatisticsEntry 7}

swAccumStatisticsNumOfUnsuccessfulAttempts OBJECT-TYPE
	SYNTAX	Counter
	ACCESS	read-only
	STATUS	mandatory
	DESCRIPTION	"Number of unsuccessful connects (attempts) for the 
			switch statistics accumulated statistics report." 
	::= {swAccumStatisticsEntry 8}

swAccumStatisticsMaxNumInQueue OBJECT-TYPE
	SYNTAX	INTEGER
	ACCESS	read-only
	STATUS	mandatory
	DESCRIPTION	"Maximum number in the queue during report period
			for the switch statistics accumulated statistics report." 
	::= {swAccumStatisticsEntry 9}

-- More Frame Relay Accumulated Statistics

linkFRAccLnkAccumStatisticsTable OBJECT-TYPE
	SYNTAX	SEQUENCE OF LinkFRAccLnkAccumStatisticsEntry
	ACCESS	not-accessible
	STATUS	mandatory
	DESCRIPTION	"Table of Frame Relay link access channel statistics for
			accumulated statistics reports. (Note: More accumulated FR link
			stats are contained in table linkFRAccumStatisticsTable.)" 
	::= { statistics-accumulated 8}

linkFRAccLnkAccumStatisticsEntry OBJECT-TYPE
	SYNTAX	LinkFRAccLnkAccumStatisticsEntry 
	ACCESS	not-accessible
	STATUS	mandatory
	DESCRIPTION	"Entry within the table to specify a particular FR link
			access channel on specific module/card." 
	INDEX		{linkFRAccLnkAccumStatisticsCardNumber,
			linkFRAccLnkAccumStatisticsChannelNumber}
	::= {linkFRAccLnkAccumStatisticsTable 1}

LinkFRAccLnkAccumStatisticsEntry ::= SEQUENCE {
	linkFRAccLnkAccumStatisticsCardNumber				INTEGER,
	linkFRAccLnkAccumStatisticsChannelNumber			INTEGER,
	linkFRAccLnkAccumStatisticsMonth 				INTEGER,
	linkFRAccLnkAccumStatisticsDay					INTEGER,
	linkFRAccLnkAccumStatisticsHours				INTEGER,
	linkFRAccLnkAccumStatisticsMinutes				INTEGER,
	linkFRAccLnkAccumStatisticsSeconds				INTEGER,
	linkFRAccLnkAccumStatisticsLocalCompositeUtilization	   	Gauge,
	linkFRAccLnkAccumStatisticsLocalBufferUtilization		Gauge,
	linkFRAccLnkAccumStatisticsLocalLineAlarms			Counter,
	linkFRAccLnkAccumStatisticsLocalSecInSysFlowControl		INTEGER,
	linkFRAccLnkAccumStatisticsLocalSecInSyncLoss			INTEGER,
	linkFRAccLnkAccumStatisticsLocalSecInCarrierLoss		INTEGER
	}

linkFRAccLnkAccumStatisticsCardNumber OBJECT-TYPE
	SYNTAX	INTEGER (1..5)
	ACCESS	read-only
	STATUS	mandatory
	DESCRIPTION	"Identifies the module/card number for the FR link
			access channel specific to the accumulated statistics 
			report data." 
	::= { linkFRAccLnkAccumStatisticsEntry 1}

linkFRAccLnkAccumStatisticsChannelNumber OBJECT-TYPE
	SYNTAX	INTEGER
	ACCESS	read-only
	STATUS	mandatory
	DESCRIPTION	"Identifies the FR link access channel number specific to
			 the accumulated statistics report data." 
	::= { linkFRAccLnkAccumStatisticsEntry 2}

linkFRAccLnkAccumStatisticsMonth OBJECT-TYPE
	SYNTAX	INTEGER (1..12)
	ACCESS	read-only
	STATUS	mandatory
	DESCRIPTION	"Month portion of the time stamp for the FR link 
			access channel accumulated statistics report." 
	::= { linkFRAccLnkAccumStatisticsEntry 3}

linkFRAccLnkAccumStatisticsDay OBJECT-TYPE
	SYNTAX	INTEGER (1..31)
	ACCESS	read-only
	STATUS	mandatory
	DESCRIPTION	"Day portion of the time stamp for the FR link 
			access channel periodic statistics report." 
	::= { linkFRAccLnkAccumStatisticsEntry 4}

linkFRAccLnkAccumStatisticsHours OBJECT-TYPE
	SYNTAX	INTEGER (0..23)
	ACCESS	read-only
	STATUS	mandatory
	DESCRIPTION	"Hours portion of the time stamp for the FR link 
			access channel periodic statistics report." 
	::= { linkFRAccLnkAccumStatisticsEntry 5}

linkFRAccLnkAccumStatisticsMinutes OBJECT-TYPE
	SYNTAX	INTEGER (0..59)
	ACCESS	read-only
	STATUS	mandatory
	DESCRIPTION	"Minutes portion of the time stamp for the FR link 
			access channel periodic statistics report." 
	::= { linkFRAccLnkAccumStatisticsEntry 6}

linkFRAccLnkAccumStatisticsSeconds OBJECT-TYPE
	SYNTAX	INTEGER (0..59)
	ACCESS	read-only
	STATUS	mandatory
	DESCRIPTION	"Seconds portion of the time stamp for the FR link 
			access channel periodic statistics report." 
	::= { linkFRAccLnkAccumStatisticsEntry 7}

linkFRAccLnkAccumStatisticsLocalCompositeUtilization OBJECT-TYPE
	SYNTAX	Gauge
	ACCESS	read-only
	STATUS	mandatory
	DESCRIPTION	"Local composite utilization (percentage) of the specified FR 
			link access channel in the accumulated statistics report." 
	::= { linkFRAccLnkAccumStatisticsEntry 8}

linkFRAccLnkAccumStatisticsLocalBufferUtilization OBJECT-TYPE
	SYNTAX	Gauge
	ACCESS	read-only
	STATUS	mandatory
	DESCRIPTION	"Local composite utilization (percentage) of the specified FR 
			link access channel in the accumulated statistics report." 
	::= { linkFRAccLnkAccumStatisticsEntry 9}

linkFRAccLnkAccumStatisticsLocalLineAlarms OBJECT-TYPE
	SYNTAX	Counter
	ACCESS	read-only
	STATUS	mandatory
	DESCRIPTION	"Local line alarms of the specified FR link access 
			channel in the accumulated statistics report." 
	::= { linkFRAccLnkAccumStatisticsEntry 10}

linkFRAccLnkAccumStatisticsLocalSecInSysFlowControl OBJECT-TYPE
	SYNTAX	INTEGER
	ACCESS	read-only
	STATUS	mandatory
	DESCRIPTION	"Local seconds in system flow control of the specified
			FR link access channel in the accumulated statistics report." 
	::= { linkFRAccLnkAccumStatisticsEntry 11}

linkFRAccLnkAccumStatisticsLocalSecInSyncLoss OBJECT-TYPE
	SYNTAX	INTEGER
	ACCESS	read-only
	STATUS	mandatory
	DESCRIPTION	"Local seconds in sync loss of the specified FR link
			access channel in the accumulated statistics report." 
	::= { linkFRAccLnkAccumStatisticsEntry 12}

linkFRAccLnkAccumStatisticsLocalSecInCarrierLoss OBJECT-TYPE
	SYNTAX	INTEGER
	ACCESS	read-only
	STATUS	mandatory
	DESCRIPTION	"Local seconds in carrier loss of the specified
			FR link access channel in the accumulated statistics report." 
	::= { linkFRAccLnkAccumStatisticsEntry 13}

END
