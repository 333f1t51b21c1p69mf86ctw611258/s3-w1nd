-- (C)  COPYRIGHT HEWLETT-PACKARD COMPANY 1998.
--
-- LaserJet Series 8000 Printer Multibin Mailbox Model Specific MIB.
--            (Multiple Input Tray and Multibin Mailbox Options)
--   See also:
--      LaserJet Series 8000 Printer Model Specific MIB. (Base Unit)
--      LaserJet Series 8000 Printer Stapler Model Specific MIB. 
--            (High Capacity Input and Multibin Mailbox with Stapler Options)
--
-- Generated on April 1, 1998.
--
-- Company names and product names mentioned herein may be
-- trademarks, and/or registered trademarks of their respective
-- companies.
--
-- For interal and external use.
--
-- This MIB describes all the printer model specific
-- objects suppported by the LaserJet Series 8000 printer
-- when networked connected using a JetDirect print
-- server.
--
-- The following MIB also contain objects supported
-- by a JetDirect connected LaserJet Series 8000 printer:
--
-- rfc 1213 MIB II
--
-- This MIB complies with the following RFCs:
--
-- rfc 1157 Simple Network Management Protocol
-- rfc 1155 Structure of Management Information
--
-- Notes:
--
-- 1) Proprietary Objects containing a string which are defined in this MIB use the
--    first two bytes to hold the symbol set used to encode the string.
--    The Roman-8 symbol set has a hex encoding of 0x0115.  Other
--    symbol sets are listed in the PCL 5 Comparison Guide in table
--    C-1 Symbol Set Values.  Standard Printer MIB (prt...objects) and Host Resources
--    MIB (hr...objects) strings do not contain symbol set information. 
--
-- 2) Some of the objects included are only supported if an accessory
--    is installed.  These accessories include:
--      MIO/EIO based accessories
--      SIMM/DIMM based accessories
--      Mass storage devices
--      Paper handling accessories
--
--
LaserJet-Series8000-MBM-MIB DEFINITIONS ::= BEGIN

IMPORTS
		OBJECT-TYPE FROM RFC1155-SMI
	enterprises FROM RFC1155-SMI;

hp OBJECT IDENTIFIER ::= { enterprises 11 }
nm OBJECT IDENTIFIER ::= { hp 2 }
hpsystem OBJECT IDENTIFIER ::= { nm 3 }
net-peripheral OBJECT IDENTIFIER ::= { hpsystem 9 }
netdm OBJECT IDENTIFIER ::= { net-peripheral 4 }
dm OBJECT IDENTIFIER ::= {  netdm 2}

DisplayString ::= OCTET STRING

device                                 OBJECT IDENTIFIER ::=  { dm 1 } 
destination-subsystem                  OBJECT IDENTIFIER ::=  { device 4 } 
print-engine                           OBJECT IDENTIFIER ::=  { destination-subsystem 1 } 
intray                                 OBJECT IDENTIFIER ::=  { print-engine 3 } 
intrays                                OBJECT IDENTIFIER ::=  { intray 3 } 
intray6                                OBJECT IDENTIFIER ::=  { intrays 6 } 
intray7                                OBJECT IDENTIFIER ::=  { intrays 7 } 
outbin                                 OBJECT IDENTIFIER ::=  { print-engine 4 } 
outbins                                OBJECT IDENTIFIER ::=  { outbin 3 } 
outbin3                                OBJECT IDENTIFIER ::=  { outbins 3 } 
outbin4                                OBJECT IDENTIFIER ::=  { outbins 4 } 
outbin5                                OBJECT IDENTIFIER ::=  { outbins 5 } 
outbin6                                OBJECT IDENTIFIER ::=  { outbins 6 } 
outbin7                                OBJECT IDENTIFIER ::=  { outbins 7 } 
outbin8                                OBJECT IDENTIFIER ::=  { outbins 8 } 
outbin9                                OBJECT IDENTIFIER ::=  { outbins 9 } 
outbin10                               OBJECT IDENTIFIER ::=  { outbins 10 } 
outbin11                               OBJECT IDENTIFIER ::=  { outbins 11 } 
printmib                               OBJECT IDENTIFIER ::=  { dm 2 } 
prtInput                               OBJECT IDENTIFIER ::=  { printmib 8 } 
prtInputTable                          OBJECT IDENTIFIER ::=  { prtInput 2 } 
prtInputEntry                          OBJECT IDENTIFIER ::=  { prtInputTable 1 } 
prtOutput                              OBJECT IDENTIFIER ::=  { printmib 9 } 
prtOutputTable                         OBJECT IDENTIFIER ::=  { prtOutput 2 } 
prtOutputEntry                         OBJECT IDENTIFIER ::=  { prtOutputTable 1 } 


tray6-media-size-loaded OBJECT-TYPE
    SYNTAX  INTEGER {
		   eUSLetter(2),
		   eUSLegal(3),
		   eISOandJISA4(26),
		   eJISB4(46)
		   }
    ACCESS  read-only
    STATUS  optional
    DESCRIPTION
                "Returns the media size that is currently configured in
                tray #5.  Complete list of supported media sizes along
                with their dimensions are listed in the ''Media Size
                Table'' near the end of this document.
                Additional information:
                If the tray drawer is open, a get on this object
                will cause a status of
                <genErr> to be
                returned.  If the tray is empty, the size that the
                tray is configured for will be returned"
::= { intray6 1 }
               
               
tray6-phd OBJECT-TYPE
    SYNTAX  INTEGER
    ACCESS  read-only
    STATUS  optional
    DESCRIPTION
                "Provides the number of the Paper Handling Device that
                contains this input tray.
                Additional information:
                The internal trays belong to device 0 (base engine), the
                envelope feeder is considered to be device 1
                and the external input devices can number
                between 2 and 6 depending on individual user
                configurations."
::= { intray6 12 }
               
               
tray7-media-size-loaded OBJECT-TYPE
    SYNTAX  INTEGER {
		   eUSLetter(2),
		   eUSLegal(3),
		   eLedger(11),
		   eISOandJISA4(26),
		   eISOandJISA3(27),
		   eJISB4(46)
		   }
    ACCESS  read-only
    STATUS  optional
    DESCRIPTION
                "Returns the media size that is currently configured in
                tray #5.  Complete list of supported media sizes along
                with their dimensions are listed in the ''Media Size
                Table'' near the end of this document.
                Additional information:
                If the tray drawer is open, a get on this object
                will cause a status of
                <genErr> to be
                returned.  If the tray is empty, the size that the
                tray is configured for will be returned"
::= { intray7 1 }
               
               
tray7-phd OBJECT-TYPE
    SYNTAX  INTEGER
    ACCESS  read-only
    STATUS  optional
    DESCRIPTION
                "Provides the number of the Paper Handling Device that
                contains this input tray.
                Additional information:
                The internal trays belong to device 0 (base engine), the
                envelope feeder is considered to be device 1
                and the external input devices can number
                between 2 and 6 depending on individual user
                configurations.
                NOTE: only TRAY6 and TRAY7 are listed here
                because HP does not make a device with more than
                two trays, but the Specification requires
                support of up to 10 external trays. Therefore the
                objects for TRAY8-PHD ... TRAY15-PHD will exist if
                that many trays exist."
::= { intray7 12 }
               
               
outbin3-override-mode OBJECT-TYPE
    SYNTAX  OCTET STRING
    ACCESS  read-write
    STATUS  optional
    DESCRIPTION
                "Returns or sets the device behavior when this output bin
                condition causes printing to stop.  
                  cCancelJob - The device cancels the job.  
                  cOutbinFullOverride - The device sends subsequent
                media to the overflow bin.  
                  cOutbinAttentionOverride - The device ignores the
                attention condition and continues printing.  
                  cBinderAttentionOverride - The device ignores the
                binder attention condition and continues printing.
                Additional information:
                This object describes the action that is performed
                when the JOB-OUTPUT-AUTO-CONTINUE-TIMEOUT expires.
                The action performed by the CONTINUE object being set
                to eInitiateAction or the GO key being pressed on the
                control panel may cause different actions. See the
                CONTINUE object description for information on the
		actions that occur for those conditions.
                The cCancelJob item overrides the other two options, if
                it is set then the job will be canceled regardless of
                the other settings.  If cJobCancel is not set then
                cBinFullOverride will cause the printer to use the
                overflow bin (Set by PML object OVERFLOW-BIN)in
                the case of a bin full condtion. If
                the cBinderAttentionOverride option is set then the
                finisher out warning will be displayed but ignored
                and jobs will continue to go to the finisher anyway.
                OUTBIN3 is the topmost bin on the output device.  This bin
                replaces the left output bin on the base printer.  OUTBIN4
                through OUTBIN11 are the additional 8 bins supplied by
                the MBM8 device.  
                NOTE: Because HP is marketing a device with a max of
                9 bins (MBM8) the OUTBIN-OVERRIDE-MODE objects are
               	3-11 but the external device specification requires
               	support of up to 315 output bins.  Therefore if these
               	bins exist above 11, then the coresponding objects will
               	also exist OUTBIN12-OVERRIDE-MODE through 
               	OUTBIN317-OVERRIDE-MODE.
               	The data for this object is stored in NVRAM."
::= { outbin3 9 }
               
               
outbin3-maximum-binding OBJECT-TYPE
    SYNTAX  INTEGER
    ACCESS  read-only
    STATUS  optional
    DESCRIPTION
                "The maximum number of sheets of 20 pound paper that can
                be bound by the binding device that serves this output
                bin.  If a job exceeds this number and the job has
                requested binding, cBindingError will be set in NOT-
                READY-DESTINATION-PRINT-ENGINE.
                Additional information:
                This is a read only object that returns the number of
                20# pages that this bin can bind(i.e. staple).  This
                number is used by the host applications to prevent 
                jobs that exceed this amount from being sent to this
                bin.  If this bin does not have a finishing function
                like stapling where this object is necessary the 
                object will return 0.
               	OUTBIN3 is the topmost bin on the output device.  This bin
                replaces the left output bin on the base printer.  OUTBIN4
                through OUTBIN11 are the additional 8 bins supplied by
                the MBM8 device.  
                NOTE: Because HP is marketing a device with a max of
                9 bins (MBM8) the OUTBINn-MAXIMUM-BINDING objects are
               	3-11 but the external device specification requires
               	support of up to 315 output bins.  Therefore if these
               	bins exist above 11, then the coresponding objects will
               	also exist OUTBIN12-MAXIMUM-BINDING through 
               	OUTBIN317-MAXIMUM-BINDING."
::= { outbin3 10 }
               
               
outbin3-phd OBJECT-TYPE
    SYNTAX  INTEGER
    ACCESS  read-only
    STATUS  optional
    DESCRIPTION
                "Provides the number of the Paper Handling Device that
                contains this output bin.
                Additional information:
                This object will return the the device number that
                contains this output bin.  The envelope feed is
                considered PHD1 thus this object will return 
                2-6 depending on where in the device chain the bin
                exists. 
               	OUTBIN3 is the topmost bin on the output device.  This bin
                replaces the left output bin on the base printer.  OUTBIN4
                through OUTBIN11 are the additional 8 bins supplied by
                the MBM8 device.  
                NOTE: Because HP is marketing a device with a max of
                9 bins (MBM8) the OUTBINn-PHD objects are
               	3-11 but the external device specification requires
                support of up to 315 output bins.  Therefore if these
                bins exist above 11, then the coresponding objects will
               	also exist OUTBIN12-PHD through 
               	OUTBIN317-PHD."
::= { outbin3 11 }
               
               
outbin4-override-mode OBJECT-TYPE
    SYNTAX  OCTET STRING
    ACCESS  read-write
    STATUS  optional
    DESCRIPTION
                "Returns or sets the device behavior when this output bin
                condition causes printing to stop.  
                  cCancelJob - The device cancels the job.  
                  cOutbinFullOverride - The device sends subsequent
                media to the overflow bin.  
                  cOutbinAttentionOverride - The device ignores the
                attention condition and continues printing.  
                  cBinderAttentionOverride - The device ignores the
                binder attention condition and continues printing.
                Additional information:
                See OUTBIN3-OVERRIDE-MODE."
::= { outbin4 9 }
               
               
outbin4-maximum-binding OBJECT-TYPE
    SYNTAX  INTEGER
    ACCESS  read-only
    STATUS  optional
    DESCRIPTION
                "The maximum number of sheets of 20 pound paper that can
                be bound by the binding device that serves this output
                bin.  If a job exceeds this number and the job has
                requested binding, cBindingError will be set in NOT-
                READY-DESTINATION-PRINT-ENGINE.
                Additional information:
                See OUTBIN3-MAXIMUM-BINDING."
::= { outbin4 10 }
               
               
outbin4-phd OBJECT-TYPE
    SYNTAX  INTEGER
    ACCESS  read-only
    STATUS  optional
    DESCRIPTION
                "Provides the number of the Paper Handling Device that
                contains this output bin.
                Additional information:
                See OUTBIN3-PHD."
::= { outbin4 11 }
               
               
outbin5-override-mode OBJECT-TYPE
    SYNTAX  OCTET STRING
    ACCESS  read-write
    STATUS  optional
    DESCRIPTION
                "Returns or sets the device behavior when this output bin
                condition causes printing to stop.  
                  cCancelJob - The device cancels the job.  
                  cOutbinFullOverride - The device sends subsequent
                media to the overflow bin.  
                  cOutbinAttentionOverride - The device ignores the
                attention condition and continues printing.  
                  cBinderAttentionOverride - The device ignores the
                binder attention condition and continues printing.
                Additional information:
                See OUTBIN3-OVERRIDE-MODE."
::= { outbin5 9 }
               
               
outbin5-maximum-binding OBJECT-TYPE
    SYNTAX  INTEGER
    ACCESS  read-only
    STATUS  optional
    DESCRIPTION
                "The maximum number of sheets of 20 pound paper that can
                be bound by the binding device that serves this output
                bin.  If a job exceeds this number and the job has
                requested binding, cBindingError will be set in NOT-
                READY-DESTINATION-PRINT-ENGINE.
                Additional information:
                See OUTBIN3-MAXIMUM-BINDING."
::= { outbin5 10 }
               
               
outbin5-phd OBJECT-TYPE
    SYNTAX  INTEGER
    ACCESS  read-only
    STATUS  optional
    DESCRIPTION
                "Provides the number of the Paper Handling Device that
                contains this output bin.
                Additional information:
                See OUTBIN3-PHD."
::= { outbin5 11 }
               
               
outbin6-override-mode OBJECT-TYPE
    SYNTAX  OCTET STRING
    ACCESS  read-write
    STATUS  optional
    DESCRIPTION
                "Returns or sets the device behavior when this output bin
                condition causes printing to stop.  
                  cCancelJob - The device cancels the job.  
                  cOutbinFullOverride - The device sends subsequent
                media to the overflow bin.  
                  cOutbinAttentionOverride - The device ignores the
                attention condition and continues printing.  
                  cBinderAttentionOverride - The device ignores the
                binder attention condition and continues printing.
                Additional information:
                See OUTBIN3-OVERRIDE-MODE."
::= { outbin6 9 }
               
               
outbin6-maximum-binding OBJECT-TYPE
    SYNTAX  INTEGER
    ACCESS  read-only
    STATUS  optional
    DESCRIPTION
                "The maximum number of sheets of 20 pound paper that can
                be bound by the binding device that serves this output
                bin.  If a job exceeds this number and the job has
                requested binding, cBindingError will be set in NOT-
                READY-DESTINATION-PRINT-ENGINE.
                Additional information:
                See OUTBIN3-MAXIMUM-BINDING."
::= { outbin6 10 }
               
               
outbin6-phd OBJECT-TYPE
    SYNTAX  INTEGER
    ACCESS  read-only
    STATUS  optional
    DESCRIPTION
                "Provides the number of the Paper Handling Device that
                contains this output bin.
                Additional information:
                See OUTBIN3-PHD."
::= { outbin6 11 }
               
               
outbin7-override-mode OBJECT-TYPE
    SYNTAX  OCTET STRING
    ACCESS  read-write
    STATUS  optional
    DESCRIPTION
                "Returns or sets the device behavior when this output bin
                condition causes printing to stop.  
                  cCancelJob - The device cancels the job.  
                  cOutbinFullOverride - The device sends subsequent
                media to the overflow bin.  
                  cOutbinAttentionOverride - The device ignores the
                attention condition and continues printing.  
                  cBinderAttentionOverride - The device ignores the
                binder attention condition and continues printing.
                Additional information:
                See OUTBIN3-OVERRIDE-MODE."
::= { outbin7 9 }
               
               
outbin7-maximum-binding OBJECT-TYPE
    SYNTAX  INTEGER
    ACCESS  read-only
    STATUS  optional
    DESCRIPTION
                "The maximum number of sheets of 20 pound paper that can
                be bound by the binding device that serves this output
                bin.  If a job exceeds this number and the job has
                requested binding, cBindingError will be set in NOT-
                READY-DESTINATION-PRINT-ENGINE.
                Additional information:
                See OUTBIN3-MAXIMUM-BINDING."
::= { outbin7 10 }
               
               
outbin7-phd OBJECT-TYPE
    SYNTAX  INTEGER
    ACCESS  read-only
    STATUS  optional
    DESCRIPTION
                "Provides the number of the Paper Handling Device that
                contains this output bin.
                Additional information:
                See OUTBIN3-PHD."
::= { outbin7 11 }
               
               
outbin8-override-mode OBJECT-TYPE
    SYNTAX  OCTET STRING
    ACCESS  read-write
    STATUS  optional
    DESCRIPTION
                "Returns or sets the device behavior when this output bin
                condition causes printing to stop.  
                  cCancelJob - The device cancels the job.  
                  cOutbinFullOverride - The device sends subsequent
                media to the overflow bin.  
                  cOutbinAttentionOverride - The device ignores the
                attention condition and continues printing.  
                  cBinderAttentionOverride - The device ignores the
                binder attention condition and continues printing.
                Additional information:
                See OUTBIN3-OVERRIDE-MODE."
::= { outbin8 9 }
               
               
outbin8-maximum-binding OBJECT-TYPE
    SYNTAX  INTEGER
    ACCESS  read-only
    STATUS  optional
    DESCRIPTION
                "The maximum number of sheets of 20 pound paper that can
                be bound by the binding device that serves this output
                bin.  If a job exceeds this number and the job has
                requested binding, cBindingError will be set in NOT-
                READY-DESTINATION-PRINT-ENGINE.
                Additional information:
                See OUTBIN3-MAXIMUM-BINDING."
::= { outbin8 10 }
               
               
outbin8-phd OBJECT-TYPE
    SYNTAX  INTEGER
    ACCESS  read-only
    STATUS  optional
    DESCRIPTION
                "Provides the number of the Paper Handling Device that
                contains this output bin.
                Additional information:
                See OUTBIN3-PHD."
::= { outbin8 11 }
               
               
outbin9-override-mode OBJECT-TYPE
    SYNTAX  OCTET STRING
    ACCESS  read-write
    STATUS  optional
    DESCRIPTION
                "Returns or sets the device behavior when this output bin
                condition causes printing to stop.  
                  cCancelJob - The device cancels the job.  
                  cOutbinFullOverride - The device sends subsequent
                media to the overflow bin.  
                  cOutbinAttentionOverride - The device ignores the
                attention condition and continues printing.  
                  cBinderAttentionOverride - The device ignores the
                binder attention condition and continues printing.
                Additional information:
                See OUTBIN3-OVERRIDE-MODE."
::= { outbin9 9 }
               
               
outbin9-maximum-binding OBJECT-TYPE
    SYNTAX  INTEGER
    ACCESS  read-only
    STATUS  optional
    DESCRIPTION
                "The maximum number of sheets of 20 pound paper that can
                be bound by the binding device that serves this output
                bin.  If a job exceeds this number and the job has
                requested binding, cBindingError will be set in NOT-
                READY-DESTINATION-PRINT-ENGINE.
                Additional information:
                See OUTBIN3-MAXIMUM-BINDING."
::= { outbin9 10 }
               
               
outbin9-phd OBJECT-TYPE
    SYNTAX  INTEGER
    ACCESS  read-only
    STATUS  optional
    DESCRIPTION
                "Provides the number of the Paper Handling Device that
                contains this output bin.
                Additional information:
                See OUTBIN3-PHD."
::= { outbin9 11 }
               
               
outbin10-override-mode OBJECT-TYPE
    SYNTAX  OCTET STRING
    ACCESS  read-write
    STATUS  optional
    DESCRIPTION
                "Returns or sets the device behavior when this output bin
                condition causes printing to stop.  
                  cCancelJob - The device cancels the job.  
                  cOutbinFullOverride - The device sends subsequent
                media to the overflow bin.  
                  cOutbinAttentionOverride - The device ignores the
                attention condition and continues printing.  
                  cBinderAttentionOverride - The device ignores the
                binder attention condition and continues printing.
                Additional information:
                See OUTBIN3-OVERRIDE-MODE."
::= { outbin10 9 }
               
               
outbin10-maximum-binding OBJECT-TYPE
    SYNTAX  INTEGER
    ACCESS  read-only
    STATUS  optional
    DESCRIPTION
                "The maximum number of sheets of 20 pound paper that can
                be bound by the binding device that serves this output
                bin.  If a job exceeds this number and the job has
                requested binding, cBindingError will be set in NOT-
                READY-DESTINATION-PRINT-ENGINE.
                Additional information:
                See OUTBIN3-MAXIMUM-BINDING."
::= { outbin10 10 }
               
               
outbin10-phd OBJECT-TYPE
    SYNTAX  INTEGER
    ACCESS  read-only
    STATUS  optional
    DESCRIPTION
                "Provides the number of the Paper Handling Device that
                contains this output bin.
                Additional information:
                See OUTBIN3-PHD."
::= { outbin10 11 }
               
               
outbin11-override-mode OBJECT-TYPE
    SYNTAX  OCTET STRING
    ACCESS  read-write
    STATUS  optional
    DESCRIPTION
                "Returns or sets the device behavior when this output bin
                condition causes printing to stop.  
                  cCancelJob - The device cancels the job.  
                  cOutbinFullOverride - The device sends subsequent
                media to the overflow bin.  
                  cOutbinAttentionOverride - The device ignores the
                attention condition and continues printing.  
                  cBinderAttentionOverride - The device ignores the
                binder attention condition and continues printing.
                Additional information:
                See OUTBIN3-OVERRIDE-MODE."
::= { outbin11 9 }
               
               
outbin11-maximum-binding OBJECT-TYPE
    SYNTAX  INTEGER
    ACCESS  read-only
    STATUS  optional
    DESCRIPTION
                "The maximum number of sheets of 20 pound paper that can
                be bound by the binding device that serves this output
                bin.  If a job exceeds this number and the job has
                requested binding, cBindingError will be set in NOT-
                READY-DESTINATION-PRINT-ENGINE.
                Additional information:
                See OUTBIN3-MAXIMUM-BINDING."
::= { outbin11 10 }
               
               
outbin11-phd OBJECT-TYPE
    SYNTAX  INTEGER
    ACCESS  read-only
    STATUS  optional
    DESCRIPTION
                "Provides the number of the Paper Handling Device that
                contains this output bin.
                Additional information:
                See OUTBIN3-PHD."
::= { outbin11 11 }
               
               
prtinputtype OBJECT-TYPE
    SYNTAX  INTEGER {
		   ePsheetFeedAutoRemovableTray(3),
		   ePsheetFeedAutoNonRemovableTray(4)
		   }
    ACCESS  read-only
    STATUS  optional
    DESCRIPTION
                "The type of technology (discriminated primarily according to
        feeder mechanism type) employed by the input sub-unit.  Note,
        the Optional Input Class provides for a descriptor field to
        further qualify the other choice.
	Refer to ftp://ftp.pwg.org/pub/pwg/pmp/drafts/pmib_031698.txt, for more details in the Standard Printer MIB.
                Additional information:
                Tray 1 is the multi-purpose tray and is always present.
                It supports both sheets and envelopes. Its type is
                ePsheetFeedAutoNonRemovableTray.  
                Tray 2 is a removable tray that comes standard
                with the printer, although it is usually not removed
                from the printer.  It is of type
                ePsheetFeedAutoRemovableTray.  
                Tray 3 is a removable tray that comes standard
                with the printer, although it is usually not removed
                from the printer.  It is of type
                ePsheetFeedAutoRemovableTray.  
                The 4th tray in this array is the envelope feeder.  It
                can be detected even when it is installed while the
                printer is powered on.  
                Tray 6 and Tray 7 are the Multiple Input tray device,
                and it must be installed before the printer is powered
                on. They are of type ePsheetFeedAutoRemovableTray."
::= { prtInputEntry 2 }
               
               
prtinputdimunit OBJECT-TYPE
    SYNTAX  INTEGER {
		   ePtenThousandthsOfInches(3),
		   ePmicrometers(4)
		   }
    ACCESS  read-only
    STATUS  optional
    DESCRIPTION
                "The unit of measurement for use calculating and relaying
         dimensional values for this input sub-unit.
	 Refer to ftp://ftp.pwg.org/pub/pwg/pmp/drafts/pmib_031698.txt, for more details in the Standard Printer MIB.
                Additional information:
                Following is a table of paper sizes and dimensions
                for each paper size supported by Yukon:  
                
                Size                    Inches (ten-thousandths)  Millimeters  
               			        Feed   x Cross-Feed       Feed   x Cross-Feed  
                ---------------         ------------------------  -----------  
                eUSExecutive            105000 x 72500            266700 x 184150  
                eUSLetter               85000  x 110000           215900 x 279400  
                eUSLegal                140000 x 85000            355600 x 215900  
                eLedger                 170000 x 110000           431800 x 279400  
                eISOandJISA5            82677  x 58268            210000 x 148000  
                eISOandJISA4            82677  x 116929           210000 x 297000  
                eJISB4                  143307 x 101181           364000 x 257000  
                eJISB5                  101181 x 71654            257000 x 182000  
                eISOandJISA3            165354 x 116929           420000 x 297000  
                eMonarch                75000  x 38750            190500 x 98425  
                eCommercial10           95000  x 41250            241300 x 104775  
                eInternationalDL        86614  x 43307            220000 x 110000  
                eInternationalC5        90157  x 63780            229000 x 162000  
                eInternationalB5        98425  x 69291            250000 x 176000  
                eJapanesePostcardDouble 78740  x 58268            200000 x 148000  
                eCustom                 177000 x 117000(max)      449580 x 297180(max)
                "
::= { prtInputEntry 3 }
               
               
prtinputmediadimfeeddirdeclared OBJECT-TYPE
    SYNTAX  INTEGER
    ACCESS  read-write
    STATUS  optional
    DESCRIPTION
                "This object provides the value of the declared dimension, in
        the feed direction, of the media that is (or, if empty, was or
        will be) in this input sub-unit.  The feed direction is the
        direction in which the media is fed on this sub-unit.  This
        dimension is measured in input sub-unit dimensional units
        (prtInputDimUnit).  If this input sub-unit can reliably sense
        this value, the value is sensed by the printer and may not be
        changed by management requests.  Otherwise, the value may be
        changed. The value (-1) means other and specifically means
        that this sub-unit places no restriction on this parameter.
        The value (-2) indicates unknown.
	Refer to ftp://ftp.pwg.org/pub/pwg/pmp/drafts/pmib_031698.txt, for more details in the Standard Printer MIB.
                Additional information:
                For trays 2, 3, 6 and 7 (which can reliably sense this
                value) these objects behave exactly the same as 
                prtInputMediaDimFeedDirChosen.  Attempting to set the
                objects for tray 2, 3, 6 or 7 will cause
                <noSuchName> to be
                returned.
                The default values assume the trays are configured for
                letter size paper (or COM10, in the case of the
                envelope feeder).  For tray 1, the value is the
                dimension for the media size currently declared.  For 
                the envelope feeder (tray 4), the value is the
                dimension for the media size currently declared.  
                Valid values are 0 to 268435455. If a value within 0.2 
                inches of a standard size (e.g. 85001) is chosen when
                setting these objects, the standard size will be set
                for the specified tray if the value of
                prtInputMediaDimXFeedDirDeclared is also set to within
                0.2 inches of the same standard size. If the value is
                not within 0.2 inches, Custom will be chosen as the
                size if it is supported by the specified tray, 
                otherwise the first available standard size for the 
                tray will be selected."
::= { prtInputEntry 4 }
               
               
prtinputmediadimxfeeddirdeclared OBJECT-TYPE
    SYNTAX  INTEGER
    ACCESS  read-write
    STATUS  optional
    DESCRIPTION
                "This object provides the value of the declared dimension, in
        the cross feed direction, of the media that is (or, if empty,
        was or will be) in this input sub-unit.  The cross  feed
        direction is ninety degrees relative to the feed direction
        associated with this sub-unit. This dimension is measured in
        input sub-unit dimensional units (prtInputDimUnit).  If this
        input sub-unit can reliably sense this value, the value is
        sensed by the printer and may not be changed by management
        requests. Otherwise, the value may be changed. The value (-1)
        means other and specifically means that this sub-unit places
        no restriction on this parameter. The value (-2) indicates
        unknown.
	Refer to ftp://ftp.pwg.org/pub/pwg/pmp/drafts/pmib_031698.txt, for more details in the Standard Printer MIB.
                Additional information:
                For trays 2, 3, 6 and 7 (which can reliably sense this
                value) these objects behave exactly the same as 
                prtInputMediaDimFeedDirChosen.  Attempting to set the
                objects for tray 2, 3, 6 or 7 will cause
                <noSuchName> to be
                returned.
                The default values assume the trays are configured for
                letter size paper (or COM10, in the case of the
                envelope feeder).  For tray 1, the value is the
                dimension for the media size currently declared.  For 
                the envelope feeder (tray 4), the value is the
                dimension for the media size currently declared.  
                Valid values are 0 to 268435455. If a value within 0.2 
                inches of a standard size (e.g. 85001) is chosen when
                setting these objects, the standard size will be set
                for the specified tray if the value of
                prtInputMediaDimXFeedDirDeclared is also set to within
                0.2 inches of the same standard size. If the value is
                not within 0.2 inches, Custom will be chosen as the
                size if it is supported by the specified tray, 
                otherwise the first available standard size for the 
                tray will be selected."
::= { prtInputEntry 5 }
               
               
prtinputmediadimfeeddirchosen OBJECT-TYPE
    SYNTAX  INTEGER
    ACCESS  read-only
    STATUS  optional
    DESCRIPTION
                "The printer will act as if media of the chosen dimension (in
        the feed direction) is present in this input source.  Note
        that this value will be used even if the input tray is empty.
        Feed dimension measurements are taken relative to the feed
        direction associated with that sub-unit and are in input sub-unit
        dimensional units (MediaUnit). If the printer supports the
        declared dimension, the granted dimension is the same as
        the declared dimension. If not, the granted dimension is
        set to the closest dimension that the printer supports
        when the declared dimension is set. The value (-1) means
        other and specifically indicates that this sub-unit
        places no restriction on this parameter. The value (-2)
        indicates unknown.
	Refer to ftp://ftp.pwg.org/pub/pwg/pmp/drafts/pmib_031698.txt, for more details in the Standard Printer MIB.
                Additional information:
                The objects for trays 2, 3, 6 and 7 reflect the
                configuration of the corresponding trays. When the tray
                is removed, a value of -2 is returned. The default
                values assume the trays are configured for letter size
                paper (or COM10, in the case of the envelope feeder).
                For tray 1 and the envelope feeder, the object returns
                the value of the media size for which the tray is 
                currently configured because those trays cannot sense
                what size media they contain."
::= { prtInputEntry 6 }
               
               
prtinputmediadimxfeeddirchosen OBJECT-TYPE
    SYNTAX  INTEGER
    ACCESS  read-only
    STATUS  optional
    DESCRIPTION
                "The printer will act as if media of the chosen dimension (in
        the cross feed direction) is present in this input source.
        Note that this value will be used even if the input tray is
        empty.  The cross feed direction is ninety degrees relative
        to the feed direction associated with this sub-unit. This
        dimension is measured in input sub-unit dimensional units
        (MediaUnit).  If the printer supports the declared
        dimension, the granted dimension is the same as the
        declared dimension. If not, the granted dimension is set
        to the closest dimension that the printer supports when
        the declared dimension is set. The value (-1) means other
        and specifically indicates that this sub-unit places no
        restriction on this parameter.  The value (-2) indicates
        unknown.
	Refer to ftp://ftp.pwg.org/pub/pwg/pmp/drafts/pmib_031698.txt, for more details in the Standard Printer MIB.
                Additional information:
                The objects for trays 2, 3, 6 and 7 reflect the
                configuration of the corresponding trays. When the tray
                is removed, a value of -2 is returned. The default
                values assume the trays are configured for letter size
                paper (or COM10, in the case of the envelope feeder).
                For tray 1 and the envelope feeder, the object returns
                the value of the media size for which the tray is 
                currently configured because those trays cannot sense
                what size media they contain."
::= { prtInputEntry 7 }
               
               
prtinputcapacityunit OBJECT-TYPE
    SYNTAX  INTEGER {
		   ePsheets(8)
		   }
    ACCESS  read-only
    STATUS  optional
    DESCRIPTION
                "The unit of measurement for use in calculating and relaying
        capacity values for this input sub-unit.
	Refer to ftp://ftp.pwg.org/pub/pwg/pmp/drafts/pmib_031698.txt, for more details in the Standard Printer MIB.
                Additional information:
                A sheet is a single piece of 20 pound paper. For tray
                4, the envelope feeder, a sheet is one envelope"
::= { prtInputEntry 8 }
               
               
prtinputmaxcapacity OBJECT-TYPE
    SYNTAX  INTEGER
    ACCESS  read-only
    STATUS  optional
    DESCRIPTION
                "The maximum capacity of the input sub-unit in input
        sub-unit capacity units (PrtCapacityUnitTC).  There is no
        convention associated with the media itself so this value
        reflects claimed capacity. If this input sub-unit can
        reliably sense this value, the value is sensed by the
        printer and may not be changed by management requests;
        otherwise, the value may be written (by a Remote
        Control Panel or a Management Application).
        The value (-1) means other and specifically
        indicates that the sub-unit places no restrictions
        on this parameter.  The value (-2) means unknown.
	Refer to ftp://ftp.pwg.org/pub/pwg/pmp/drafts/pmib_031698.txt, for more details in the Standard Printer MIB.
                Additional information:
                Replaces PML TRAYn-MAXIMUM-CAPACITY.  This is
                specified assuming 20 pound paper for the paper trays."
::= { prtInputEntry 9 }
               
               
prtinputcurrentlevel OBJECT-TYPE
    SYNTAX  INTEGER
    ACCESS  read-only
    STATUS  optional
    DESCRIPTION
                "The current capacity of the input sub-unit in input
        sub-unit capacity units (PrtCapacityUnitTC). If this input
        sub-unit can reliably sense this value, the value is
        sensed by the printer and may not be changed by
        management requests; otherwise, the value may
        be written (by a Remote Contol Panel or a
        Management Application).  The value (-1) means other and
        specifically indicates that the sub-unit places no
        restrictions on this parameter. The value (-2) means unknown.
        The value (-3) means that the printer knows that at least one
        unit remains.
	Refer to ftp://ftp.pwg.org/pub/pwg/pmp/drafts/pmib_031698.txt, for more details in the Standard Printer MIB.
                Additional information:
                Koala & Yukon can detect tray level within roughly 25% for
                trays 2, 3, 6, & 7.
                For Trays 1 and 4, -3 will be returned if the tray is
                not empty, and 0 will be returned if the tray is empty.
                If a tray is removed, a value of -2 (unknown) will
                be returned."
::= { prtInputEntry 10 }
               
               
prtinputstatus OBJECT-TYPE
    SYNTAX  INTEGER
    ACCESS  read-only
    STATUS  optional
    DESCRIPTION
                "The current status of this input sub-unit.
	Refer to ftp://ftp.pwg.org/pub/pwg/pmp/drafts/pmib_031698.txt, for more details in the Standard Printer MIB.
                Additional information:
                Replaces PML STATUS-TRAY-MISSING and
                STATUS-TRAY-EMPTY.
                Values returned by the firmware are detailed in the
                following table. 'Value Or'd Due To Condition' indicates
                that the specified value will be logically or'd into the
                value for this object when the specified Condition
                occurs.  
                Condition                   Value Or'd Due To Condition  
                -----------------------     ------------------------  
                Tray Lifter Error               1 + 2  
                Tray not installed or  
                not inserted or empty           1  
                Tray is current source tray     4 + 2  
                Tray involved in paper mount    16 + 32  
                Value 3 or 1 is Or'd in         8  
                Tray is lifting                 64
                "
::= { prtInputEntry 11 }
               
               
prtinputmedianame OBJECT-TYPE
    SYNTAX  OCTET STRING (SIZE(0..63))
    ACCESS  read-write
    STATUS  optional
    DESCRIPTION
                "A description of the media contained in this input sub-unit;
        This description is intended for display to a human operator.
        This description is not processed by the printer.  It is used
        to provide information not expressible in terms of the other
        media attributes (e.g. prtInputMediaDimFeedDirChosen,
        prtInputMediaDimXFeedDirChosen, prtInputMediaWeight,
        prtInputMediaType). An example would be `legal tender bond
        paper'.
	Refer to ftp://ftp.pwg.org/pub/pwg/pmp/drafts/pmib_031698.txt, for more details in the Standard Printer MIB.
                Additional information:
                Replaces PML TRAYn-MEDIA-NAME.  
                If set to a string other than one contained by a
                MEDIAn-NAME object, a status of 
                <badValue> is returned.  If set 
                to a string that is unsupported for the specified tray
                object, a status of <badValue> is
                returned. The value of this object is saved across a
                power cycle."
::= { prtInputEntry 12 }
               
               
prtinputname OBJECT-TYPE
    SYNTAX  OCTET STRING (SIZE(0..63))
    ACCESS  read-only
    STATUS  optional
    DESCRIPTION
                "The name assigned to this input sub-unit.
	Refer to ftp://ftp.pwg.org/pub/pwg/pmp/drafts/pmib_031698.txt, for more details in the Standard Printer MIB.
                Additional information:
                Replaces PML TRAYn-NAME."
::= { prtInputEntry 13 }
               
               
prtinputvendorname OBJECT-TYPE
    SYNTAX  OCTET STRING (SIZE(0..63))
    ACCESS  read-only
    STATUS  optional
    DESCRIPTION
                "The vendor name of this input sub-unit.
	Refer to ftp://ftp.pwg.org/pub/pwg/pmp/drafts/pmib_031698.txt, for more details in the Standard Printer MIB."
::= { prtInputEntry 14 }
               
               
prtinputmodel OBJECT-TYPE
    SYNTAX  OCTET STRING (SIZE(0..63))
    ACCESS  read-only
    STATUS  optional
    DESCRIPTION
                "The model name of this input sub-unit.
	Refer to ftp://ftp.pwg.org/pub/pwg/pmp/drafts/pmib_031698.txt, for more details in the Standard Printer MIB.
                Additional information:
                MoBY does not specify a model name for Tray 1, 2 or 3"
::= { prtInputEntry 15 }
               
               
prtinputversion OBJECT-TYPE
    SYNTAX  OCTET STRING (SIZE(0..63))
    ACCESS  read-only
    STATUS  optional
    DESCRIPTION
                "The version of this input sub-unit.
	Refer to ftp://ftp.pwg.org/pub/pwg/pmp/drafts/pmib_031698.txt, for more details in the Standard Printer MIB.
                Additional information:
                Yukon does not specify a version number
                for the input trays."
::= { prtInputEntry 16 }
               
               
prtinputserialnumber OBJECT-TYPE
    SYNTAX  OCTET STRING (SIZE(0..32))
    ACCESS  read-only
    STATUS  optional
    DESCRIPTION
                "The serial number assigned to this input sub-unit.
	Refer to ftp://ftp.pwg.org/pub/pwg/pmp/drafts/pmib_031698.txt, for more details in the Standard Printer MIB.
                Additional information:
                Yukon does not specify a serial number for the
                input trays."
::= { prtInputEntry 17 }
               
               
prtinputdescription OBJECT-TYPE
    SYNTAX  OCTET STRING (SIZE(0..255))
    ACCESS  read-only
    STATUS  optional
    DESCRIPTION
                "A free-form text description of this input
        sub-unit in the localization specified by
        prtGeneralCurrentLocalization.
	Refer to ftp://ftp.pwg.org/pub/pwg/pmp/drafts/pmib_031698.txt, for more details in the Standard Printer MIB."
::= { prtInputEntry 18 }
               
               
prtinputsecurity OBJECT-TYPE
    SYNTAX  INTEGER {
		   ePother(1),
		   ePon(3),
		   ePoff(4),
		   ePnotPresent(5)
		   }
    ACCESS  read-only
    STATUS  optional
    DESCRIPTION
                "Indicates if this input sub-unit has some security
        associated with it.
	Refer to ftp://ftp.pwg.org/pub/pwg/pmp/drafts/pmib_031698.txt, for more details in the Standard Printer MIB.
                Additional information:
                No security mechanism provided."
::= { prtInputEntry 19 }
               
               
prtinputmedialoadtimeout OBJECT-TYPE
    SYNTAX  INTEGER
    ACCESS  read-only
    STATUS  optional
    DESCRIPTION
                "When the printer is not able to print due to a subunit
          being empty or the requested media must be manually loaded, the
          printer will wait for the duration (in seconds) specified by this
          object. Upon expiration of the timeout, the printer will take the
          action specified by prtInputNextIndex.
          The event which causes the printer to enter the waiting state is
          product specific. If the printer is not waiting for manually fed
          media, it may switch from an empty subunit to a different subunit
          without waiting for the timeout to expire.
          A value of (-1) implies 'other' or 'infinite' which translates to
          'wait forever'. The action which causes printing to continue is
          product specific. A value of (-2) implies 'unknown'.
		
		Refer to ftp://ftp.pwg.org/pub/pwg/pmp/drafts/pmib_031698.txt, for more details in the Standard Printer MIB.
                Additional information:
                This object simply reflects the value of the
                JOB-INPUT-AUTO-CONTINUE-TIMEOUT object. See the
                description of that object for additional information."
::= { prtInputEntry 24 }
               
               
prtinputnextindex OBJECT-TYPE
    SYNTAX  INTEGER
    ACCESS  read-only
    STATUS  optional
    DESCRIPTION
                "The value of prtInputIndex corresponding to the input
          subunit which will be used when this input subunit is emptied and
          the timeout specified by prtInputMediaLoadTimeout expires. A
          value of zero(0) indicates that auto input switching will not
          occur when this input subunit is emptied. If the timeout
          specified by prtInputLoadMediaTimeout expires and this value is
          zero(0), the job will be aborted. A value of (-1) means other.
          The value (-2) means 'unknown' and specifically indicates that an
          implementation specific method will determine the next input
          subunit to use at the time this subunit is emptied and the
          timeout expires. The value(-3) means input switching is not
          supported for this subunit.
		 Refer to ftp://ftp.pwg.org/pub/pwg/pmp/drafts/pmib_031698.txt, for more details in the Standard Printer MIB.
                Additional information:
                This object reflects the state of 
                JOB-INPUT-AUTO-CONTINUE -MODE
                and JOB-INPUT-AUTO-CONTINUE-TIMEOUT. If
                JOB-INPUT-AUTO-CONTINUE-TIMEOUT is set to -1 or
                JOB-INPUT-AUTO-CONTINUE-MODE is set up to cancel the
                job, this object will return 0. If 
                JOB-INPUT-AUTO-CONTINUE-TIMEOUT is >= 0 and 
                JOB-INPUT-AUTO-CONTINUE-MODE is not set up to
                cancel the job, this object will return -2, meaning that
                a product-specific tray switching action will occur."
::= { prtInputEntry 26 }
               
               
prtoutputtype OBJECT-TYPE
    SYNTAX  INTEGER {
		   ePremovableBin(3),
		   ePunRemovableBin(4)
		   }
    ACCESS  read-only
    STATUS  optional
    DESCRIPTION
                "The type of technology supported by this output sub-unit.
	Refer to ftp://ftp.pwg.org/pub/pwg/pmp/drafts/pmib_031698.txt, for more details in the Standard Printer MIB."
::= { prtOutputEntry 2 }
               
               
prtoutputcapacityunit OBJECT-TYPE
    SYNTAX  INTEGER {
		   ePsheets(8)
		   }
    ACCESS  read-only
    STATUS  optional
    DESCRIPTION
                "The unit of measurement for use in calculating and relaying
        capacity values for this output sub-unit.
	Refer to ftp://ftp.pwg.org/pub/pwg/pmp/drafts/pmib_031698.txt, for more details in the Standard Printer MIB.
                Additional information:
                A sheet is a single piece of 20 pound paper."
::= { prtOutputEntry 3 }
               
               
prtoutputmaxcapacity OBJECT-TYPE
    SYNTAX  INTEGER
    ACCESS  read-only
    STATUS  optional
    DESCRIPTION
                "The maximum capacity of this output sub-unit in output
        sub-unit capacity units (PrtCapacityUnitTC). There is no
        convention associated with the media itself so this value
        essentially reflects claimed capacity. If this output
        sub-unit can reliably sense this value, the value is
        sensed by the printer and may not be changed by management
        requests; otherwise, the value may be written
        (by a Remote Control Panel or a Management Application).
        The value (-1) means other and specifically indicates
        that the sub-unit places no restrictions on this parameter.
        The value (-2) means unknown.
	Refer to ftp://ftp.pwg.org/pub/pwg/pmp/drafts/pmib_031698.txt, for more details in the Standard Printer MIB.
                Additional information:
                Replaces PML OUTBINn-MAXIMUM-CAPACITY.  
                Output sub-unit 2 is not supported if any output paper
                handling device is attached.  
                The capacity of sub-unit 4 depends on the mode of 
                operation. The capcities are as follows:  
                Stacker: OutBin3: 125   
                         OutBin4: 2000 (sub-units 5-15 do not exist)  
                Job Separator: OutBin3: 125   
                               OutBin4: 2000  
                Mailbox: OutBin3: 125 (this is the default mode)  
                         OutBin4: 250  
                         OutBin5: 250  
                         OutBin6: 250  
                         OutBin7: 250  
                         OutBin8: 250  
                         OutBin9: 250  
                         OutBin10: 250  
                         OutBin11: 250"
::= { prtOutputEntry 4 }
               
               
prtoutputremainingcapacity OBJECT-TYPE
    SYNTAX  INTEGER
    ACCESS  read-only
    STATUS  optional
    DESCRIPTION
                "The remaining capacity of the possible output sub-unit
        capacity in output sub-unit capacity units (PrtCapacityUnitTC)
        of this output sub-unit. If this output sub-unit can
        reliably sense this value, the value is sensed by the
        printer and may not be modified by management requests;
        otherwise, the value may be written (by
        a Remote Control Panel or a Management
        Application).  The value (-1) means other and
        specifically indicates that the sub-unit places no
        restrictions on this parameter.  The value (-2) means
        unknown.  The value (-3) means that the printer knows that
        there remains capacity for at least one unit.
	Refer to ftp://ftp.pwg.org/pub/pwg/pmp/drafts/pmib_031698.txt, for more details in the Standard Printer MIB.
                Additional information:
                Replaces PML NOT-READY-OUTBIN-FULL and
                STATUS-OUTBIN-FULL.  
                The values reported for output sub-unit 1 (face-down, 
                top bin) will be either (-3) if it is not
                full or (0) if it is full.   
                The first output sub-unit (3) of the MBM reports
                either (-3) if it is not full or (0) if
                it is full.  
                In mailbox mode, the MBM sub-units (4-11) will report
                (250) when empty, (0) when full. 
                Note: Due to MBM mechanism limitations, the value 
                reported may not always be accurate (the bin status is
                detected only when the media delivery head is moved to
                or past a physical bin). Also, for stacker mode a bin
                is considered full as long as any bin above it is not
                empty.  
                Default values assume all sub-units are empty and the
                MBM is in mailbox mode."
::= { prtOutputEntry 5 }
               
               
prtoutputstatus OBJECT-TYPE
    SYNTAX  INTEGER
    ACCESS  read-only
    STATUS  optional
    DESCRIPTION
                "The current status of this output sub-unit.
	Refer to ftp://ftp.pwg.org/pub/pwg/pmp/drafts/pmib_031698.txt, for more details in the Standard Printer MIB.
                Additional information:
                Replaces PML NOT-READY-OUTBIN-MISSING and
                STATUS-OUTBIN-MISSING.
                The default values assume all bins are empty.
                See SubUnitStatus in RFC1759 Printer MIB for details on
                values reported by this object. Yukon will not include
                values Available and Standby (2), Available and Active
                (4), Unknown (5) or Transitioning to intended state
                (64).
                Values returned by the firmware are detailed in the
                following table. 'Value Or'd Due To Condition' indicates
                that the specified value will be logically or'd into the
                value for this object when the specified Condition 
                occurs.
                Condition                       Value Or'd Due To Condition  
                ----------------------------    ---------------------------  
                Binder Error                    1 + 2  
                Bin full, binder empty,  
                bind limit reached, binder  
                align error, bin attention  
                error, or bin attention  
                warning                         1  
                Bin is current bin and  
                paper is moving                 4 + 2  
                Bin is the bin responsible  
                for Bin Full error message  
                being displayed                 16 + 32  
                Value 1 or 3 is Or'd in         8"
::= { prtOutputEntry 6 }
               
               
prtoutputname OBJECT-TYPE
    SYNTAX  OCTET STRING (SIZE(0..15))
    ACCESS  read-write
    STATUS  optional
    DESCRIPTION
                "The name assigned to this output sub-unit.
	Refer to ftp://ftp.pwg.org/pub/pwg/pmp/drafts/pmib_031698.txt, for more details in the Standard Printer MIB.
                Additional information:
                Replaces PML OUTBINn-NAME.
                The characters must be in the range 20H to 7FH except
                5C cannot be used. When this string is displayed on the
                control panel the Roman-8 symbol set is used.
              	Factory default bin names are localized, but users can 
                rename the output bins.  The STANDARD OUTBIN cannot be
                renamed, but all of the optional outbins can."
::= { prtOutputEntry 7 }
               
               
prtoutputvendorname OBJECT-TYPE
    SYNTAX  OCTET STRING (SIZE(0..63))
    ACCESS  read-only
    STATUS  optional
    DESCRIPTION
                "The vendor name of this output sub-unit.
	Refer to ftp://ftp.pwg.org/pub/pwg/pmp/drafts/pmib_031698.txt, for more details in the Standard Printer MIB."
::= { prtOutputEntry 8 }
               
               
prtoutputmodel OBJECT-TYPE
    SYNTAX  OCTET STRING (SIZE(0..63))
    ACCESS  read-only
    STATUS  optional
    DESCRIPTION
                "The name assigned to this output sub-unit.
	Refer to ftp://ftp.pwg.org/pub/pwg/pmp/drafts/pmib_031698.txt, for more details in the Standard Printer MIB.
                Additional information:
                The value returned by the MBM depends on the current
                mode of the device. The possible values are as follows:  
                			MULTIBIN MAILBOX MBM-8 C4785B  
                MULTIBIN MAILBOX MBM-5S C4787A  
                STAPLER MODULE C3766A"
::= { prtOutputEntry 9 }
               
               
prtoutputversion OBJECT-TYPE
    SYNTAX  OCTET STRING (SIZE(0..63))
    ACCESS  read-only
    STATUS  optional
    DESCRIPTION
                "The version of this output sub-unit.
	Refer to ftp://ftp.pwg.org/pub/pwg/pmp/drafts/pmib_031698.txt, for more details in the Standard Printer MIB.
                Additional information:
                Returns device-specific information about the
                configuration of the output bin. May include
                information about the type of processing that can be 
                done to media sent to this bin; processing includes but
                is not limited to binding, punching, folding and 
                sealing. Format of this object is specified by the
                output device documentation."
::= { prtOutputEntry 10 }
               
               
prtoutputserialnumber OBJECT-TYPE
    SYNTAX  OCTET STRING (SIZE(0..63))
    ACCESS  read-only
    STATUS  optional
    DESCRIPTION
                "The serial number assigned to this output sub-unit.
	Refer to ftp://ftp.pwg.org/pub/pwg/pmp/drafts/pmib_031698.txt, for more details in the Standard Printer MIB.
                Additional information:
                Yukon does not support a serial number for output
                devices."
::= { prtOutputEntry 11 }
               
               
prtoutputdescription OBJECT-TYPE
    SYNTAX  OCTET STRING (SIZE(0..255))
    ACCESS  read-only
    STATUS  optional
    DESCRIPTION
                "  A free-form text description of this output sub-unit in the
        localization specified by prtGeneralCurrentLocalization.
	Refer to ftp://ftp.pwg.org/pub/pwg/pmp/drafts/pmib_031698.txt, for more details in the Standard Printer MIB.
                Additional information:
                This object returns the exact same string as 		
                prtOutputName. The factory default bin names
                are localized, but users have the ability to
                rename them."
::= { prtOutputEntry 12 }
               
               
prtoutputsecurity OBJECT-TYPE
    SYNTAX  INTEGER {
		   ePother(1),
		   ePon(3),
		   ePoff(4),
		   ePnotPresent(5)
		   }
    ACCESS  read-only
    STATUS  optional
    DESCRIPTION
                "Indicates if this output sub-unit has some security associated
        with it and if that security is enabled or not.
	Refer to ftp://ftp.pwg.org/pub/pwg/pmp/drafts/pmib_031698.txt, for more details in the Standard Printer MIB.
                Additional information:
                No security mechanism provided."
::= { prtOutputEntry 13 }
               
               
prtoutputdimunit OBJECT-TYPE
    SYNTAX  INTEGER {
		   ePtenThousandthsOfInches(3),
		   ePmicrometers(4)
		   }
    ACCESS  read-only
    STATUS  optional
    DESCRIPTION
                "The unit of measurement for use in calculating and relaying
        dimensional values for this output sub-unit.
	Refer to ftp://ftp.pwg.org/pub/pwg/pmp/drafts/pmib_031698.txt, for more details in the Standard Printer MIB.
                Additional information:
                See the description for prtInputDimUnit for a table
                of dimensions for supported paper sizes for Yukon."
::= { prtOutputEntry 14 }
               
               
prtoutputmaxdimfeeddir OBJECT-TYPE
    SYNTAX  INTEGER
    ACCESS  read-only
    STATUS  optional
    DESCRIPTION
                "The maximum dimensions supported by this output sub-unit
        for measurements taken parallel relative to the feed
        direction associated with that sub-unit in output
        sub-unit dimensional units (MediaUnit). If this output
        sub-unit can reliably sense this value, the value is
        sensed by the printer and may not be changed with
        management protocol operations.
	Refer to ftp://ftp.pwg.org/pub/pwg/pmp/drafts/pmib_031698.txt, for more details in the Standard Printer MIB.
                Additional information:
                The value returned by this object depends on the value
                of prtOutputDimUnit. For example, for the built-in 
                output bins, it is 177000 if prtOutputDimUnit is 
                ePtenThousandthsOfInches or 450000 if prtOutputDimUnit 
                is ePmicrometers.  
                177000 is the largest custom size supported by Yukon.
                170000 is the long dimension of Ledger paper, the largest
                dimension supported by an output device."
::= { prtOutputEntry 15 }
               
               
prtoutputmaxdimxfeeddir OBJECT-TYPE
    SYNTAX  INTEGER
    ACCESS  read-only
    STATUS  optional
    DESCRIPTION
                "The maximum dimensions supported by this output sub-unit
        for measurements taken ninety degrees relative to the
        feed direction associated with that sub-unit in output
        sub-unit dimensional units (MediaUnit). If this output
        sub-unit can reliably sense this value, the value is
        sensed by the printer and may not be changed with
        management protocol operations.
	Refer to ftp://ftp.pwg.org/pub/pwg/pmp/drafts/pmib_031698.txt, for more details in the Standard Printer MIB.
                Additional information:
                The value returned by this object depends on the value
                of prtOutputDimUnit. For example, for the built-in
                output bins, it is 117000 if prtOutputDimUnit is 
                ePtenThousandthsOfInches and 297180 if prtOutputDimUnit 
                is ePmicrometers."
::= { prtOutputEntry 16 }
               
               
prtoutputmindimfeeddir OBJECT-TYPE
    SYNTAX  INTEGER
    ACCESS  read-only
    STATUS  optional
    DESCRIPTION
                "The minimum dimensions supported by this output sub-unit
        for measurements taken parallel relative to the feed
        direction associated with that sub-unit in output
        sub-unit dimensional units (DimUnit).  If this output
        sub-unit can reliably sense this value, the value is
        sensed by the printer and may not be changed with
        management protocol operations.
	Refer to ftp://ftp.pwg.org/pub/pwg/pmp/drafts/pmib_031698.txt, for more details in the Standard Printer MIB.
                Additional information:
                The value returned by this object depends on the value
                of prtOutputDimUnit. For example, for the built-in 
                output bins, it is 75000 if prtOutputDimUnit is
                ePtenThousandthsOfInches or 190500 if prtOutputDimUnit
                is ePmicrometers."
::= { prtOutputEntry 17 }
               
               
prtoutputmindimxfeeddir OBJECT-TYPE
    SYNTAX  INTEGER
    ACCESS  read-only
    STATUS  optional
    DESCRIPTION
                "The minimum dimensions supported by this output sub-unit
        for measurements taken ninety degrees relative to the
        feed direction associated with that sub-unit in output
        sub-unit dimensional units (DimUnit). If this output
        sub-unit can reliably sense this value, the value is
        sensed by the printer and may not be changed with
        management protocol operations.
	Refer to ftp://ftp.pwg.org/pub/pwg/pmp/drafts/pmib_031698.txt, for more details in the Standard Printer MIB.
                Additional information:
                The value returned by this object depends on the value
                of prtOutputDimUnit. For example, for the built-in
                output trays, it is 36700 if prtOutputDimUnit is 
                ePtenThousandthsOfInches or 93000 if prtOutputDimUnit
                is ePmicrometers."
::= { prtOutputEntry 18 }
               
               
prtoutputstackingorder OBJECT-TYPE
    SYNTAX  INTEGER {
		   ePunknown(2),
		   ePfirstToLast(3),
		   ePlastToFirst(4)
		   }
    ACCESS  read-only
    STATUS  optional
    DESCRIPTION
                "The current state of the stacking order for the
        associated output sub-unit. `FirstToLast' means
        that as pages are output the front of the next page is
        placed against the back of the previous page.
        `LasttoFirst' means that as pages are output the back
        of the next page is placed against the front of the
        previous page.
	Refer to ftp://ftp.pwg.org/pub/pwg/pmp/drafts/pmib_031698.txt, for more details in the Standard Printer MIB.
                Additional information:
                Replaces PML OUTBINn-STACK-ORDER."
::= { prtOutputEntry 19 }
               
               
prtoutputpagedeliveryorientation OBJECT-TYPE
    SYNTAX  INTEGER {
		   ePfaceUp(3),
		   ePfaceDown(4)
		   }
    ACCESS  read-only
    STATUS  optional
    DESCRIPTION
                "The reading surface that will be `up' when pages are
        delivered to the associated output sub-unit. Values are
        faceUp and faceDown. (Note: interpretation of these
        values is in general context-dependent based on locale;
        presentation of these values to an end-user should be
        normalized to the expectations of the user).
	Refer to ftp://ftp.pwg.org/pub/pwg/pmp/drafts/pmib_031698.txt, for more details in the Standard Printer MIB."
::= { prtOutputEntry 20 }
               
               
prtoutputbursting OBJECT-TYPE
    SYNTAX  INTEGER {
		   ePother(1),
		   ePon(3),
		   ePoff(4),
		   ePnotPresent(5)
		   }
    ACCESS  read-only
    STATUS  optional
    DESCRIPTION
                "This object indicates that the outputting sub-unit
        supports bursting, and if so, whether the feature is enabled.
        Bursting is the process by which continuous media is separated
        into individual sheets, typically by bursting along pre-formed
        perforations.
	Refer to ftp://ftp.pwg.org/pub/pwg/pmp/drafts/pmib_031698.txt, for more details in the Standard Printer MIB.
                Additional information:
                Bursting is not supported."
::= { prtOutputEntry 21 }
               
               
prtoutputdecollating OBJECT-TYPE
    SYNTAX  INTEGER {
		   ePother(1),
		   ePon(3),
		   ePoff(4),
		   ePnotPresent(5)
		   }
    ACCESS  read-only
    STATUS  optional
    DESCRIPTION
                "This object indicates that the output supports
        supports decollating, and if so, whether the feature
        is enabled. Decollating is the process by which the
        individual parts within a multi-part form are separated
        and sorted into separate stacks for each part.
	Refer to ftp://ftp.pwg.org/pub/pwg/pmp/drafts/pmib_031698.txt, for more details in the Standard Printer MIB.
                Additional information:
                Decollating is not supported."
::= { prtOutputEntry 22 }
               
               
prtoutputpagecollated OBJECT-TYPE
    SYNTAX  INTEGER {
		   ePother(1),
		   ePon(3),
		   ePoff(4),
		   ePnotPresent(5)
		   }
    ACCESS  read-only
    STATUS  optional
    DESCRIPTION
                "This object indicates that the output sub-unit
        supports page collation, and if so, whether the feature is
        enabled. See glossary for definition of how this document defines
        collation.
	Refer to ftp://ftp.pwg.org/pub/pwg/pmp/drafts/pmib_031698.txt, for more details in the Standard Printer MIB.
                Additional information:
                Page collation is not supported."
::= { prtOutputEntry 23 }
               
               
prtoutputoffsetstacking OBJECT-TYPE
    SYNTAX  INTEGER {
		   ePother(1),
		   ePon(3),
		   ePoff(4),
		   ePnotPresent(5)
		   }
    ACCESS  read-only
    STATUS  optional
    DESCRIPTION
                "This object indicates that the output supports
        supports offset stacking, and if so, whether the feature is
        enabled. See glossary for how Offset Stacking is defined by this
        document.
	Refer to ftp://ftp.pwg.org/pub/pwg/pmp/drafts/pmib_031698.txt, for more details in the Standard Printer MIB.
                Additional information:
                Offset stacking is not supported."
::= { prtOutputEntry 24 }
               
               
END
