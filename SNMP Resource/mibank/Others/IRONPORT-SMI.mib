--- MIB created 11/03/04

IRONPORT-SMI DEFINITIONS ::= BEGIN

--
-- Top-level infrastructure of the IronPort project enterprise MIB tree
--

IMPORTS
    MODULE-IDENTITY, enterprises FROM SNMPv2-SMI;

ironPort MODULE-IDENTITY
 LAST-UPDATED "200506170000Z"
 ORGANIZATION "IronPort Systems"
 CONTACT-INFO "Postal: 950 Elm Avenue
               San Bruno, CA 94066
               USA

               Email:  customercare@ironport.com"
 DESCRIPTION
               "Top-level infrastructure of the IronPort project
                enterprise MIB tree"
 REVISION      "200506170000Z"
 DESCRIPTION
               "Beta1 Release."
                  ::= { enterprises 15497 }


--
--  IronPort enterprise-specific management objects
--


asyncOSAppliances              OBJECT IDENTIFIER ::= {ironPort 1}
asyncOSMail                    OBJECT IDENTIFIER ::= {asyncOSAppliances  1}
asyncOSWebSecurityAppliance    OBJECT IDENTIFIER ::= {asyncOSAppliances  2}
--ironPort OBJECT IDENTIFIER ::= { enterprises 15497 }
END
