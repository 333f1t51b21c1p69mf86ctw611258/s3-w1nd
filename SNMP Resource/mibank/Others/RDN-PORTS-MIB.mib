RDN-PORTS-MIB DEFINITIONS ::= BEGIN

    IMPORTS
        MODULE-IDENTITY
            FROM SNMPv2-SMI
        rdnDefinitions
            FROM RDN-DEFINITIONS-MIB;

    -- riverdelta ports definitions mib module

    rdnPorts MODULE-IDENTITY
        LAST-UPDATED "0105080000Z" -- example "9501201225Z"
                                   -- Fri Jan 20 12:25:50 PST 1995
        ORGANIZATION "Motorola"
        CONTACT-INFO "Motorola
                      3 Highwood Drive
                      Tewksbury, MA 01867
                      Tel: +1 978 858 2000
                      Fax: +1 978 858 2399
                      E-mail:  BSRSNMP@maillist2001.mot.com

                      Tom Keske
                      Motorola BCS
                      20 Cabot Blvd. MA07 M2-330
                      Mansfield, MA 02048
                      Tel: 1-508-851-8325
                      Fax: 1-508-851-8510
                      E-mail: Tom.Keske@motorola.com"
        DESCRIPTION
                "MIB module for Motorola Port
                definitions."
        REVISION     "0105080000Z"
        DESCRIPTION
                "Initial creation."
        ::= { rdnDefinitions 5 }


      --
      -- module definitions for all riverdelta modules
      --

      rdnPortsUnknown           OBJECT IDENTIFIER ::= { rdnPorts 0 }
      rdnPortsGige              OBJECT IDENTIFIER ::= { rdnPorts 1 }
      rdnPortsEthernet          OBJECT IDENTIFIER ::= { rdnPorts 2 }
      rdnPortsCableMac          OBJECT IDENTIFIER ::= { rdnPorts 3 }
      rdnPortsCableUpstream     OBJECT IDENTIFIER ::= { rdnPorts 4 }
      rdnPortsCableDownstream   OBJECT IDENTIFIER ::= { rdnPorts 5 }
      rdnPortsLoopback          OBJECT IDENTIFIER ::= { rdnPorts 6 }
      rdnPortsT1                OBJECT IDENTIFIER ::= { rdnPorts 7 }
      rdnPortsNull              OBJECT IDENTIFIER ::= { rdnPorts 8 }
      rdnPortsTunnel            OBJECT IDENTIFIER ::= { rdnPorts 9 }
      rdnPortsPOS               OBJECT IDENTIFIER ::= { rdnPorts 10 }
      rdnPortsATM               OBJECT IDENTIFIER ::= { rdnPorts 11 }

END


-- *****************************************************************
-- 
-- RDN-SENSOR-TYPE-MIB:
--             RiverDelta Sensor Type Object Identifier Assignments
--             (riverdelta.rdnDefinitions.rdnSensorType
--                                           - 1.3.6.1.4.1.4981.4.6)
--
-- August 2001, Thor Kirleis (thor@riverdelta.com)
--
-- Copyright (c) 2001 RiverDelta Networks, all rights reserved.
-- 
-- *****************************************************************
