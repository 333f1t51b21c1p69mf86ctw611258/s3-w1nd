PDN-ARP-MIB DEFINITIONS ::= BEGIN

-- Version :  3.0 
-- Enterprise pdn arp mib
-- Copyright (C) 2000 Paradyne Corporation.

-- Created by : Wayne Jadoo / Prakash Easwar
-- Last Updated 05/02/2000 Dragana Gough

-- History
--
-- 05/02/2000
-- Updated MIB file to add history 

-- This MIB contains objects that is used configure
-- ARP Entries and display ARP information on a Device

IMPORTS
SwitchState, VnidRange
FROM PDN-TC
MacAddress, TruthValue,
RowStatus
FROM SNMPv2-TC
OBJECT-TYPE
FROM RFC-1212
IpAddress
FROM RFC1155-SMI
ifIndex
FROM RFC1213-MIB
pdn-arp
FROM PDN-HEADER-MIB
;


-- Bit32 is temporarily defined here to get pdn_Arp.mib to compile.
-- A textual convention is being defined for bit32, but needs 
-- to be approved by the mibwg. Until this has been completed
-- a temporary defintion is used here in order to get this mib
-- to compile to be proposed.

Bit32 ::= INTEGER 

pdnNetToMediaGenericMIBObjects  OBJECT IDENTIFIER ::= { pdn-arp 1 }
pdnNetToMediaMIBTraps OBJECT IDENTIFIER ::= { pdn-arp 2 }
pdnNetToMediaParams OBJECT IDENTIFIER ::= { pdnNetToMediaGenericMIBObjects 1 }
pdnNetToMediaConfig OBJECT IDENTIFIER ::= { pdnNetToMediaGenericMIBObjects 2 }
pdnNetTo8023MediaConfig OBJECT IDENTIFIER ::= { pdnNetToMediaGenericMIBObjects 3 }

-- The ARP Parameters Configuration  group

          pdnNetToMediaParamsCompEntryTimeout OBJECT-TYPE
              SYNTAX  INTEGER
              ACCESS  read-write
              STATUS  mandatory
              DESCRIPTION
                      " Complete Entry Timeout is the length of time that 
                        a complete entry remains in the ARP table before 
                        removal.  A complete entry is one for which there is 
                        a MAC address -- i.e. a node has responded to the
                        ARP request. If an entry gets this old without being 
                        referenced, it will be removed from the table.  The 
                        range for this parameter is 1  to 200000 minutes."
              DEFVAL { 20 }
              ::= { pdnNetToMediaParams 1 }

          pdnNetToMediaParamsIncompEntryTimeout OBJECT-TYPE
              SYNTAX   INTEGER 
              ACCESS   read-write
              STATUS   mandatory
              DESCRIPTION
                      " Incomplete Entry Timeout is the length of time that 
                        an incomplete entry remains in the ARP table before 
                        removal. An incomplete entry is one for which there 
                        is no MAC address -- i.e. an ARP request has been made,
                        but no response has been received. This is also the 
                        amount of time that a packet will remain in the system 
                        while waiting for address resolution. The range 
                        for this parameter is  1 to  255  minutes."
              DEFVAL { 3 }
              ::= { pdnNetToMediaParams 2 }
        
          pdnNetToMediaParamsDefRouteEntryTimeout OBJECT-TYPE
              SYNTAX   INTEGER 
              ACCESS   read-write
              STATUS   mandatory
              DESCRIPTION
                      "Default Route Entry Timeout is the length of time 
                       a default route entry will remain in the ARP table. 
                       If default route gets this old without being referenced,
                       an ARP request will be sent to the next hop router.
                       If no response is received, it will be removed from 
                       the ARP table and the card will switch to the next 
                       reachable default route with the highest preference. 
                       The range for this parameter is 1  to  20  minutes."
              DEFVAL { 1 }
              ::= { pdnNetToMediaParams 3 }


 -- The ARP Entry Configuration Table for 802.3 Media Cards


          pdnNetToMediaConfigTable OBJECT-TYPE
              SYNTAX  SEQUENCE OF PdnNetToMediaConfigEntry
              ACCESS  not-accessible
              STATUS  mandatory
              DESCRIPTION
                 "A table displaying  information about ARP Entries"
              ::= { pdnNetToMediaConfig 1 }

          pdnNetToMediaConfigEntry OBJECT-TYPE
              SYNTAX  PdnNetToMediaConfigEntry
              ACCESS  not-accessible
              STATUS  mandatory
              DESCRIPTION
                      "A list of information for each ARP Entry in the 
                       ARP Table to be displayed."
              INDEX  { ifIndex,
                       pdnNetToMediaConfigIpAddr }
              ::= { pdnNetToMediaConfigTable 1 }

          PdnNetToMediaConfigEntry ::=
              SEQUENCE {
                  pdnNetToMediaConfigIpAddr     IpAddress,
                  pdnNetToMediaConfigMacAddr    MacAddress,
                  pdnNetToMediaConfigMin        INTEGER,
                  pdnNetToMediaConfigFlags      Bit32,
                  pdnNetToMediaConfigTrailer    SwitchState,
                  pdnNetToMediaConfigPerm       TruthValue,
                  pdnNetToMediaConfigRowStatus  RowStatus
            }
          
			 pdnNetToMediaConfigIpAddr OBJECT-TYPE
              SYNTAX  IpAddress
              ACCESS  read-only
              STATUS  mandatory
              DESCRIPTION
                 "This objects corresponds to an IP Address of a
                  Host or Client "
              ::= { pdnNetToMediaConfigEntry 1 }

          pdnNetToMediaConfigMacAddr OBJECT-TYPE
              SYNTAX  MacAddress
              ACCESS  read-write
              STATUS  mandatory
              DESCRIPTION
             	"This object corresponds to a MAC Address of a Host 
                 or Client"
              ::= { pdnNetToMediaConfigEntry 2 }

          pdnNetToMediaConfigMin OBJECT-TYPE
              SYNTAX  INTEGER
              ACCESS  read-only
              STATUS  mandatory
              DESCRIPTION
                      "This objects displays the number of
                       minutes since an Arp entry was last 
                       used." 
              ::= { pdnNetToMediaConfigEntry 3 }

          pdnNetToMediaConfigFlags OBJECT-TYPE
              SYNTAX  Bit32
              ACCESS  read-only
              STATUS  mandatory
              DESCRIPTION
                      " This object contains multiple information
                        for an entry. The information can be
                        interpreted as follows: 
                        0x0004  -- permanent entry 
                        0x0008  -- publish entry (respond for other host) 
                        0x0010  -- has requested trailers 
                        0x0020  -- Proxy Arp Entry 
                        0x0040  -- Subnetted Proxy ARP entry 
                        0x0100  -- Arp For Default Gateway 
                      " 
              ::= { pdnNetToMediaConfigEntry 4 }

          pdnNetToMediaConfigTrailer OBJECT-TYPE
              SYNTAX  SwitchState
              ACCESS  read-write
              STATUS  mandatory
              DESCRIPTION
                      "This object is used to specify whether 
                       or not trailer encapsulation should be 
                       enabled or disabled" 
              ::= { pdnNetToMediaConfigEntry 5 }

          pdnNetToMediaConfigPerm OBJECT-TYPE
              SYNTAX  TruthValue 
              ACCESS  read-write
              STATUS  mandatory
              DESCRIPTION
                      "This object is used to specify whether 
                       or not an entry should be stored permanently
                       in Non-volatile storage. If the value is 
                       'true' (1) a permanent entry is added to 
                       non-volatile storage.  " 
              ::= { pdnNetToMediaConfigEntry 6 }

          pdnNetToMediaConfigRowStatus OBJECT-TYPE
              SYNTAX  RowStatus 
              ACCESS  read-write
              STATUS  mandatory
              DESCRIPTION
                      "This object is used to create or delete a row in this
                       table " 
              ::= { pdnNetToMediaConfigEntry 7 }


 -- The ARP Entry Configuration Table for 802.3 Media Cards


          pdnNetTo8023MediaConfigTable OBJECT-TYPE
              SYNTAX  SEQUENCE OF PdnNetTo8023MediaConfigEntry
              ACCESS  not-accessible
              STATUS  mandatory
              DESCRIPTION
                 "A table displaying  information about ARP Entries"
              ::= { pdnNetTo8023MediaConfig 1 }

          pdnNetTo8023MediaConfigEntry OBJECT-TYPE
              SYNTAX  PdnNetTo8023MediaConfigEntry
              ACCESS  not-accessible
              STATUS  mandatory
              DESCRIPTION
                      "A list of information for each ARP Entry in the 
                       ARP Table to be displayed."
              INDEX  { ifIndex,
                       pdnNetTo8023MediaConfigIpAddr, 
                       pdnNetTo8023MediaConfigVnidId }
              ::= { pdnNetTo8023MediaConfigTable 1 }

          PdnNetTo8023MediaConfigEntry ::=
              SEQUENCE {
                  pdnNetTo8023MediaConfigIpAddr     IpAddress,
                  pdnNetTo8023MediaConfigVnidId     VnidRange,
                  pdnNetTo8023MediaConfigMacAddr    MacAddress,
                  pdnNetTo8023MediaConfigMin        INTEGER,
                  pdnNetTo8023MediaConfigFlags      Bit32,
                  pdnNetTo8023MediaConfigTrailer    SwitchState,
                  pdnNetTo8023MediaConfigPerm       TruthValue,
                  pdnNetTo8023MediaConfigRowStatus  RowStatus
            }
          
			 pdnNetTo8023MediaConfigIpAddr OBJECT-TYPE
              SYNTAX  IpAddress
              ACCESS  read-only
              STATUS  mandatory
              DESCRIPTION
                 "This objects corresponds to an IP Address of a
                  Host or Client "
              ::= { pdnNetTo8023MediaConfigEntry 1 }

          pdnNetTo8023MediaConfigVnidId    OBJECT-TYPE
              SYNTAX  VnidRange
              ACCESS  read-only
              STATUS  mandatory
              DESCRIPTION
                 "The VNID Id number of the virtual network for which this entry
                  contains management information."
              ::= { pdnNetTo8023MediaConfigEntry 2 }

          pdnNetTo8023MediaConfigMacAddr OBJECT-TYPE
              SYNTAX  MacAddress
              ACCESS  read-only
              STATUS  mandatory
              DESCRIPTION
             	"This object corresponds to a MAC Address of a Host 
                 or Client"
              ::= { pdnNetTo8023MediaConfigEntry 3 }

          pdnNetTo8023MediaConfigMin OBJECT-TYPE
              SYNTAX  INTEGER
              ACCESS  read-only
              STATUS  mandatory
              DESCRIPTION
                      "This objects displays the number of
                       minutes since an Arp entry was last 
                       used." 
              ::= { pdnNetTo8023MediaConfigEntry 4 }

          pdnNetTo8023MediaConfigFlags OBJECT-TYPE
              SYNTAX  Bit32
              ACCESS  read-only
              STATUS  mandatory
              DESCRIPTION
                      " This object contains multiple information
                        for an entry. The information can be
                        interpreted as follows: 
                        0x0004  -- permanent entry 
                        0x0008  -- publish entry (respond for other host) 
                        0x0010  -- has requested trailers 
                        0x0020  -- Proxy Arp Entry 
                        0x0040  -- Subnetted Proxy ARP entry 
                        0x0100  -- Arp For Default Gateway 
                      " 
              ::= { pdnNetTo8023MediaConfigEntry 5 }

          pdnNetTo8023MediaConfigTrailer OBJECT-TYPE
              SYNTAX  SwitchState
              ACCESS  read-write
              STATUS  mandatory
              DESCRIPTION
                      "This object is used to specify whether 
                       or not trailer encapsulation should be 
                       enabled or disabled" 
              ::= { pdnNetTo8023MediaConfigEntry 6 }

          pdnNetTo8023MediaConfigPerm OBJECT-TYPE
              SYNTAX  TruthValue 
              ACCESS  read-write
              STATUS  mandatory
              DESCRIPTION
                      "This object is used to specify whether 
                       or not an entry should be stored permanently
                       in Non-volatile storage. If the value is 
                       'true' (1) a permanent entry is added to 
                       non-volatile storage.  " 
              ::= { pdnNetTo8023MediaConfigEntry 7 }

          pdnNetTo8023MediaConfigRowStatus OBJECT-TYPE
              SYNTAX  RowStatus 
              ACCESS  read-write
              STATUS  mandatory
              DESCRIPTION
                      "This object is used to create or delete a row in this
                       table " 
              ::= { pdnNetTo8023MediaConfigEntry 8 }

-- groups for ARP MIB

	pdnNetToMediaClearAllArp  OBJECT-TYPE
	    SYNTAX INTEGER {
	       noop (1),
	       clear (2)
			   }
	    ACCESS read-write
	    STATUS mandatory
	    DESCRIPTION
		    " Setting this object to a value of 'clear' will remove all entries 
		      from the ARP table."
	    ::= { pdnNetToMediaConfig 2 }

-- Proxy ARP 

	pdnNetToMediaProxyArpTable  OBJECT-TYPE
	    SYNTAX SEQUENCE OF PdnNetToMediaProxyArpEntry
	    ACCESS not-accessible
	    STATUS mandatory 
	    DESCRIPTION
		    " This table is used to enable or disable
		      proxy ARP for the specified interface. "
	    ::= { pdnNetToMediaConfig 3 }

	pdnNetToMediaProxyArpEntry OBJECT-TYPE
	    SYNTAX  PdnNetToMediaProxyArpEntry
	    ACCESS  not-accessible
	    STATUS  mandatory
	    DESCRIPTION
		    " This is an entry that allows user to enable or disable
		      proxy ARP for the specified interface. "
	    INDEX  { ifIndex }
	    ::= { pdnNetToMediaProxyArpTable 1 }

	PdnNetToMediaProxyArpEntry ::=
	    SEQUENCE {
               pdnNetToMediaProxyArpStatus	INTEGER
	    }

        pdnNetToMediaProxyArpStatus   OBJECT-TYPE
	    SYNTAX   INTEGER  { disable (1), enable (2) }
	    ACCESS   read-write
	    STATUS   mandatory
	    DESCRIPTION
		    " Setting this object to a value 'enable' will enable
		      proxy ARP for the interface identified by IfIndex.
		      The value 'disable' will disable proxy ARP for
		      the interface. "
	    ::= { pdnNetToMediaProxyArpEntry 1 }
        
          END
