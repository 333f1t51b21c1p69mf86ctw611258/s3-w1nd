--========================================================
--
-- MIB      : IPO  Avaya Inc.
--
-- Version  : 2.00.02   28 April 2008
--
--========================================================
--
-- Copyright (c) 2003 - 2008 Avaya Inc.
-- All Rights Reserved.
--
--========================================================
IPO-MIB DEFINITIONS ::= BEGIN

IMPORTS
    MODULE-IDENTITY, OBJECT-TYPE,
    NOTIFICATION-TYPE, Unsigned32, Integer32,
    IpAddress
        FROM SNMPv2-SMI
    DateAndTime
        FROM SNMPv2-TC
    MODULE-COMPLIANCE, OBJECT-GROUP,
    NOTIFICATION-GROUP
        FROM SNMPv2-CONF
    SnmpAdminString
        FROM SNMP-FRAMEWORK-MIB
    sysDescr
        FROM SNMPv2-MIB
    ItuPerceivedSeverity
        FROM ITU-ALARM-TC-MIB
    ifIndex
        FROM IF-MIB
    avayaMibs
        FROM AVAYAGEN-MIB
	;

ipoMIB MODULE-IDENTITY
    LAST-UPDATED    "200804281640Z" -- 28 April 2008
    ORGANIZATION    "Avaya Inc."
    CONTACT-INFO
        "Avaya Customer Services
         Postal: Avaya, Inc.
                 211 Mt Airy Rd.
                 Basking Ridge, NJ 07920
                 USA
         Tel:    +1 908 953 6000

         WWW:    http://www.avaya.com"
    DESCRIPTION
        "Avaya IP Office MIBs OID tree.

         This MIB module defines the root items for MIBs for
         use with Avaya IP Office family of telephone switches."

    REVISION    "200804281640Z" -- 28 April 2008
    DESCRIPTION
        "Rev 2.00.02
        Added smallBusinessContactCenter(3) value to
        ipoGTEventAppEntity."
    REVISION    "200804181450Z" -- 18 April 2008
    DESCRIPTION
        "Rev 2.00.01
        Added traps related to Universal PRI licensing."
    REVISION    "200606290000Z" -- 29 June 2006
    DESCRIPTION
        "Rev 2.00.00
        Traps/notifications revised to provide more information about
        the entity and device concerned."
    REVISION    "200410060000Z" -- 06 October 2004
    DESCRIPTION
        "Rev 1.00.08
        Corrected description of event severities for physical
        entities."
    REVISION    "200408270000Z" -- 27 August 2004
    DESCRIPTION
        "Rev 1.00.07
        Corrected mandatory groups after addition of SOG event
        related objects and notifications."
    REVISION    "200408060000Z" -- 06 August 2004
    DESCRIPTION
        "Rev 1.00.06
        Added SOG event related object and notifications."
    REVISION 	"200407100000Z" -- 10 July 2004
    DESCRIPTION
        "Rev 1.00.05
        Added application event related object and notifications.
        Corrected description of ipoGenLKSCommsOperationalEvent."
    REVISION 	"200405280000Z" -- 28 May 2004
    DESCRIPTION
        "Rev 1.00.04
        Revised usage description for ipoGTEventSeverity."
    REVISION 	"200403030000Z" -- 03 March 2004
    DESCRIPTION
        "Rev 1.00.03
        Revised for external publication."
    REVISION 	"200312150000Z" -- 15 December 2003
    DESCRIPTION
        "Rev 1.00.02
        Added loopback object and notification."
    REVISION 	"200311110000Z" -- 11 November 2003
    DESCRIPTION
        "Rev 1.00.01
        Corrected ipoGTEventEntity MAX-ACCESS."
    REVISION 	"200310100000Z" -- 10 October 2003
    DESCRIPTION
        "Rev 1.00.00
        The first published version of this MIB module."
    ::= { avayaMibs 2 }

-- sub-tree for IP Office wide objects and events irrespective of function
ipoGeneric         OBJECT IDENTIFIER ::= { ipoMIB 1 }

-- sub-tree for IP Office functional MIBs
ipoGenMibs         OBJECT IDENTIFIER ::= { ipoGeneric 1 }

-- sub-tree for IP Office wide traps/notifications
ipoGenTraps        OBJECT IDENTIFIER ::= { ipoGeneric 2 }

-- sub-tree for IP Office wide conformance information
ipoGenConformance  OBJECT IDENTIFIER ::= { ipoGeneric 3 }

--********************************************************************
-- IP Office wide traps/notifications
--********************************************************************

ipoGTEvents  OBJECT IDENTIFIER ::= { ipoGenTraps 0 }
ipoGTObjects OBJECT IDENTIFIER ::= { ipoGenTraps 1 }

--
-- trap objects
--

ipoGTEventSeverity OBJECT-TYPE
    SYNTAX      INTEGER {
        critical(1),
	major(2),
	minor(3)
    }
    MAX-ACCESS  accessible-for-notify
    STATUS      deprecated
    DESCRIPTION
        "Severity of the event that has occurred.

        The event severity depends upon the type of
        entity/notification that the operational state change event
        relates to:

        GenEntityEvents:

        Type of physical   Severity
        entity
        container          critical
        module             major
        port               major

        Known transient errors for entities have a severity of minor.

        LKSCommsEvents:
        Severity is major

        GenLoopbackEvent:
        Severity is major

        GenAppEvents:
        Severity depends on sub-event
        Failure/Operational - severity is major
        Event               - severity depends on event condition

        ipoGenSogEvents:
        Severity depends on sub-event
        HostFailure         - severity is Major
        ModeChange:
          - Mode survivable: severity is Major
          - Mode subTending: severity is Minor

        PhoneChangeEvents:
        Severity is minor

        **NOTE: This object is deprecated and replaced by
          ipoGTEventStdSeverity."
    ::= { ipoGTObjects 1 }

ipoGTEventDateTime OBJECT-TYPE
    SYNTAX      DateAndTime
    MAX-ACCESS  accessible-for-notify
    STATUS      current
    DESCRIPTION
        "Date and time of the occurence of the event."
    ::= { ipoGTObjects 2 }

ipoGTEventEntity OBJECT-TYPE
    SYNTAX      Unsigned32
    MAX-ACCESS  accessible-for-notify
    STATUS      current
    DESCRIPTION
        "A reference, by entPhysicalIndex value, to the
        EntPhysicalEntry representing the physical entity that an
        event is associated with in an entity MIB instantiation within
        the IP Office agent."
    ::= { ipoGTObjects 3 }

ipoGTEventLoopbackStatus OBJECT-TYPE
    SYNTAX      Integer32 (1..127)
    MAX-ACCESS  accessible-for-notify
    STATUS      deprecated
    DESCRIPTION
        "This variable represents the current state of the
         loopback on the DS1 interface.  It contains
         information about loopbacks established by a
         manager and remotely from the far end.

         The ipoGTEventLoopbackStatus is a bit map represented as
         a sum, therefore is can represent multiple
         loopbacks simultaneously.

         The various bit positions are:
          1  noLoopback
          2  nearEndPayloadLoopback
          4  nearEndLineLoopback
          8  nearEndOtherLoopback
         16  nearEndInwardLoopback
         32  farEndPayloadLoopback
         64  farEndLineLoopback"
    ::= { ipoGTObjects 4 }

ipoGTEventAppEntity OBJECT-TYPE
    SYNTAX      INTEGER {
          voiceMail(1),
          deltaServer(2),
          smallBusinessContactCenter(3)
    }
    MAX-ACCESS  accessible-for-notify
    STATUS      current
    DESCRIPTION
        "The IP Office application to which a notification/trap
        relates."
    ::= { ipoGTObjects 5 }

ipoGTEventAppEvent OBJECT-TYPE
    SYNTAX      INTEGER {
              storageFull(1), -- severity: Critical
        storageNearlyFull(2), -- severity: Major
              storageOkay(3)  -- severity: Minor
    }
    MAX-ACCESS  accessible-for-notify
    STATUS      current
    DESCRIPTION
        "IP Office application event states.  The associated event
        severity of the notification/trap the object is carried in
        varies depending upon the event condition. The appropriate
        severity is detailed against event enumeration."
    ::= { ipoGTObjects 6 }

ipoGTEventHostAddress OBJECT-TYPE
    SYNTAX      IpAddress
    MAX-ACCESS  accessible-for-notify
    STATUS      current
    DESCRIPTION
        "Address of an IP Office Small Office Gateway Subtending Host."
    ::= { ipoGTObjects 7 }

ipoGTEventSOGMode OBJECT-TYPE
    SYNTAX      INTEGER {
                survivable(1), -- severity: Major
                subTending(2)  -- severity: Minor
    }
    MAX-ACCESS  accessible-for-notify
    STATUS      current
    DESCRIPTION
        "IP Office Small Office Gateway operating modes.  
        survivable(1) indicates the control unit has no current host, 
        either through confguration error or communication failure.  
        subTending(2) indicates normal operation to a valid Sub-
        tending Host."
    ::= { ipoGTObjects 8 }

ipoGTEventStdSeverity OBJECT-TYPE
    SYNTAX      ItuPerceivedSeverity
    MAX-ACCESS  accessible-for-notify
    STATUS      current
    DESCRIPTION
        "Severity of the event that has occurred.

        The event severity depends upon the type of
        entity/notification that the operational state change event
        relates to. The severity values that are normally used are
        detailed below:

        The enterprise versions of standard SNMP traps all have a
        severity of major (4).

        Operational events which notify the transition back to an
        operational state from a failure state have a severity of
        cleared (1).


        GenEntityEvents:
          Operational - severity is cleared (1)

          Failure event severity levels
            Type of physical   Severity for failure
            entity
            container          critical (3)
            module             major (4)
            port               major (4)

          Error
            Known transient errors for entities have a severity of
            warning (6).

          Change - severity is major (4)

        LKSCommsSvcEvents:
          Operational - severity is cleared (1)
          Failure -     severity is major (4)

        GenLoopbackSvcEvent:
          Severity is major (4)

        GenAppSvcEvents:
          Severity depends on sub-event
          Operational - severity is cleared (1)
          Failure -     severity is major (4)
          Event -       severity depends on event condition
            For voicemail storage conditions the severity is as
            follows:
              storageOkay       - severity is cleared (1)
              storageNearlyFull - severity is warning (6)
                (Only warning severity as it could be transitory.)
              storageFull       - severity is critical (3)

        GenSogSvcEvents:
          Severity depends on sub-event
          HostFailure         - severity is Major (4)
          ModeChange:
            - Mode survivable: severity is Major (4)
            - Mode subTending: severity is Minor (5)

        GenUPriLicSvcEvents:
          Severity depends on sub-event
          ChansReduced        - severity is Major (4)
          CallRejected        - severity is Minor (5)

        PhoneChangeSvcEvents:
          Severity is minor (5)"
    ::= { ipoGTObjects 9 }

ipoGTEventDevID OBJECT-TYPE
    SYNTAX      SnmpAdminString (SIZE (10))
    MAX-ACCESS  accessible-for-notify
    STATUS      current
    DESCRIPTION
        "A unique textual identifier of the alarming device."
    ::= { ipoGTObjects 10 }

ipoGTEventEntityName OBJECT-TYPE
    SYNTAX      SnmpAdminString (SIZE (0..64))
    MAX-ACCESS  accessible-for-notify
    STATUS      current
    DESCRIPTION
        "The textual name of the alarming physical entity. The
        contents of this object is made of concatenated
        entPhysicalName values that fully identify the object with the
        overall IP Office entity. Examples values are:

        Controller, Trunk Slot B, Trunk Module, T1 PRI 2
          = T1 PRI Port 2, on a dual T1 Trunk Module, in Trunk Slot B,
            on the IP Office Controller Unit

        Controller, VCM Slot 1, VCM 1
          = VCM Card, in VCM Slot 1, on the IP Office Controller Unit

        Controller, EXP 1, DS EXP 16, DS 12
          = DS Phone Port 12, on a DS16 Expansion Module, attached to
          Expansion Port 1, on the IP Office Controller Unit"
    ::= { ipoGTObjects 11 }

ipoGTEventLoopbackStatusBits OBJECT-TYPE
    SYNTAX      BITS {
        noLoopback(0),
        nearEndPayloadLoopback(1),
        nearEndLineLoopback(2),
        nearEndOtherLoopback(3),
        nearEndInwardLoopback(4),
        farEndPayloadLoopback(5),
        farEndLineLoopback(6)
    }
    MAX-ACCESS  accessible-for-notify
    STATUS      current
    DESCRIPTION
        "This variable represents the current state of the loopback on
         the DS1 interface.  It contains information about loopbacks
         established by a manager and remotely from the far end.

         The ipoGTEventLoopbackStatus is a bit map therefore is can
         represent multiple loopbacks simultaneously."
    ::= { ipoGTObjects 12 }

--
-- traps
--

ipoGenEntityFailureEvent NOTIFICATION-TYPE
    OBJECTS {
	ipoGTEventSeverity,
	ipoGTEventDateTime,
	ipoGTEventEntity
    }
    STATUS deprecated
    DESCRIPTION
	"A ipoGenEntityFailureEvent notification is generated whenever a
	physical entity on the IP Office fails in its operation. It
	signifies that the SNMP entity, acting in an agent role, has
	detected that the state of a physical entity of the system has
	transitioned from the operational to the failed state

        **NOTE: This notification is deprecated and replaced by ipoGenEntityFailureSvcEvent"
    ::= { ipoGTEvents 1 }

ipoGenEntityOperationalEvent NOTIFICATION-TYPE
    OBJECTS {
	ipoGTEventSeverity,
	ipoGTEventDateTime,
	ipoGTEventEntity
    }
    STATUS deprecated
    DESCRIPTION
	"A ipoGenEntityOperationalEvent notification is generated whenever
	a physical entity on the IP Office becomes operational again
	after having failed. It signifies that the SNMP entity, acting
	in an agent role, has detected that the state of a physical
	entity of the system has transitioned from the failed to the
	operational state

        **NOTE: This notification is deprecated and replaced by
          ipoGenEntityOperationalSvcEvent."
    ::= { ipoGTEvents 2 }

ipoGenEntityErrorEvent NOTIFICATION-TYPE
    OBJECTS {
	ipoGTEventSeverity,
	ipoGTEventDateTime,
	ipoGTEventEntity
    }
    STATUS deprecated
    DESCRIPTION
	"A ipoGenEntityErrorEvent notification is generated whenever a
	physical entity on the IP Office experiences a temporary
	error. It signifies that the SNMP entity, acting in an agent
	role, has detected a transitory error on a physical entity of
	the system.

        **NOTE: This notification is deprecated and replaced by
          ipoGenEntityErrorSvcEvent."
    ::= { ipoGTEvents 3 }

ipoGenEntityChangeEvent NOTIFICATION-TYPE
    OBJECTS {
	ipoGTEventSeverity,
	ipoGTEventDateTime,
	ipoGTEventEntity
    }
    STATUS deprecated
    DESCRIPTION
	"A ipoGenEntityChangeEvent notification is generated whenever
	a physical entity on the IP Office experiences a change itself
	or with other entities associated with it. It signifies that
	the SNMP entity, acting in an agent role, has detected a non
	error/failure change for a physical entity on the system.

        **NOTE: This notification is deprecated and replaced by
          ipoGenEntityChangeSvcEvent."
   ::= { ipoGTEvents 4 }

ipoGenLKSCommsFailureEvent NOTIFICATION-TYPE
    OBJECTS {
	ipoGTEventSeverity,
	ipoGTEventDateTime
    }
    STATUS deprecated
    DESCRIPTION
	"A ipoGenLKSCommsFailureEvent notification is generated
	whenever communication with a Licence Key Server fails.  It
	signifies that the SNMP entity, acting in an agent role, has
	detected that the state of the communications between the
	Licence Key Server has transitioned from the operational to
	the failed state.

        **NOTE: This notification is deprecated and replaced by
          ipoGenLKSCommsFailureSvcEvent."
    ::= { ipoGTEvents 5 }

ipoGenLKSCommsOperationalEvent NOTIFICATION-TYPE
    OBJECTS {
	ipoGTEventSeverity,
	ipoGTEventDateTime
    }
    STATUS deprecated
    DESCRIPTION
	"A ipoGenLKSCommsOperationalEvent notification is generated
	whenever communication with a Licence Key Server becomes
	operational again after having failed.  It signifies that the
	SNMP entity, acting in an agent role, has detected that the
	state of the communications between the Licence Key Server has
	transitioned from the failed to the operational state.

        **NOTE: This notification is deprecated and replaced by
          ipoGenLKSCommsOperationalSvcEvent."
    ::= { ipoGTEvents 6 }

ipoGenLKSCommsErrorEvent NOTIFICATION-TYPE
    OBJECTS {
	ipoGTEventSeverity,
	ipoGTEventDateTime
    }
    STATUS deprecated
    DESCRIPTION
	"A ipoGenLKSCommsErrorEvent notification is generated whenever
	 a IP Office experiences a temporary error with License Key
	 Server communication. It signifies that the SNMP entity,
	 acting in an agent role, has detected a transitory error with
	 the communication between the License Key Server and Client
	 on the system.

        **NOTE: This notification is deprecated and replaced by
          ipoGenLKSCommsErrorSvcEvent."
    ::= { ipoGTEvents 7 }

ipoGenLKSCommsChangeEvent NOTIFICATION-TYPE
    OBJECTS {
	ipoGTEventSeverity,
	ipoGTEventDateTime
    }
    STATUS deprecated
    DESCRIPTION
	"A ipoGenLKSCommsChangeEvent notification is generated
	whenever a IP Office experiences a change a non error change
	License Key Server communication operation.  It signifies that
	the SNMP entity, acting in an agent role, has detected a non
	error/failure change with the License Key Server and Client
	operation on the system.

        **NOTE: This notification is deprecated and replaced by
          ipoGenLKSCommsChangeSvcEvent."
   ::= { ipoGTEvents 8 }

ipoGenLoopbackEvent NOTIFICATION-TYPE
    OBJECTS {
	ipoGTEventSeverity,
	ipoGTEventDateTime,
	ipoGTEventEntity,
	ipoGTEventLoopbackStatus
    }
    STATUS deprecated
    DESCRIPTION
	"A ipoGenLoopbackEvent notification is generated whenever a IP
	Office T1 (DS1) interface operating as a CSU actions a loopback
	status change.

        **NOTE: This notification is deprecated and replaced by
          ipoGenLoopbackSvcEvent."
   ::= { ipoGTEvents 9 }

ipoGenAppFailureEvent NOTIFICATION-TYPE
    OBJECTS {
	ipoGTEventSeverity,
	ipoGTEventDateTime,
	ipoGTEventAppEntity
    }
    STATUS deprecated
    DESCRIPTION
	"A ipoGenAppFailureEvent notification is generated whenever
	communication between a IP Office switch and a IP Office
	application fails.  It signifies that the SNMP entity, acting
	in an agent role, has detected that the state of the
	communications between the IP Office switch and a IP Office
	application has transitioned from the operational to the
	failed state.  The IP Office application between which
	communication has been lost is identified by the value of
	ipoGTEventAppEntity.

        **NOTE: This notification is deprecated and replaced by
          ipoGenAppFailureSvcEvent."
    ::= { ipoGTEvents 10 }

ipoGenAppOperationalEvent NOTIFICATION-TYPE
    OBJECTS {
	ipoGTEventSeverity,
	ipoGTEventDateTime,
	ipoGTEventAppEntity
    }
    STATUS deprecated
    DESCRIPTION
	"A ipoGenAppOperationalEvent notification is generated
	whenever communication between a IP Office switch and a IP
	Office application becomes operational again after having
	failed.  It signifies that the SNMP entity, acting in an agent
	role, has detected that the state of the communications
	between the IP Office switch and a IP Office application has
	transitioned from the failed to the operational state.  The IP
	Office application between which communication has been lost
	is identified by the value of ipoGTEventAppEntity.

        **NOTE: This notification is deprecated and replaced by
          ipoGenAppOperationalSvcEvent."
    ::= { ipoGTEvents 11 }

ipoGenAppEvent NOTIFICATION-TYPE
    OBJECTS {
	ipoGTEventSeverity,
	ipoGTEventDateTime,
	ipoGTEventAppEntity,
	ipoGTEventAppEvent
    }
    STATUS deprecated
    DESCRIPTION
	"A ipoGenAppEvent notification is generated whenever a
	application entity of the IP Office system experiences an event.
        It signifies that the SNMP entity, acting as a proxy for
        the application, has detected an event on the application
        entity of the overall IP Office system.
        The event severity varies dependent upon the event condition.

        **NOTE: This notification is deprecated and replaced by
          ipoGenAppSvcEvent."
    ::= { ipoGTEvents 12 }

ipoGenSogHostFailureEvent NOTIFICATION-TYPE
    OBJECTS {
        ipoGTEventSeverity,
        ipoGTEventDateTime,
        ipoGTEventHostAddress
    }
    STATUS deprecated
    DESCRIPTION
        "An ipoGenSogFailureEvent notification is generated whenever a
        previously valid Sub-tending host fails during Small Office 
        Gateway operation.
        The ipAddress field indicates the address of the failed host.
        The event severity will always indicate Major.

        **NOTE: This notification is deprecated and replaced by
          ipoGenSogHostFailureSvcEvent."
    ::= { ipoGTEvents 13 }

ipoGenSogModeChangeEvent NOTIFICATION-TYPE
    OBJECTS {
        ipoGTEventSeverity,
        ipoGTEventDateTime,
        ipoGTEventSOGMode
    }
    STATUS deprecated
    DESCRIPTION
        "An ipoGenSogModeChangeEvent notification is generated whenever 
        the Small Office Gateway operating mode changes. This also
        includes entry to the initial mode.
        The ipoGTEventSOGMode field indicates the new operating mode.
        The event severity will be major(2) for a ipoGTEventSOGMode value
        of survivable(1), and minor(3) for a ipoGTEventSOGMode value of
        subTending(2).

        **NOTE: This notification is deprecated and replaced by
          ipoGenSogModeChangeSvcEvent."
    ::= { ipoGTEvents 14 }

ipoGenColdStartSvcEvent NOTIFICATION-TYPE
    OBJECTS {
	ipoGTEventStdSeverity,
	ipoGTEventDateTime,
	ipoGTEventDevID,
	sysDescr
    }
    STATUS current
    DESCRIPTION
        "Enterprise version of standard coldstart trap featuring
         device identification information.  A coldStart trap
         signifies that the sending protocol entity is reinitializing
         itself such that the agent's configuration or the protocol
         entity implementation may be altered."
    ::= { ipoGTEvents 15 }

ipoGenWarmStartSvcEvent NOTIFICATION-TYPE
    OBJECTS {
	ipoGTEventStdSeverity,
	ipoGTEventDateTime,
	ipoGTEventDevID,
	sysDescr
    }
    STATUS current
    DESCRIPTION
        "Enterprise version of standard warmstart trap featuring
         device identification information.  A warmStart trap
         signifies that the sending protocol entity is reinitializing
         that neither the agent configuration nor the protocol entity
         implementation is altered."
    ::= { ipoGTEvents 16 }

ipoGenLinkDownSvcEvent NOTIFICATION-TYPE
    OBJECTS {
	ipoGTEventStdSeverity,
	ipoGTEventDateTime,
	ipoGTEventDevID,
	sysDescr,
        ifIndex
    }
    STATUS current
    DESCRIPTION
        "Enterprise version of standard linkDown trap featuring device
         identification information.  A linkDown trap signifies that
         the sending protocol entity recognizes a failure in one of
         the communication links represented in the agent's
         configuration."
    ::= { ipoGTEvents 17 }

ipoGenLinkUpSvcEvent NOTIFICATION-TYPE
    OBJECTS {
	ipoGTEventStdSeverity,
	ipoGTEventDateTime,
	ipoGTEventDevID,
	sysDescr,
        ifIndex
    }
    STATUS current
    DESCRIPTION
        "Enterprise version of standard linkUp trap featuring device
         identification information.  A linkUp trap signifies that the
         sending protocol entity recognizes that one of the
         communication links represented in the agent's configuration
         has come up."
    ::= { ipoGTEvents 18 }

ipoGenAuthFailureSvcEvent NOTIFICATION-TYPE
    OBJECTS {
	ipoGTEventStdSeverity,
	ipoGTEventDateTime,
	ipoGTEventDevID,
	sysDescr
    }
    STATUS current
    DESCRIPTION
        "Enterprise version of standard authenticationFailure trap
         featuring device identification information.  An
         authenticationFailure trap signifies that the sending
         protocol entity is the addressee of a protocol message that
         is not properly authenticated.  While implementations of the
         SNMP must be capable of generating this trap, they must also
         be capable of suppressing the emission of such traps via an
         implementation- specific mechanism."
    ::= { ipoGTEvents 19 }

ipoGenEntityFailureSvcEvent NOTIFICATION-TYPE
    OBJECTS {
	ipoGTEventStdSeverity,
	ipoGTEventDateTime,
	ipoGTEventDevID,
	sysDescr,
	ipoGTEventEntity,
	ipoGTEventEntityName
    }
    STATUS current
    DESCRIPTION
	"A ipoGenEntityFailureSvcEvent notification is generated
	whenever a physical entity on the IP Office fails in its
	operation. It signifies that the SNMP entity, acting in an
	agent role, has detected that the state of a physical entity
	of the system has transitioned from the operational to the
	failed state"
    ::= { ipoGTEvents 20 }

ipoGenEntityOperationalSvcEvent NOTIFICATION-TYPE
    OBJECTS {
	ipoGTEventStdSeverity,
	ipoGTEventDateTime,
	ipoGTEventDevID,
	sysDescr,
	ipoGTEventEntity,
	ipoGTEventEntityName
    }
    STATUS current
    DESCRIPTION
	"A ipoGenEntityOperationalSvcEvent notification is generated
	whenever a physical entity on the IP Office becomes
	operational again after having failed. It signifies that the
	SNMP entity, acting in an agent role, has detected that the
	state of a physical entity of the system has transitioned from
	the failed to the operational state"
    ::= { ipoGTEvents 21 }

ipoGenEntityErrorSvcEvent NOTIFICATION-TYPE
    OBJECTS {
	ipoGTEventStdSeverity,
	ipoGTEventDateTime,
	ipoGTEventDevID,
	sysDescr,
	ipoGTEventEntity,
	ipoGTEventEntityName
    }
    STATUS current
    DESCRIPTION
	"A ipoGenEntityErrorSvcEvent notification is generated
	whenever a physical entity on the IP Office experiences a
	temporary error. It signifies that the SNMP entity, acting in
	an agent role, has detected a transitory error on a physical
	entity of the system."
    ::= { ipoGTEvents 22 }

ipoGenEntityChangeSvcEvent NOTIFICATION-TYPE
    OBJECTS {
	ipoGTEventStdSeverity,
	ipoGTEventDateTime,
	ipoGTEventDevID,
	sysDescr,
	ipoGTEventEntity,
	ipoGTEventEntityName
    }
    STATUS current
    DESCRIPTION
	"A ipoGenEntityChangeSvcEvent notification is generated
	whenever a physical entity on the IP Office experiences a
	change itself or with other entities associated with it. It
	signifies that the SNMP entity, acting in an agent role, has
	detected a non error/failure change for a physical entity on
	the system."
    ::= { ipoGTEvents 23 }

ipoGenLKSCommsFailureSvcEvent NOTIFICATION-TYPE
    OBJECTS {
	ipoGTEventStdSeverity,
	ipoGTEventDateTime,
	ipoGTEventDevID,
	sysDescr
    }
    STATUS current
    DESCRIPTION
	"A ipoGenLKSCommsFailureSvcEvent notification is generated
	whenever communication with a Licence Key Server fails.  It
	signifies that the SNMP entity, acting in an agent role, has
	detected that the state of the communications between the
	Licence Key Server has transitioned from the operational to
	the failed state."
    ::= { ipoGTEvents 24 }

ipoGenLKSCommsOperationalSvcEvent NOTIFICATION-TYPE
    OBJECTS {
	ipoGTEventStdSeverity,
	ipoGTEventDateTime,
	ipoGTEventDevID,
	sysDescr
    }
    STATUS current
    DESCRIPTION
	"A ipoGenLKSCommsOperationalSvcEvent notification is generated
	whenever communication with a Licence Key Server becomes
	operational again after having failed.  It signifies that the
	SNMP entity, acting in an agent role, has detected that the
	state of the communications between the Licence Key Server has
	transitioned from the failed to the operational state."
    ::= { ipoGTEvents 25 }

ipoGenLKSCommsErrorSvcEvent NOTIFICATION-TYPE
    OBJECTS {
	ipoGTEventStdSeverity,
	ipoGTEventDateTime,
	ipoGTEventDevID,
	sysDescr
    }
    STATUS current
    DESCRIPTION
	"A ipoGenLKSCommsErrorSvcEvent notification is generated
	 whenever a IP Office experiences a temporary error with
	 License Key Server communication. It signifies that the SNMP
	 entity, acting in an agent role, has detected a transitory
	 error with the communication between the License Key Server
	 and Client on the system."
    ::= { ipoGTEvents 26 }

ipoGenLKSCommsChangeSvcEvent NOTIFICATION-TYPE
    OBJECTS {
	ipoGTEventStdSeverity,
	ipoGTEventDateTime,
	ipoGTEventDevID,
	sysDescr
    }
    STATUS current
    DESCRIPTION
	"A ipoGenLKSCommsChangeSvcEvent notification is generated
	whenever a IP Office experiences a change a non error change
	License Key Server communication operation.  It signifies that
	the SNMP entity, acting in an agent role, has detected a non
	error/failure change with the License Key Server and Client
	operation on the system."
    ::= { ipoGTEvents 27 }

ipoGenLoopbackSvcEvent NOTIFICATION-TYPE
    OBJECTS {
	ipoGTEventStdSeverity,
	ipoGTEventDateTime,
	ipoGTEventDevID,
	sysDescr,
	ipoGTEventEntity,
	ipoGTEventEntityName,
	ipoGTEventLoopbackStatusBits
    }
    STATUS current
    DESCRIPTION
	"A ipoGenLoopbackSvcEvent notification is generated whenever a
	IP Office T1 (DS1) interface operating as a CSU actions a
	loopback status change."
   ::= { ipoGTEvents 28 }

ipoGenAppFailureSvcEvent NOTIFICATION-TYPE
    OBJECTS {
	ipoGTEventStdSeverity,
	ipoGTEventDateTime,
	ipoGTEventDevID,
	sysDescr,
	ipoGTEventAppEntity
    }
    STATUS current
    DESCRIPTION
	"A ipoGenAppFailureSvcEvent notification is generated whenever
	communication between a IP Office switch and a IP Office
	application fails.  It signifies that the SNMP entity, acting
	in an agent role, has detected that the state of the
	communications between the IP Office switch and a IP Office
	application has transitioned from the operational to the
	failed state.  The IP Office application between which
	communication has been lost is identified by the value of
	ipoGTEventAppEntity."
    ::= { ipoGTEvents 29 }

ipoGenAppOperationalSvcEvent NOTIFICATION-TYPE
    OBJECTS {
	ipoGTEventStdSeverity,
	ipoGTEventDateTime,
	ipoGTEventDevID,
	sysDescr,
	ipoGTEventAppEntity
    }
    STATUS current
    DESCRIPTION
	"A ipoGenAppOperationalSvcEvent notification is generated
	whenever communication between a IP Office switch and a IP
	Office application becomes operational again after having
	failed.  It signifies that the SNMP entity, acting in an agent
	role, has detected that the state of the communications
	between the IP Office switch and a IP Office application has
	transitioned from the failed to the operational state.  The IP
	Office application between which communication has been lost
	is identified by the value of ipoGTEventAppEntity."
    ::= { ipoGTEvents 30 }

ipoGenAppSvcEvent NOTIFICATION-TYPE
    OBJECTS {
	ipoGTEventStdSeverity,
	ipoGTEventDateTime,
	ipoGTEventDevID,
	sysDescr,
	ipoGTEventAppEntity,
	ipoGTEventAppEvent
    }
    STATUS current
    DESCRIPTION
	"A ipoGenAppSvcEvent notification is generated whenever a
	application entity of the IP Office system experiences an
	event.  It signifies that the SNMP entity, acting as a proxy
	for the application, has detected an event on the application
	entity of the overall IP Office system.

        The event severity varies dependent upon the event condition."
    ::= { ipoGTEvents 31 }

ipoGenSogHostFailureSvcEvent NOTIFICATION-TYPE
    OBJECTS {
	ipoGTEventStdSeverity,
	ipoGTEventDateTime,
	ipoGTEventDevID,
	sysDescr,
        ipoGTEventHostAddress
    }
    STATUS current
    DESCRIPTION
        "An ipoGenSogFailureSvcEvent notification is generated
        whenever a previously valid Sub-tending host fails during
        Small Office Gateway operation.

        The ipAddress field indicates the address of the failed host.
        The event severity will always indicate major(4)."
    ::= { ipoGTEvents 32 }

ipoGenSogModeChangeSvcEvent NOTIFICATION-TYPE
    OBJECTS {
	ipoGTEventStdSeverity,
	ipoGTEventDateTime,
	ipoGTEventDevID,
	sysDescr,
        ipoGTEventSOGMode
    }
    STATUS current
    DESCRIPTION
        "An ipoGenSogModeChangeSvcEvent notification is generated
        whenever the Small Office Gateway operating mode changes. This
        also includes entry to the initial mode.

        The ipoGTEventSOGMode field indicates the new operating mode.
        The event severity will be major(4) for a ipoGTEventSOGMode
        value of survivable(1), and minor(5) for a ipoGTEventSOGMode
        value of subTending(2)."
    ::= { ipoGTEvents 33 }

ipoGenUPriLicChansReducedSvcEvent NOTIFICATION-TYPE
    OBJECTS {
	ipoGTEventStdSeverity,
	ipoGTEventDateTime,
	ipoGTEventDevID,
	sysDescr
    }
    STATUS current
    DESCRIPTION
	"A ipoGenUPriLicChansReducedSvcEvent notification is generated
	whenever the number of Universal PRI Licensed channels has
	been reduced. It signifies that the SNMP entity, acting in an
	agent role, has detected a reduction in the licensed channels
	on a Univeral PRI trunk."
    ::= { ipoGTEvents 34 }

ipoGenUPriLicCallRejectedSvcEvent NOTIFICATION-TYPE
    OBJECTS {
	ipoGTEventStdSeverity,
	ipoGTEventDateTime,
	ipoGTEventDevID,
	sysDescr
    }
    STATUS current
    DESCRIPTION
	"A ipoGenUPriLicCallRejectedSvcEvent notification is generated
	whenever a call on a Universal PRI is rejected due to a
	licensed channel not being available.  It signifies that the
	SNMP entity, acting in an agent role, has detected a licensed
	channel not available in order to make a call on a Univeral
	PRI trunk."
    ::= { ipoGTEvents 35 }


--********************************************************************
-- IP Office wide compliance
--********************************************************************

ipoGenCompliances OBJECT IDENTIFIER ::= { ipoGenConformance 1 }
ipoGenGroups      OBJECT IDENTIFIER ::= { ipoGenConformance 2 }

--
-- compliance statements
--

ipoGenCompliance MODULE-COMPLIANCE
    STATUS deprecated
    DESCRIPTION
	"The compliance statement for IP Office agents which implement
         up to and including version 1.00.05 of this MIB."
    MODULE -- this module
    MANDATORY-GROUPS {
        ipoGenNotificationObjectsGroup,
        ipoGenNotificationsGroup
    }
    ::= { ipoGenCompliances 1 }

ipoGen2Compliance MODULE-COMPLIANCE
    STATUS deprecated
    DESCRIPTION
	"The compliance statement for IP Office agents which implement
         version 1.00.06 and later versions of this MIB."
    MODULE -- this module
    MANDATORY-GROUPS {
        ipoGenNotificationObjectsGroup,
        ipoGenNotificationsGroup
    }
    GROUP ipoGenSOGNotificationObjectsGroup
    DESCRIPTION
        "Implementation of this group is only mandatory for IP Office
         SOG devices."
        GROUP ipoGenSOGNotificationsGroup
    DESCRIPTION
        "Implementation of this group is only mandatory for IP Office
         SOG devices."
    ::= { ipoGenCompliances 2 }

ipoGen3Compliance MODULE-COMPLIANCE
    STATUS deprecated
    DESCRIPTION
	"The compliance statement for IP Office agents which implement
         version 1.01.01 and later versions of this MIB."
    MODULE -- this module
    MANDATORY-GROUPS {
        ipoGenv2NotificationObjectsGroup,
        ipoGenEntGenNotificationsGroup,
        ipoGenSvcNotificationsGroup
    }
    GROUP ipoGenSOGNotificationObjectsGroup
    DESCRIPTION
        "Implementation of this group is only mandatory for IP Office
         SOG devices."
    GROUP ipoGenSvcSOGNotificationsGroup
    DESCRIPTION
        "Implementation of this group is only mandatory for IP Office
         SOG devices."
    ::= { ipoGenCompliances 3 }

ipoGen4Compliance MODULE-COMPLIANCE
    STATUS current
    DESCRIPTION
	"The compliance statement for IP Office agents which implement
         version 2.01.01 and later versions of this MIB."
    MODULE -- this module
    MANDATORY-GROUPS {
        ipoGenv2NotificationObjectsGroup,
        ipoGenEntGenNotificationsGroup,
        ipoGenSvcNotificationsGroup
    }
    GROUP ipoGenSOGNotificationObjectsGroup
    DESCRIPTION
        "Implementation of this group is only mandatory for IP Office
         SOG devices."
    GROUP ipoGenSvcSOGNotificationsGroup
    DESCRIPTION
        "Implementation of this group is only mandatory for IP Office
         SOG devices."
    GROUP ipoGenUPriLicSvcNotificationsGroup
    DESCRIPTION
        "Implementation of this group is only mandatory for IP Office
         systems that support the Universal PRI trunk module such as
         the IP500."
    ::= { ipoGenCompliances 4 }

--
-- MIB groupings
--

ipoGenNotificationObjectsGroup OBJECT-GROUP
    OBJECTS {
        ipoGTEventSeverity,
        ipoGTEventDateTime,
        ipoGTEventEntity,
        ipoGTEventLoopbackStatus,
        ipoGTEventAppEntity,
        ipoGTEventAppEvent
    }
    STATUS deprecated
    DESCRIPTION
        "Objects that are contained in IP Office wide notifications.

        **NOTE: This group is deprecated and replaced by
          ipoGenv2NotificationObjectsGroup."
    ::= { ipoGenGroups 1 }

ipoGenNotificationsGroup NOTIFICATION-GROUP
    NOTIFICATIONS {
        ipoGenEntityFailureEvent,
        ipoGenEntityOperationalEvent,
        ipoGenEntityErrorEvent,
        ipoGenEntityChangeEvent,
        ipoGenLKSCommsFailureEvent,
        ipoGenLKSCommsOperationalEvent,
        ipoGenLKSCommsErrorEvent,
        ipoGenLKSCommsChangeEvent,
        ipoGenLoopbackEvent,
        ipoGenAppOperationalEvent,
        ipoGenAppFailureEvent,
        ipoGenAppEvent
   }
    STATUS deprecated
    DESCRIPTION
        "The notifications which indicate specific changes in the
        state of the IP Office system.

        **NOTE: This group is deprecated and replaced by
          ipoGenSvcNotificationsGroup."
    ::= { ipoGenGroups 2 }

ipoGenSOGNotificationObjectsGroup OBJECT-GROUP
    OBJECTS {
        ipoGTEventHostAddress,
        ipoGTEventSOGMode
    }
    STATUS current
    DESCRIPTION
        "Objects that are contained in IP Office SOG notifications."
    ::= { ipoGenGroups 3 }

ipoGenSOGNotificationsGroup NOTIFICATION-GROUP
    NOTIFICATIONS {
        ipoGenSogHostFailureEvent,
        ipoGenSogModeChangeEvent
    }
    STATUS deprecated
    DESCRIPTION
        "The notifications which indicate specific changes in the
        state of the IP Office SOG system.

        **NOTE: This group is deprecated and replaced by
          ipoGenSvcNotificationsGroup."
    ::= { ipoGenGroups 4 }

ipoGenv2NotificationObjectsGroup OBJECT-GROUP
    OBJECTS {
        ipoGTEventDateTime,
        ipoGTEventEntity,
        ipoGTEventAppEntity,
        ipoGTEventAppEvent,
        ipoGTEventStdSeverity,
        ipoGTEventDevID,
        ipoGTEventEntityName,
        ipoGTEventLoopbackStatusBits
    }
    STATUS current
    DESCRIPTION
        "Objects that are contained in IP Office wide notifications."
    ::= { ipoGenGroups 5 }

ipoGenEntGenNotificationsGroup NOTIFICATION-GROUP
    NOTIFICATIONS {
        ipoGenColdStartSvcEvent,
        ipoGenWarmStartSvcEvent,
        ipoGenLinkDownSvcEvent,
        ipoGenLinkUpSvcEvent,
        ipoGenAuthFailureSvcEvent
   }
    STATUS current
    DESCRIPTION
        "IP Office Enterpise versions of the generic traps as defined
        RFC1215 that provide more identification of the entity
        concerned."
    ::= { ipoGenGroups 6 }

ipoGenSvcNotificationsGroup NOTIFICATION-GROUP
    NOTIFICATIONS {
        ipoGenEntityFailureSvcEvent,
        ipoGenEntityOperationalSvcEvent,
        ipoGenEntityErrorSvcEvent,
        ipoGenEntityChangeSvcEvent,
        ipoGenLKSCommsFailureSvcEvent,
        ipoGenLKSCommsOperationalSvcEvent,
        ipoGenLKSCommsErrorSvcEvent,
        ipoGenLKSCommsChangeSvcEvent,
        ipoGenLoopbackSvcEvent,
        ipoGenAppOperationalSvcEvent,
        ipoGenAppFailureSvcEvent,
        ipoGenAppSvcEvent
   }
    STATUS current
    DESCRIPTION
        "The service notifications which indicate specific changes in
        the state of the IP Office system."
    ::= { ipoGenGroups 7 }

ipoGenSvcSOGNotificationsGroup NOTIFICATION-GROUP
    NOTIFICATIONS {
        ipoGenSogHostFailureSvcEvent,
        ipoGenSogModeChangeSvcEvent
    }
    STATUS current
    DESCRIPTION
        "The service notifications which indicate specific changes in
        the state of the IP Office SOG system."
    ::= { ipoGenGroups 8 }

ipoGenUPriLicSvcNotificationsGroup NOTIFICATION-GROUP
    NOTIFICATIONS {
        ipoGenUPriLicChansReducedSvcEvent,
        ipoGenUPriLicCallRejectedSvcEvent
    }
    STATUS current
    DESCRIPTION
        "The service notifications which indicate specific changes
        related to the state licensing and Universal PRI trunks on the
        IP Office system."
    ::= { ipoGenGroups 9 }

END
