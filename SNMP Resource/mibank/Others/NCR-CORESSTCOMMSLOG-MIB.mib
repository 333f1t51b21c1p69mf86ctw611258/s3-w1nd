NCR-CORESSTCOMMSLOG-MIB DEFINITIONS ::= BEGIN

--
-- NCR Core SST Comms Log MIB
--

IMPORTS
    enterprises, Counter
        FROM RFC1155-SMI
    OBJECT-TYPE
        FROM RFC-1212
    DisplayString
        FROM RFC1213-MIB
    TruthValue
    FROM RFC1253-MIB;
        
        ncr                     OBJECT IDENTIFIER ::= { enterprises 191 }
        sst                     OBJECT IDENTIFIER ::= { ncr 39 }
        sstCore                 OBJECT IDENTIFIER ::= { sst 1 }
        sstProduct              OBJECT IDENTIFIER ::= { sst 13 }
        sstObjs                 OBJECT IDENTIFIER ::= { sstProduct 2}
        sstGeneral              OBJECT IDENTIFIER ::= { sstObjs 1 }    
        sstDevice               OBJECT IDENTIFIER ::= { sstObjs 2 }
        sstApplic               OBJECT IDENTIFIER ::= { sstObjs 3 }
        sstLogs                 OBJECT IDENTIFIER ::= { sstObjs 4 }

-----------------------------------------------------------
-- Comms Log Table
-----------------------------------------------------------

sstCommsLogTable OBJECT-TYPE
    SYNTAX  SEQUENCE OF SstLogEntry
    ACCESS  not-accessible
    STATUS  mandatory
    DESCRIPTION                        
    "This group defines the attributes of event entries in the 
    SST comms log."
    ::= { sstLogs 8 }

sstLogEntry OBJECT-TYPE
    SYNTAX  SstLogEntry
    ACCESS  not-accessible
    STATUS  mandatory
    DESCRIPTION
    "This defines the contents of the table."
    INDEX   { sstLogIndex }
    ::= { sstCommsLogTable 1 }

SstLogEntry ::=
    SEQUENCE { 
           sstLogIndex           INTEGER,
           sstLogDeviceName      DisplayString,
           sstLogServiceName     DisplayString,
           sstLogTCode           OCTET STRING,
           sstLogSData           OCTET STRING,
           sstLogMData           OCTET STRING,
           sstLogDescription     OCTET STRING
         }

sstLogIndex OBJECT-TYPE
    SYNTAX INTEGER
    ACCESS read-only
    STATUS mandatory    
    DESCRIPTION 
    "A unique number for every entry in the comms log."
    ::= { sstLogEntry 1 }

sstLogDeviceName OBJECT-TYPE
    SYNTAX DisplayString
    ACCESS read-only
    STATUS mandatory    
    DESCRIPTION 
    "The name of the device that generated the event."
    ::= { sstLogEntry 2 }

sstLogServiceName OBJECT-TYPE
    SYNTAX DisplayString
    ACCESS read-only
    STATUS mandatory    
    DESCRIPTION 
    "The name of the service associated with the device."
    ::= { sstLogEntry 3 }

sstLogTCode OBJECT-TYPE
    SYNTAX OCTET STRING
    ACCESS read-only
    STATUS mandatory    
    DESCRIPTION 
    "The transaction code reported from the device."
    ::= { sstLogEntry 4 }

sstLogSData OBJECT-TYPE
    SYNTAX OCTET STRING
    ACCESS read-only
    STATUS mandatory    
    DESCRIPTION 
    "The severity information reported from the device."
    ::= { sstLogEntry 5 }

sstLogMData OBJECT-TYPE
    SYNTAX OCTET STRING
    ACCESS read-only
    STATUS mandatory    
    DESCRIPTION 
    "The maintenance information reported from the device."
    ::= { sstLogEntry 6 }

sstLogDescription OBJECT-TYPE
    SYNTAX OCTET STRING
    ACCESS read-only
    STATUS mandatory    
    DESCRIPTION 
    "Additional information about the event."
    ::= { sstLogEntry 7 }

END
