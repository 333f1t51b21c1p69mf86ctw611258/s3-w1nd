-- *****************************************************************
-- 
-- RDN-SENSOR-MIB:
--             RiverDelta Definitions Object Identifier Assignments
--             (riverdelta.rdnSensor - 1.3.6.1.4.1.4981.5)
--
-- August 2001, Thor Kirleis (thor@riverdelta.com)
--
-- Copyright (c) 2001 RiverDelta Networks, all rights reserved.
-- 
-- *****************************************************************

RDN-SENSOR-MIB DEFINITIONS ::= BEGIN

    IMPORTS
        MODULE-IDENTITY, OBJECT-TYPE, NOTIFICATION-TYPE, Integer32
            FROM SNMPv2-SMI
        DisplayString
            FROM RFC1213-MIB
        riverdelta
            FROM RDN-MIB;

    --
    -- riverdelta sensor mib module
    --

    rdnSensor MODULE-IDENTITY
        LAST-UPDATED "0108070000Z" -- example "9501201225Z"
                                   -- Fri Jan 20 12:25:50 PST 1995
        ORGANIZATION "Motorola"
        CONTACT-INFO "Motorola
                      3 Highwood Drive
                      Tewksbury, MA 01867
                      Tel: +1 978 858 2000
                      Fax: +1 978 858 2399
                      E-mail:  BSRSNMP@maillist2001.mot.com

                      Tom Keske 
                      Motorola BCS
                      20 Cabot Blvd. MA07 M2-330
                      Mansfield, MA 02048
                      Tel: 1-508-851-8325
                      Fax: 1-508-851-8510
                      E-mail: Tom.Keske@motorola.com"
        DESCRIPTION
                "MIB module for Motorola hardware sensors."
        REVISION     "0108070000Z"
        DESCRIPTION
                "Initial creation."
        ::= { riverdelta 5 }


    rdnSensorTable OBJECT-TYPE
        SYNTAX  SEQUENCE OF RdnSensorEntry
        MAX-ACCESS  not-accessible
        STATUS  current
        DESCRIPTION
                 "Hardware Senor table."
        ::= { rdnSensor 1 }

    rdnSensorEntry OBJECT-TYPE
        SYNTAX RdnSensorEntry
        MAX-ACCESS  not-accessible
        STATUS  current
        DESCRIPTION
                 "Hardware Sensor table entry."
        INDEX { rdnSensorIndex }
       ::= { rdnSensorTable 1 }

    RdnSensorEntry ::=
        SEQUENCE {
            rdnSensorIndex
                Integer32,
            rdnSensorDescr
                DisplayString,
            rdnSensorObjectID
                OBJECT IDENTIFIER,
            rdnSensorValue
                Integer32,
            rdnSensorThresholdHigh
                Integer32,
            rdnSensorThresholdLow
                Integer32,
            rdnSensorStatus
                INTEGER,
            rdnSensorNotificationEnable
                INTEGER
        }

    --
    -- start of sensor table
    --

    rdnSensorIndex OBJECT-TYPE
        SYNTAX  Integer32
        MAX-ACCESS  read-only
        STATUS  current
        DESCRIPTION
                "An index uniquely identifying an entry
                in the rdnSensorTable."
        ::= { rdnSensorEntry 1 }

    rdnSensorDescr OBJECT-TYPE
        SYNTAX  DisplayString
        MAX-ACCESS  read-only
        STATUS  current
        DESCRIPTION
                "A text description of the sensor described
                by this table entry."
        ::= { rdnSensorEntry 2 }

    rdnSensorObjectID OBJECT-TYPE
        SYNTAX  OBJECT IDENTIFIER
        MAX-ACCESS  read-only
        STATUS  current
        DESCRIPTION
                "The object identifier (OID) describing the
                type of sensor described by this entry."
        ::= { rdnSensorEntry 3 }

    rdnSensorValue OBJECT-TYPE
        SYNTAX  Integer32
        MAX-ACCESS  read-only
        STATUS  current
        DESCRIPTION
                "The temperature value in degrees Celsius of
                the sensor described by this entry."
        ::= { rdnSensorEntry 4 }

    rdnSensorThresholdHigh OBJECT-TYPE
        SYNTAX  Integer32
        MAX-ACCESS  read-write
        STATUS  current
        DESCRIPTION
                "The high temperature threshold value of normal
                operating conditions described by this entry."
        ::= { rdnSensorEntry 5 }

    rdnSensorThresholdLow OBJECT-TYPE
        SYNTAX  Integer32
        MAX-ACCESS  read-write
        STATUS  current
        DESCRIPTION
                "The low temperature threshold value of normal
                operating conditions described by this entry."
        ::= { rdnSensorEntry 6 }

    rdnSensorStatus OBJECT-TYPE
        SYNTAX  INTEGER {
             unknown(1),
             ok(2),
             below-min(3),
             above-max(4),
             defective(5),
             not-present(6)
             }
        MAX-ACCESS  read-only
        STATUS  current
        DESCRIPTION
                "The operational status of the sensor described
                by this entry."
        ::= { rdnSensorEntry 7 }

    rdnSensorNotificationEnable OBJECT-TYPE
        SYNTAX  INTEGER { enabled(1), disabled(2) }
        MAX-ACCESS  read-write
        STATUS  current
        DESCRIPTION
                "The notification enable of the sensor
                described by this entry."
        ::= { rdnSensorEntry 8 }


    --
    -- sensor notifications
    --

    rdnSensorNotifications       OBJECT IDENTIFIER ::= { rdnSensor 2 }
    rdnSensorNotificationsPrefix OBJECT IDENTIFIER ::= { rdnSensorNotifications 0 }

    rdnSensorThresholdExceeded NOTIFICATION-TYPE
        OBJECTS {
             rdnSensorIndex,
		     rdnSensorDescr,
             rdnSensorObjectID,
             rdnSensorValue,
             rdnSensorThresholdHigh,
             rdnSensorThresholdLow,
             rdnSensorStatus
             }
        STATUS  current
        DESCRIPTION
                "The notification sent for the alarm condition
                triggered when the temperature of a sensor exceeds
                its low or high threshold level."
        ::= { rdnSensorNotificationsPrefix 1 }

END
