-- COPYRIGHT NOTICE
-- Copyright (c) Alteon WebSystems, Inc. 2002
-- All rights reserved
-- 
-- HISTORY
-- $Log: cheetahSwitch.mib $
-- Revision ge_latest_margozzi/1 2002/12/04 23:54:08 margozzi
-- 	Added Port and rmon Oper commands.
-- 
-- Revision submit_cheetah_1620/1 2002/12/04 21:56:40 rmundhra
-- Fixed CR Q00574195: EMS: Port Ena/Dis does not
-- seem to work.
-- Added SNMP support for /oper/port x commands.
-- 
-- Revision submit_cheetah_1544/1 2002/11/20 00:24:03 rrekha
-- Fixed Q00542489: Added mib object agClearFlashDump to clear the 
-- dump.
-- 
-- Revision submit_cheetah_1520/1 2002/11/16 00:20:24 rrekha
-- Added mib objects agMgmtCurCfgDns/agMgmtNewCfgDns.
-- 
-- Revision submit_cheetah_1368/1 2002/10/24 20:14:46 rrekha
-- Fixed Q00546514: Added missing SP maintenance statistics.
-- 
-- Revision submit_cheetah_1329/1 2002/10/22 02:14:49 rrekha
-- Added mib objects to get mgmt port info.
-- 
-- Revision submit_cheetah_1324/1 2002/10/21 23:23:01 rrekha
-- Fixed typo in pktStatsDiscards description.
-- 
-- Revision submit_cheetah_1286/1 2002/10/17 23:48:45 rrekha
-- Fixed Q00543161: Remove coldReset/warmReset from enum in agReset
-- as cheetah has only one reset.
-- 
-- Revision submit_cheetah_1248/1 2002/10/16 16:40:59 rmundhra
-- Fixed CR Q00536352 & CR Q00538316: EMS & WebUI
-- not able to view Man port stats.
-- 
-- Revision submit_cheetah_1231/1 2002/10/14 23:25:33 rmundhra
-- Fixed CR Q00540448: WebUI: always shows speed as
-- 10 and shows flow control for Man port.
-- 
-- Removed flow control as its been removed from CLI.
-- 
-- Revision submit_cheetah_1148/2 2002/10/11 22:48:42 rmundhra
-- Merged Rekha S. changes.
-- 
-- Revision submit_cheetah_1165/1 2002/10/10 18:39:31 rrekha
-- Added MIB object pktStatsDiscards.
-- 
-- Revision submit_cheetah_1150/1 2002/10/07 23:38:06 rrekha
-- Fixed Q00534536: Added agCurCfgTelnetServerPort/agNewCfgTelnetSeverPort.
-- 
-- Revision submit_cheetah_1124/1 2002/10/06 19:02:56 rrekha
-- Added objects for mgmt port defaults, agTfptPort for user input of data/mgmt
-- port for tftp.
-- Removed agMgmtPortDelete and agCurCfgNtpPort/agNewCfgNtpPort.
-- 
-- Revision submit_cheetah_1114/1 2002/10/04 00:38:46 rrekha
-- Added agCurCfgSnmpTimeout/agNewCfgSnmpTimeout.
-- Removed seperate timeout for apply, diff and dump.
-- 
-- Revision submit_cheetah_1068/1 2002/10/01 01:16:19 rrekha
-- Changed value of clear in enum to 2 to be consistent with 
-- other mibs as per Wendell's request.
-- 
-- Revision submit_cheetah_1058/1 2002/09/30 18:51:13 rrekha
-- Fixed Q00529961: Remove agNewCfgSyslogTrapIsd/agCurCfgSyslogTrapIsd.
-- 
-- Revision submit_cheetah_959/1 2002/09/18 23:50:41 rrekha
-- Added MIB objects and method routines for configuration dump.
-- 
-- Revision submit_cheetah_900/1 2002/09/09 21:30:50 rrekha
-- Added more description to agApplyConfig and agDiffState 
-- variables.
-- 
-- Revision submit_cheetah_833/1 2002/09/03 20:59:13 rmundhra
-- Fixed CR Q00512335: EMS cannot provision NTP to use
-- management port or data port.
-- Fixed CR Q00512343: WebUI cannot provision NTP to use
-- management port or data port.
-- 
-- Revision submit_cheetah_787/1 2002/08/28 20:08:54 rrekha
-- Added mib variables agHwTemperatureStatus and agHwFanStatus.
-- Removed old mib variables agHwPowerSupplyStatus and agHwSensor1Temp
-- as they are no longer available in Cheetah.
-- 
-- Revision submit_cheetah_649/1 2002/08/16 02:10:54 rrekha
-- Added MIB objects and method routines for management port 
-- support.
-- 
-- Revision submit_cheetah_507/1 2002/07/31 17:44:56 rrekha
-- Correct descriptions for pkt statistics.
-- 
-- Revision submit_cheetah_501/1 2002/07/29 23:26:09 rrekha
-- Added mib objects for ptk alloc hi-watermark statistics.
-- Remove unused mib objects agTftpServerIpAddr and agTftpDownload.
-- 
-- Revision submit_cheetah_405/1 2002/07/22 18:32:21 rmundhra
-- Fixed Q00487022: EMS: There should be OSPF syslog
-- messages implemented under Syslog-Trap.
-- 
-- Revision submit_cheetah_365/1 2002/07/16 19:01:51 rrekha
-- Ported NTP changes for GE_LATEST.
-- Changed ntp timezone setting from hours to hours:minutes, to support 
-- locales with a non-zero minute offset.
-- 
-- Revision submit_cheetah_176/1 2002/06/20 23:47:50 rmundhra
-- Added mib objects to clear the port statistics.
-- 
-- Revision submit_cheetah_162/1 2002/06/19 18:56:00 rrekha
-- Added entry 'failed' to agApplyConfig enum.
-- 
-- Revision submit_cheetah_81/1 2002/06/18 23:29:17 rrekha
-- Added a new node agApply to support apply warning/error messages
-- via SNMP.
-- 
-- Revision ch_1_0_0_dev/11 2002/06/04 18:55:00 rrekha
-- Fixed CR Q00436747: Ported fix from ge_latest.
-- Change type for pktStatsMediums, pktStatsJumbos, pktStatsSmalls to Gauge.
-- Added better descpritions for pktStats.
-- 
-- Revision ch_1_0_0_dev/10 2002/06/04 02:21:46 rrekha
-- Added remaining SP maint statistics.
-- 
-- Revision ch_1_0_0_dev/9 2002/06/03 20:29:21 rrekha
-- Added MIB objects for SP maint and CPU utilization statistics.
-- 
-- Revision ch_1_0_0_dev/8 2002/05/31 01:24:12 rrekha
-- Added node agDiff for SNMP diff support.
-- 
-- Revision ch_1_0_0_dev/7 2002/05/15 21:55:36 rrekha
-- Removed memStats as they no longer apply.
-- 
-- Revision ch_1_0_0_dev/6 2002/05/09 21:00:53 smiao
-- Removed TEMP_REMOVE_FOR_CHEETAH flag. Broght back CPU utilization stats.
-- 
-- Revision ch_1_0_0_dev/5 2002/04/30 20:42:46 rrekha
-- Added agSyslogMsgTable for the list of syslog messages.
-- 
-- Revision ch_1_0_0_dev/4 2002/04/25 01:04:49 rrekha
-- Removed mib objects agCurCfgSpanningTree/agNewCfgSpanningTree as
-- they are no longer used. 
-- Rearranged nodes under agGeneralGroup and agGeneralConfig group
-- into more meaningful groups : agSystem, agTftp, agNtp, agSyslog.
-- 
-- Revision ch_1_0_0_dev/3 2002/04/23 21:49:30 smiao
-- Renamed node cheetah to aws-switches.
-- 
-- Revision ch_1_0_0_dev/2 2002/04/09 18:03:04 ocheung
-- Bring back pkt stats for jumbo frames.
-- 
-- Revision ch_1_0_0_dev/1 2002/03/07 19:01:57 smiao
-- Removed unnecssary MIB objects for CHEEATH.
-- 
-- Revision ch10latest_smiao/2 2002/02/13 01:41:50 smiao
-- 	Initial checked in for cheetah MIB files.
-- 
-- $EndLog$
-- 
--

ALTEON-CHEETAH-SWITCH-MIB DEFINITIONS ::= BEGIN

IMPORTS
    enterprises, mgmt, NetworkAddress, IpAddress, Counter, Gauge, TimeTicks 
        FROM RFC1155-SMI
    OBJECT-TYPE
	FROM RFC-1212
    PhysAddress, DisplayString
	FROM RFC1213-MIB
    aws-switch 
	FROM ALTEON-ROOT-MIB;

-- groups in private-mibs
agent		  OBJECT IDENTIFIER ::= { aws-switch 1 }

agentConfig       OBJECT IDENTIFIER ::= { agent 1 }
agentStats        OBJECT IDENTIFIER ::= { agent 2 }
agentInfo         OBJECT IDENTIFIER ::= { agent 3 }
agentOper         OBJECT IDENTIFIER ::= { agent 4 }

agSystem          OBJECT IDENTIFIER ::= { agentConfig 1 }
agPortConfig      OBJECT IDENTIFIER ::= { agentConfig 2 }
agRadiusConfig    OBJECT IDENTIFIER ::= { agentConfig 3 }
agNTP	          OBJECT IDENTIFIER ::= { agentConfig 4 }
agSyslog          OBJECT IDENTIFIER ::= { agentConfig 5 }
agTrapHost        OBJECT IDENTIFIER ::= { agentConfig 6 }
agTftp            OBJECT IDENTIFIER ::= { agentConfig 7 }
agApply           OBJECT IDENTIFIER ::= { agentConfig 8 }
agMgmt            OBJECT IDENTIFIER ::= { agentConfig 9 }

pktStats	  OBJECT IDENTIFIER ::= { agentStats 1 }
mpCpuStats	  OBJECT IDENTIFIER ::= { agentStats 2 }
portStats	  OBJECT IDENTIFIER ::= { agentStats 3 }
spStats	          OBJECT IDENTIFIER ::= { agentStats 4 }
mgmtStats	  OBJECT IDENTIFIER ::= { agentStats 5 }

hardware          OBJECT IDENTIFIER ::= { agentInfo 1 }
portInfo          OBJECT IDENTIFIER ::= { agentInfo 2 }
swKeyInfo         OBJECT IDENTIFIER ::= { agentInfo 3 }
agDiff            OBJECT IDENTIFIER ::= { agentInfo 4 }
agCfgDump         OBJECT IDENTIFIER ::= { agentInfo 5 }
mgmtInfo          OBJECT IDENTIFIER ::= { agentInfo 6 }

-- There are two configuration blocks for Alteon switches.
-- The "current_config" reflects the configuration parameters that the
-- switch is operating on and it is read-only.  The objects with "CurCfg"
-- in the name are reflect to this configuration block.
--
-- The "new_config" accepts user configurations on set.  The objects with
-- "NewCfg" in the name are reflect to this configuration block.
--
-- The newly set configurations will not take effect until a "apply"
-- command has been issued (See agApplyConfiguration object defined in
-- ALTEON-PRIVATE-MIBS).
--
-- The newly set configurations will not be saved through next restarting
-- of the switch unless a "save" command has been issued (See
-- agSaveConfiguration object defined in ALTEON-PRIVATE-MIBS).

-- Hardware Information

hwPartNumber OBJECT-TYPE
    SYNTAX  DisplayString (SIZE(0..16))
    ACCESS  read-only
    STATUS  mandatory
    DESCRIPTION
        "The hardware part number of the Alteon Switch." 
    ::= { hardware 1 }

hwRevision OBJECT-TYPE
    SYNTAX DisplayString (SIZE(0..16))
    ACCESS read-only
    STATUS mandatory
    DESCRIPTION
	"The hardware revision.  If the revision is not
	 available, a zero length string should be returned."
    ::= { hardware 2 }

hwTemperatureStatus OBJECT-TYPE
    SYNTAX  INTEGER {
        ok(1),
        exceed(2)
        }
    ACCESS  read-only
    STATUS  mandatory
    DESCRIPTION
	"The status of the temperature sensor."
    ::= { hardware 3 }

hwFanStatus OBJECT-TYPE
    SYNTAX  INTEGER {
        ok(1),
        fail(2)
        }
    ACCESS  read-only
    STATUS  mandatory
    DESCRIPTION
	"The status of the fan."
    ::= { hardware 4 }

-- Port operation table
agPortOperTable OBJECT-TYPE
    SYNTAX  SEQUENCE OF AgPortOperTableEntry
    ACCESS  not-accessible
    STATUS  mandatory
    DESCRIPTION
        "The table of port operations."
    ::= { agentOper 1 }

agPortOperTableEntry OBJECT-TYPE
    SYNTAX  AgPortOperTableEntry
    ACCESS  not-accessible
    STATUS  mandatory
    DESCRIPTION
        "A row in the port operations table."
    INDEX   { portOperIdx }
    ::= { agPortOperTable 1 }

AgPortOperTableEntry ::=
    SEQUENCE {
	portOperIdx
	    INTEGER,
	portOperState
	    INTEGER,
	portOperRmon
	    INTEGER
	}

portOperIdx OBJECT-TYPE
    SYNTAX  INTEGER  
    ACCESS  read-only
    STATUS  mandatory
    DESCRIPTION
        "The port index."
    ::= { agPortOperTableEntry 1 }

portOperState OBJECT-TYPE
    SYNTAX  INTEGER {
        enabled(1),
        disabled(2)
        }
    ACCESS  read-write
    STATUS  mandatory
    DESCRIPTION
        "Enable/Disable port."
    ::= { agPortOperTableEntry 2 }

portOperRmon OBJECT-TYPE
    SYNTAX  INTEGER {
        enabled(1),
        disabled(2)
        }
    ACCESS  read-write
    STATUS  mandatory
    DESCRIPTION
        "Enable/Disable RMON for port."
    ::= { agPortOperTableEntry 3 }

-- Port information table

portInfoTable OBJECT-TYPE
    SYNTAX  SEQUENCE OF PortInfoTableEntry
    ACCESS  not-accessible
    STATUS  mandatory
    DESCRIPTION
        "The table of port information."
    ::= { portInfo 1 }

portInfoTableEntry OBJECT-TYPE
    SYNTAX  PortInfoTableEntry
    ACCESS  not-accessible
    STATUS  mandatory
    DESCRIPTION
        "A row in the port information table."
    INDEX   { portInfoIndx }
    ::= { portInfoTable 1 }

PortInfoTableEntry ::= SEQUENCE {
    portInfoIndx        	INTEGER,
    portInfoSpeed       	INTEGER,
    portInfoMode        	INTEGER,
    portInfoFlowCtrl    	INTEGER,
    portInfoLink        	INTEGER,
    portInfoPhyIfDescr  	DisplayString,
    portInfoPhyIfType   	INTEGER,
    portInfoPhyIfMtu    	INTEGER,
    portInfoPhyIfPhysAddress  	PhysAddress,
    portInfoPhyIfOperStatus	INTEGER, 
    portInfoPhyIfLastChange	TimeTicks	
    }

portInfoIndx OBJECT-TYPE
    SYNTAX  INTEGER  (1..255)
    ACCESS  read-only
    STATUS  mandatory
    DESCRIPTION
        "The port index."
    ::= { portInfoTableEntry 1 }

portInfoSpeed OBJECT-TYPE
    SYNTAX  INTEGER {
        mbs10(2),
        mbs100(3),
        mbs1000(4),
        any(5)
        }
    ACCESS  read-only
    STATUS  mandatory
    DESCRIPTION
        "The current operational speed of the port."
    ::= { portInfoTableEntry 2 }

portInfoMode OBJECT-TYPE
    SYNTAX  INTEGER {
        full-duplex(2),
        half-duplex(3)
        }
    ACCESS  read-only
    STATUS  mandatory
    DESCRIPTION
        "The current operational mode of the port."
    ::= { portInfoTableEntry 3 }

portInfoFlowCtrl OBJECT-TYPE
    SYNTAX  INTEGER {
        transmit(2),
        receive(3),
        both(4),
        none(5)
        }
    ACCESS  read-only
    STATUS  mandatory
    DESCRIPTION
        "The current operational flow control of the port."
    ::= { portInfoTableEntry 4 }

portInfoLink OBJECT-TYPE
    SYNTAX  INTEGER {
        up(1),
        down(2),
        disabled(3),
        inoperative(4) -- unrecognized PCI device
        }
     ACCESS  read-only
     STATUS  mandatory
     DESCRIPTION
         "The current operational link status of the port."
     ::= { portInfoTableEntry 5 }

portInfoPhyIfDescr OBJECT-TYPE
    SYNTAX  DisplayString (SIZE (0..255))
    ACCESS  read-only
    STATUS  mandatory
    DESCRIPTION
	    "A textual string containing information about the
	    interface.  This string should include the name of
	    the manufacturer, the product name and the version
	    of the hardware interface."
    ::= { portInfoTableEntry 6 }

portInfoPhyIfType OBJECT-TYPE
    SYNTAX  INTEGER {
		other(1),          -- none of the following
		regular1822(2),
		hdh1822(3),
		ddn-x25(4),
		rfc877-x25(5),
		ethernet-csmacd(6),
		iso88023-csmacd(7),
		iso88024-tokenBus(8),
		iso88025-tokenRing(9),
		iso88026-man(10),
		starLan(11),
		proteon-10Mbit(12),
		proteon-80Mbit(13),
		hyperchannel(14),
		fddi(15),
		lapb(16),
		sdlc(17),
		ds1(18),           -- T-1
		e1(19),            -- european equiv. of T-1
		basicISDN(20),
		primaryISDN(21),   -- proprietary serial
		propPointToPointSerial(22),
		ppp(23),
		softwareLoopback(24),
		eon(25),            -- CLNP over IP [11]
		ethernet-3Mbit(26),
		nsip(27),           -- XNS over IP
		slip(28),           -- generic SLIP
		ultra(29),          -- ULTRA technologies
		ds3(30),            -- T-3
		sip(31),            -- SMDS
		frame-relay(32)
	    }
    ACCESS  read-only
    STATUS  mandatory
    DESCRIPTION
	    "The type of interface, distinguished according to
	    the physical/link protocol(s) immediately `below'
	    the network layer in the protocol stack."
    ::= { portInfoTableEntry 7 }

portInfoPhyIfMtu OBJECT-TYPE
    SYNTAX  INTEGER
    ACCESS  read-only
    STATUS  mandatory
    DESCRIPTION
	    "The size of the largest datagram which can be
	    sent/received on the interface, specified in
	    octets.  For interfaces that are used for
	    transmitting network datagrams, this is the size
	    of the largest network datagram that can be sent
	    on the interface."
    ::= { portInfoTableEntry 8 }

portInfoPhyIfPhysAddress OBJECT-TYPE
    SYNTAX  PhysAddress
    ACCESS  read-only
    STATUS  mandatory
    DESCRIPTION
	    "The interface's address at the protocol layer
	    immediately `below' the network layer in the
	    protocol stack.  For interfaces which do not have
	    such an address (e.g., a serial line), this object
	    should contain an octet string of zero length."
    ::= { portInfoTableEntry 9 }

portInfoPhyIfOperStatus OBJECT-TYPE
    SYNTAX  INTEGER {
		up(1),       -- ready to pass packets
		down(2),
		testing(3)   -- in some test mode
	    }
    ACCESS  read-only
    STATUS  mandatory
    DESCRIPTION
	    "The current operational state of the interface.
	    The testing(3) state indicates that no operational
	    packets can be passed."
    ::= { portInfoTableEntry 10 }

portInfoPhyIfLastChange OBJECT-TYPE
    SYNTAX  TimeTicks
    ACCESS  read-only
    STATUS  mandatory
    DESCRIPTION
	    "The value of sysUpTime at the time the interface
	    entered its current operational state.  If the
	    current state was entered prior to the last re-
	    initialization of the local network management
	    subsystem, then this object contains a zero
	    value."
    ::= { portInfoTableEntry 11 }

agEnabledSwFeatures OBJECT-TYPE
    SYNTAX  DisplayString
    ACCESS  read-only
    STATUS  mandatory
    DESCRIPTION
        "The software features that are enabled on the switch."
    ::= { swKeyInfo 1 }

agEnabledGslbKey OBJECT-TYPE
    SYNTAX  INTEGER {
        enabled(1),
        disabled(2)
        }
    ACCESS  read-only
    STATUS  mandatory
    DESCRIPTION
        "Query if software key Global slb enabled on switch."
    ::= { swKeyInfo 2 }

agEnabledBwmKey OBJECT-TYPE
    SYNTAX  INTEGER {
        enabled(1),
        disabled(2)
        }
    ACCESS  read-only
    STATUS  mandatory
    DESCRIPTION
        "Query if software key Bandwidth Mgmt. enabled on switch."
    ::= { swKeyInfo 3 }

-- Agent System Group
-- This group of objects take effect on the 'SET' request.
-- There is no need to 'apply' or 'save'.
 
agApplyConfiguration OBJECT-TYPE
    SYNTAX  INTEGER {
        other(1),
        apply(2)
        }
    ACCESS  read-write
    STATUS  mandatory
    DESCRIPTION
        "This is an action object to apply the changes made to configuration 
         of the switch. By setting the value to apply(2), all the changes 
         made since the last apply are written to the new_config block.

         other(1) is returned when this object ie read. "
    ::= { agSystem 2 }

agSavePending OBJECT-TYPE
    SYNTAX  INTEGER {
        saveNeeded(1),
        noSaveNeeded(2)
        }
    ACCESS  read-only
    STATUS  mandatory
    DESCRIPTION
        "This object, when read, gives the user information
         whether an save action is needed and that the configuration
         has been applied but not saved to the flash."
    ::= { agSystem 3 }

agSaveConfiguration OBJECT-TYPE
    SYNTAX  INTEGER {
        ok(1),
        saveActive(2),
        notSaveActive(3)
        }
    ACCESS  read-write
    STATUS  mandatory
    DESCRIPTION
        "This is an action object to write current configuration to 
         nonvolatile storage.

         When issued with the saveActive, the active configuration
         in flash is saved to backup in flash and then the new
         configuration is saved to the active configuration in flash.

         When issued with notSaveActive, the active configuration
         is NOT saved to the flash and the active configuration is
         overwritten with the new configuration.

         ok(1) is returned always when read."
    ::= { agSystem 4 }

agRevert OBJECT-TYPE
    SYNTAX  INTEGER {
        other(1),
        revert(2)
        }
    ACCESS  read-write
    STATUS  mandatory
    DESCRIPTION
        "This is an action object to revert the unapplied changes 
         made to the switch. By setting the value to revert(2), 
         all the unapplied changes will be reverted. This action 
         will copy the current_config to the new_config block.

         other(1) is returned when this object is read. "
    ::= { agSystem 5 }

agRevertApply OBJECT-TYPE
    SYNTAX  INTEGER {
        other(1),
        revertApply(2)
        }
    ACCESS  read-write
    STATUS  mandatory
    DESCRIPTION
        "This is an action object to revert the unsaved changes 
         made to the switch. By setting the value to revertApply(2), 
         all the unsaved as well as unapplied changes will be 
         reverted.

         other(1) is returned when this object is read. "
    ::= { agSystem 6 }

agReset OBJECT-TYPE
    SYNTAX  INTEGER {
        other(1),
        reset(2)
        }
    ACCESS  read-write
    STATUS  mandatory
    DESCRIPTION
        "This is an action object to reboot the agent.
         other(1) is returned always when read."
    ::= { agSystem 7 }

agConfigForNxtReset OBJECT-TYPE
    SYNTAX  INTEGER {
        active(2),
        backup(3),
        default(4)
        }
    ACCESS  read-write
    STATUS  mandatory
    DESCRIPTION
        "The configuration information to be loaded from at next reset.

          The following values are writable:
              active(2)...active configuration block
              backup(3)...backup configuration block
              default(4)..default configuration block"
    ::= { agSystem 8 }

agImageForNxtReset OBJECT-TYPE
    SYNTAX  INTEGER {
        image1(2),
        image2(3)
        }
    ACCESS  read-write
    STATUS  mandatory
    DESCRIPTION
        "The software image to be booted from at next reset.

         The following values are writable:
             image1(2)...image 1
             image2(3)...image 2"
    ::= { agSystem 9 }

agSoftwareVersion OBJECT-TYPE
    SYNTAX  DisplayString (SIZE(0..16))
    ACCESS  read-only
    STATUS  mandatory
    DESCRIPTION
        "The version of the software image that is currently running on the 
         system in the form of 'major.minor.maintenance.bugfix'.  A zero 
         length string is returned if version is not available."
    ::= { agSystem 10 }

agBootVer OBJECT-TYPE
    SYNTAX  DisplayString (SIZE(0..16))
    ACCESS  read-only
    STATUS  mandatory
    DESCRIPTION
        "The version of the boot code in the form of 'major.minor.bugfix'.
         A zero length string is returned if version is not available."
    ::= { agSystem 11 }

agImage1Ver OBJECT-TYPE
    SYNTAX  DisplayString (SIZE(0..128))
    ACCESS  read-only
    STATUS  mandatory
    DESCRIPTION
        "The version of the software image stored in image 1 storage in the 
         form of 'major.minor.bugfix'.  A zero length string is returned if 
         version is not available or there is no valid software image."
    ::= { agSystem 12 }

agImage2Ver OBJECT-TYPE
    SYNTAX  DisplayString (SIZE(0..128))
    ACCESS  read-only
    STATUS  mandatory
    DESCRIPTION
        "The version of the software image stored in image 2 storage in the 
         form of 'major.minor.bugfix'.  A zero length string is returned if 
         version is not available or there is no valid software image."
    ::= { agSystem 13 }

agRtcDate OBJECT-TYPE
    SYNTAX  DisplayString (SIZE(0..16))
    ACCESS  read-write
    STATUS  mandatory
    DESCRIPTION
        "The date on the real time clock in the form of 'mm/dd/yy'.  
         A zero length string is returned if date is not available."
    ::= { agSystem 14 }

agRtcTime OBJECT-TYPE
    SYNTAX  DisplayString (SIZE(0..16))
    ACCESS  read-write
    STATUS  mandatory
    DESCRIPTION
        "The time on the real time clock in the form of 'hh:mm:ss'.  
         A zero length string is returned if time is not available."
    ::= { agSystem 15 }

agLastSetErrorReason   OBJECT-TYPE
    SYNTAX  DisplayString (SIZE(0..256))
    ACCESS  read-only
    STATUS  mandatory
    DESCRIPTION
        "The error reason of the last SET failure."
    ::= { agSystem 16 }

agCurCfgHttpServerPort OBJECT-TYPE
    SYNTAX  INTEGER (1..65535)
    ACCESS  read-only
    STATUS  mandatory
    DESCRIPTION
        "The TCP port number that the HTTP server is listening to 
         in the current_configuration block."
    ::= { agSystem 17 }

agNewCfgHttpServerPort OBJECT-TYPE
    SYNTAX  INTEGER (1..65535)
    ACCESS  read-write
    STATUS  mandatory
    DESCRIPTION
        "The TCP port number that the HTTP server is listening to 
         in the new_configuration block."
    ::= { agSystem 18 }

agCurCfgLoginBanner OBJECT-TYPE
    SYNTAX  DisplayString (SIZE(0..79))
    ACCESS  read-only
    STATUS  mandatory
    DESCRIPTION
        "The user defined login banner."
    ::= { agSystem 19 }

agNewCfgLoginBanner OBJECT-TYPE
    SYNTAX  DisplayString (SIZE(0..79))
    ACCESS  read-write
    STATUS  mandatory
    DESCRIPTION
        "The user defined login banner."
    ::= { agSystem 20 }

agCurCfgSmtpHost OBJECT-TYPE
    SYNTAX  DisplayString (SIZE(0..127))
    ACCESS  read-only
    STATUS  mandatory
    DESCRIPTION
        "The user defined SMTP host."
    ::= { agSystem 21 }

agNewCfgSmtpHost OBJECT-TYPE
    SYNTAX  DisplayString (SIZE(0..127))
    ACCESS  read-write
    STATUS  mandatory
    DESCRIPTION
        "The user defined SMTP host."
    ::= { agSystem 22 }

agCurCfgConsole OBJECT-TYPE
    SYNTAX  INTEGER {
        enabled(1),
        disabled(2)
        }
    ACCESS  read-only
    STATUS  mandatory
    DESCRIPTION
        "Enable or disable console output of syslog messages."
    ::= { agSystem 23 }

agNewCfgConsole OBJECT-TYPE
    SYNTAX  INTEGER {
        enabled(1),
        disabled(2)
        }
    ACCESS  read-write
    STATUS  mandatory
    DESCRIPTION
        "Enable or disable console output of syslog messages."
    ::= { agSystem 24 }

agCurCfgMgmtNetwork OBJECT-TYPE
    SYNTAX  IpAddress
    ACCESS  read-only
    STATUS  mandatory
    DESCRIPTION
        "The management network - corresponding to the mnet command of 
         the slb configuration menu." 
    ::= { agSystem 25 }

agNewCfgMgmtNetwork OBJECT-TYPE
    SYNTAX  IpAddress
    ACCESS  read-write
    STATUS  mandatory
    DESCRIPTION
        "The management network - corresponding to the mnet command of 
         the system menu." 
    ::= { agSystem 26 }

agCurCfgMgmtMask OBJECT-TYPE
    SYNTAX  IpAddress
    ACCESS  read-only
    STATUS  mandatory
    DESCRIPTION
        "The management subnet mask - corresponding to the mmask command 
         of the system configuration menu." 
    ::= { agSystem 27 }

agNewCfgMgmtMask OBJECT-TYPE
    SYNTAX  IpAddress
    ACCESS  read-write
    STATUS  mandatory
    DESCRIPTION
        "The management subnet mask - corresponding to the mmask command 
         of the system configuration menu." 
    ::= { agSystem 28 }

agCurCfgBootp OBJECT-TYPE
    SYNTAX  INTEGER {
        enabled(2),
        disabled(3)
        }
    ACCESS  read-only
    STATUS  mandatory
    DESCRIPTION
        "Enable or disable the use of BootP, as currently configured in the 
         current_configuration block."
    ::= { agSystem 29 }

agNewCfgBootp OBJECT-TYPE
    SYNTAX  INTEGER {
        enabled(2),
        disabled(3)
        }
    ACCESS  read-write
    STATUS  mandatory
    DESCRIPTION
        "Enable or disable the use of BootP, in the new_configuration block."
    ::= { agSystem 30 }

agSlotNumber OBJECT-TYPE
    SYNTAX INTEGER (1..10)
    ACCESS read-only
    STATUS mandatory
    DESCRIPTION
	"Identifies the slot in which this switch is installed. If the 
         agent implementing this MIB is not a blade in a chassis this 
         value has no meaning."
    ::= { agSystem 31 }

agCurCfgSnmpTimeout OBJECT-TYPE
    SYNTAX  INTEGER (1..30)
    ACCESS  read-only
    STATUS  mandatory
    DESCRIPTION
        "Once SNMP operations like agApplyConfig, agDiffState and  
         agDumpState, which use the state machine are done the resources
         used by these operations need to be freed by setting the state
         back to 'idle' so others can issue the commands via SNMP. 
         agSnmpTimeout indicates the number of minutes before the resources
         are freed and the state set back to 'idle' if this operation is not 
         performed by the user."
    ::= { agSystem 32 }

agNewCfgSnmpTimeout OBJECT-TYPE
    SYNTAX  INTEGER (1..30)
    ACCESS  read-write
    STATUS  mandatory
    DESCRIPTION
        "Once SNMP operations like agApplyConfig, agDiffState and  
         agDumpState, which use the state machine are done the resources
         used by these operations need to be freed by setting the state
         back to 'idle' so others can issue the commands via SNMP. 
         agSnmpTimeout indicates the number of minutes before the resources
         are freed and the state set back to 'idle' if this operation is not 
         performed by the user."
    ::= { agSystem 33 }

agCurCfgTelnetServerPort OBJECT-TYPE
    SYNTAX  INTEGER (1..65535)
    ACCESS  read-only
    STATUS  mandatory
    DESCRIPTION
        "The TCP port number that the telnet server listens for telnet 
         sessions."
    ::= { agSystem 34 }

agNewCfgTelnetServerPort OBJECT-TYPE
    SYNTAX  INTEGER (1..65535)
    ACCESS  read-write
    STATUS  mandatory
    DESCRIPTION
        "The TCP port number that the telnet server listens for telnet 
         sessions."
    ::= { agSystem 35 }

agClearFlashDump OBJECT-TYPE
    SYNTAX  INTEGER {
        ok(1),
        clear(2)
        }
    ACCESS  read-write
    STATUS  mandatory
    DESCRIPTION
        "This is an action object to clear the FLASH dump. 
         ok(1) is returned when this object is read. "
    ::= { agSystem 36 }

-- Syslog Configuration
agCurCfgSyslogHost OBJECT-TYPE
    SYNTAX  IpAddress
    ACCESS  read-only
    STATUS  mandatory
    DESCRIPTION
        "The syslog host IP address, as currently configured in
         the current_configuration block."
    ::= { agSyslog 1 }

agNewCfgSyslogHost OBJECT-TYPE
    SYNTAX  IpAddress
    ACCESS  read-write
    STATUS  mandatory
    DESCRIPTION
        "The syslog host IP address, in the new_configuration block."
    ::= { agSyslog 2 }

agCurCfgSyslog2Host OBJECT-TYPE
    SYNTAX  IpAddress
    ACCESS  read-only
    STATUS  mandatory
    DESCRIPTION
        "The second syslog host IP address, as currently configured in
         the current_configuration block."
    ::= { agSyslog 3 }

agNewCfgSyslog2Host OBJECT-TYPE
    SYNTAX  IpAddress
    ACCESS  read-write
    STATUS  mandatory
    DESCRIPTION
        "The second syslog host IP address, in the new_configuration block."
    ::= { agSyslog 4 }

agCurCfgSyslogFac   OBJECT-TYPE
    SYNTAX  INTEGER  {
	local0(1),
	local1(2),
	local2(3),
	local3(4),
	local4(5),
	local5(6),
	local6(7),
	local7(8)
	}
    ACCESS  read-only
    STATUS  mandatory
    DESCRIPTION
        "The facility of syslog host in the current_configuration block."
    ::= { agSyslog 5 }

agNewCfgSyslogFac   OBJECT-TYPE
    SYNTAX  INTEGER  {
	local0(1), 
	local1(2),
	local2(3),
	local3(4),
	local4(5),
	local5(6),
        local6(7),
	local7(8)
	}
    ACCESS  read-write
    STATUS  mandatory
    DESCRIPTION
        "The facility of syslog host in the new_configuration block."
    ::= { agSyslog 6 }

agCurCfgSyslog2Fac   OBJECT-TYPE
    SYNTAX  INTEGER  {
	local0(1),
	local1(2),
	local2(3),
	local3(4),
	local4(5),
	local5(6),
	local6(7),
	local7(8)
	}
    ACCESS  read-only
    STATUS  mandatory
    DESCRIPTION
        "The facility of syslog2 host in the current_configuration block."
    ::= { agSyslog 7 }

agNewCfgSyslog2Fac   OBJECT-TYPE
    SYNTAX  INTEGER  {
	local0(1), 
	local1(2),
	local2(3),
	local3(4),
        local4(5),
	local5(6),
        local6(7),
	local7(8)
	}
    ACCESS  read-write
    STATUS  mandatory
    DESCRIPTION
        "The facility of syslogs host in the new_configuration block."
    ::= { agSyslog 8 }

agClrSyslogMsgs OBJECT-TYPE
    SYNTAX  INTEGER {
            other(1),
            reset(2)
            }
    ACCESS  read-write
    STATUS  mandatory
    DESCRIPTION
        "Clears all current Syslog messages."
    ::= { agSyslog 9 }

agSyslogMsgTableMaxSize OBJECT-TYPE
    SYNTAX  INTEGER
    ACCESS  read-only
    STATUS  mandatory
    DESCRIPTION
        "The maximum number of rows in the syslog message table."
    ::= { agSyslog 10 }

agSyslogMsgTable OBJECT-TYPE
    SYNTAX  SEQUENCE OF AgSyslogMsgTableEntry
    ACCESS  not-accessible
    STATUS  mandatory
    DESCRIPTION
        "The table of syslog messages."
    ::= { agSyslog 11 }

agSyslogMsgTableEntry OBJECT-TYPE
    SYNTAX  AgSyslogMsgTableEntry
    ACCESS  not-accessible
    STATUS  mandatory
    DESCRIPTION
        "A syslog message stored on the switch."
    INDEX   { agSyslogMsgIndex }
    ::= { agSyslogMsgTable 1 }

AgSyslogMsgTableEntry ::= SEQUENCE {
    agSyslogMsgIndex          INTEGER,
    agSyslogMessage           DisplayString
    }

agSyslogMsgIndex OBJECT-TYPE
    SYNTAX  INTEGER
    ACCESS  read-only
    STATUS  mandatory
    DESCRIPTION
        "The syslog message table index."
    ::= { agSyslogMsgTableEntry 1 }

agSyslogMessage OBJECT-TYPE
    SYNTAX  DisplayString (SIZE(0..128))
    ACCESS  read-only
    STATUS  mandatory
    DESCRIPTION
        "The syslog message."
    ::= { agSyslogMsgTableEntry 2 }

agLog OBJECT IDENTIFIER ::= { agSyslog 12 }

agNewCfgSyslogTrapConsole OBJECT-TYPE
    SYNTAX  INTEGER {
        enabled(1),
        disabled(2)
        }
    ACCESS  read-write
    STATUS  mandatory
    DESCRIPTION
        "Enable or disable console syslog and SNMP trap, in the 
         new_configuration block."
    ::= { agLog 1 }

agCurCfgSyslogTrapConsole OBJECT-TYPE
    SYNTAX  INTEGER {
        enabled(1),
        disabled(2)
        }
    ACCESS  read-only
    STATUS  mandatory
    DESCRIPTION
        "Enable or disable console syslog and SNMP trap, as currently 
         configured in the current_configuration block."
    ::= { agLog 2 }

agNewCfgSyslogTrapSystem OBJECT-TYPE
    SYNTAX  INTEGER {
        enabled(1),
        disabled(2)
        }
    ACCESS  read-write
    STATUS  mandatory
    DESCRIPTION
        "Enable or disable system level syslog and SNMP trap, in the 
         new_configuration block."
    ::= { agLog 3 }

agCurCfgSyslogTrapSystem OBJECT-TYPE
    SYNTAX  INTEGER {
        enabled(1),
        disabled(2)
        }
    ACCESS  read-only
    STATUS  mandatory
    DESCRIPTION
        "Enable or disable system level syslog and SNMP trap, as currently 
         configured in the current_configuration block."
    ::= { agLog 4 }

agNewCfgSyslogTrapMgmt OBJECT-TYPE
    SYNTAX  INTEGER {
        enabled(1),
        disabled(2)
        }
    ACCESS  read-write
    STATUS  mandatory
    DESCRIPTION
        "Enable or disable management(flash, config, login) syslog and SNMP 
         trap, in the new_configuration block."
    ::= { agLog 5 }

agCurCfgSyslogTrapMgmt OBJECT-TYPE
    SYNTAX  INTEGER {
        enabled(1),
        disabled(2)
        }
    ACCESS  read-only
    STATUS  mandatory
    DESCRIPTION
        "Enable or disable management(flash, config, login) syslog and SNMP 
         trap, as currently configured in the current_configuration block."
    ::= { agLog 6 }

agNewCfgSyslogTrapCli OBJECT-TYPE
    SYNTAX  INTEGER {
        enabled(1),
        disabled(2)
        }
    ACCESS  read-write
    STATUS  mandatory
    DESCRIPTION
        "Enable or disable CLI generated error syslog and SNMP trap, in the 
	 new_configuration block."
    ::= { agLog 7 }

agCurCfgSyslogTrapCli OBJECT-TYPE
    SYNTAX  INTEGER {
        enabled(1),
        disabled(2)
        }
    ACCESS  read-only
    STATUS  mandatory
    DESCRIPTION
        "Enable or disable CLI generated error syslog and SNMP trap, as 
         currently configured in the current_configuration block." 
    ::= { agLog 8 }

agNewCfgSyslogTrapStp OBJECT-TYPE
    SYNTAX  INTEGER {
        enabled(1),
        disabled(2)
        }
    ACCESS  read-write
    STATUS  mandatory
    DESCRIPTION
        "Enable or disable spanning tree syslog and SNMP trap, in the 
         new_configuration block."
    ::= { agLog 9 }

agCurCfgSyslogTrapStp OBJECT-TYPE
    SYNTAX  INTEGER {
        enabled(1),
        disabled(2)
        }
    ACCESS  read-only
    STATUS  mandatory
    DESCRIPTION
        "Enable or disable spanning tree syslog and SNMP trap, as currently 
         configured in the current_configuration block."
    ::= { agLog 10 }

agNewCfgSyslogTrapVlan OBJECT-TYPE
    SYNTAX  INTEGER {
        enabled(1),
        disabled(2)
        }
    ACCESS  read-write
    STATUS  mandatory
    DESCRIPTION
        "Enable or disable VLAN syslog and SNMP trap, in the new_configuration
         block."
    ::= { agLog 11 }

agCurCfgSyslogTrapVlan OBJECT-TYPE
    SYNTAX  INTEGER {
        enabled(1),
        disabled(2)
        }
    ACCESS  read-only
    STATUS  mandatory
    DESCRIPTION
        "Enable or disable VLAN syslog and SNMP trap, as currently configured 
         in the current_configuration block."
    ::= { agLog 12 }

agNewCfgSyslogTrapSlb OBJECT-TYPE
    SYNTAX  INTEGER {
        enabled(1),
        disabled(2)
        }
    ACCESS  read-write
    STATUS  mandatory
    DESCRIPTION
        "Enable or disable SLB syslog and SNMP trap, in the new_configuration 
         block."
    ::= { agLog 13 }

agCurCfgSyslogTrapSlb OBJECT-TYPE
    SYNTAX  INTEGER {
        enabled(1),
        disabled(2)
        }
    ACCESS  read-only
    STATUS  mandatory
    DESCRIPTION
        "Enable or disable SLB syslog and SNMP trap, as currently configured 
         in the current_configuration block."
    ::= { agLog 14 }

agNewCfgSyslogTrapGslb OBJECT-TYPE
    SYNTAX  INTEGER {
        enabled(1),
        disabled(2)
        }
    ACCESS  read-write
    STATUS  mandatory
    DESCRIPTION
        "Enable or disable GSLB syslog and SNMP trap, in the new_configuration
         block."
    ::= { agLog 15 }

agCurCfgSyslogTrapGslb OBJECT-TYPE
    SYNTAX  INTEGER {
        enabled(1),
        disabled(2)
        }
    ACCESS  read-only
    STATUS  mandatory
    DESCRIPTION
        "Enable or disable GSLB syslog and SNMP trap, as currently configured 
         in the current_configuration block."
    ::= { agLog 16 }

agNewCfgSyslogTrapFilter OBJECT-TYPE
    SYNTAX  INTEGER {
        enabled(1),
        disabled(2)
        }
    ACCESS  read-write
    STATUS  mandatory
    DESCRIPTION
        "Enable or disable filter syslog and SNMP trap, in the 
         new_configuration block."
    ::= { agLog 17 }

agCurCfgSyslogTrapFilter OBJECT-TYPE
    SYNTAX  INTEGER {
        enabled(1),
        disabled(2)
        }
    ACCESS  read-only
    STATUS  mandatory
    DESCRIPTION
        "Enable or disable filter syslog and SNMP trap, as currently 
         configured in the current_configuration block."
    ::= { agLog 18 }

agNewCfgSyslogTrapSsh OBJECT-TYPE
    SYNTAX  INTEGER {
        enabled(1),
        disabled(2)
        }
    ACCESS  read-write
    STATUS  mandatory
    DESCRIPTION
        "Enable or disable SSH, RADIUS syslog and SNMP trap, in the 
         new_configuration block."
    ::= { agLog 19 }

agCurCfgSyslogTrapSsh OBJECT-TYPE
    SYNTAX  INTEGER {
        enabled(1),
        disabled(2)
        }
    ACCESS  read-only
    STATUS  mandatory
    DESCRIPTION
        "Enable or disable SSH, RADIUS syslog and SNMP trap, as currently 
         configured in the current_configuration block."
    ::= { agLog 20 }

agNewCfgSyslogTrapVrrp OBJECT-TYPE
    SYNTAX  INTEGER {
        enabled(1),
        disabled(2)
        }
    ACCESS  read-write
    STATUS  mandatory
    DESCRIPTION
        "Enable or disable VRRP syslog and SNMP trap, in the new_configuration
         block."
    ::= { agLog 21 }

agCurCfgSyslogTrapVrrp OBJECT-TYPE
    SYNTAX  INTEGER {
        enabled(1),
        disabled(2)
        }
    ACCESS  read-only
    STATUS  mandatory
    DESCRIPTION
        "Enable or disable VRRP syslog and SNMP trap, as currently configured 
         in the current_configuration block."
    ::= { agLog 22 }

agNewCfgSyslogTrapBgp OBJECT-TYPE
    SYNTAX  INTEGER {
        enabled(1),
        disabled(2)
        }
    ACCESS  read-write
    STATUS  mandatory
    DESCRIPTION
        "Enable or disable BGP syslog and SNMP trap, in the new_configuration 
         block."
    ::= { agLog 23 }

agCurCfgSyslogTrapBgp OBJECT-TYPE
    SYNTAX  INTEGER {
        enabled(1),
        disabled(2)
        }
    ACCESS  read-only
    STATUS  mandatory
    DESCRIPTION
        "Enable or disable BGP syslog and SNMP trap, as currently configured 
         in the current_configuration block."
    ::= { agLog 24 }

agNewCfgSyslogTrapNtp OBJECT-TYPE
    SYNTAX  INTEGER {
        enabled(1),
        disabled(2)
        }
    ACCESS  read-write
    STATUS  mandatory
    DESCRIPTION
        "Enable or disable NTP syslog and SNMP trap, in the new_configuration 
         block."
    ::= { agLog 25 }

agCurCfgSyslogTrapNtp OBJECT-TYPE
    SYNTAX  INTEGER {
        enabled(1),
        disabled(2)
        }
    ACCESS  read-only
    STATUS  mandatory
    DESCRIPTION
        "Enable or disable NTP syslog and SNMP trap, as currently configured 
         in the current_configuration block."
    ::= { agLog 26 }

agNewCfgSyslogTrapIp OBJECT-TYPE
    SYNTAX  INTEGER {
        enabled(1),
        disabled(2)
        }
    ACCESS  read-write
    STATUS  mandatory
    DESCRIPTION
        "Enable or disable IP related syslog and SNMP trap, in the 
         new_configuration block."
    ::= { agLog 31 }

agCurCfgSyslogTrapIp OBJECT-TYPE
    SYNTAX  INTEGER {
        enabled(1),
        disabled(2)
        }
    ACCESS  read-only
    STATUS  mandatory
    DESCRIPTION
        "Enable or disable IP related syslog and SNMP trap, as currently 
         configured in the current_configuration block."
    ::= { agLog 32 }

agNewCfgSyslogTrapWeb OBJECT-TYPE
    SYNTAX  INTEGER {
        enabled(1),
        disabled(2)
        }
    ACCESS  read-write
    STATUS  mandatory
    DESCRIPTION
        "Enable or disable WEBUI related syslog and SNMP trap, in the 
         new_configuration block."
    ::= { agLog 35 }

agCurCfgSyslogTrapWeb OBJECT-TYPE
    SYNTAX  INTEGER {
        enabled(1),
        disabled(2)
        }
    ACCESS  read-only
    STATUS  mandatory
    DESCRIPTION
        "Enable or disable WEBUI related syslog and SNMP trap, as currently 
         configured in the current_configuration block."
    ::= { agLog 36 }

agNewCfgSyslogTrapSynAtk OBJECT-TYPE
    SYNTAX  INTEGER {
        enabled(1),
        disabled(2)
        }
    ACCESS  read-write
    STATUS  mandatory
    DESCRIPTION
        "Enable or disable SYN attack detection related syslog and SNMP trap,
         in the new_configuration block."
    ::= { agLog 37 }

agCurCfgSyslogTrapSynAtk OBJECT-TYPE
    SYNTAX  INTEGER {
        enabled(1),
        disabled(2)
        }
    ACCESS  read-only
    STATUS  mandatory
    DESCRIPTION
        "Enable or disable SYN attack detection related syslog and SNMP trap,
         as currently configured in the current_configuration block."
    ::= { agLog 38 }

agNewCfgSyslogTrapTcpLim OBJECT-TYPE
    SYNTAX  INTEGER {
        enabled(1),
        disabled(2)
        }
    ACCESS  read-write
    STATUS  mandatory
    DESCRIPTION
        "Enable or disable TCP rate limiting related syslog and SNMP trap, 
         in the new_configuration block."
    ::= { agLog 39 }

agCurCfgSyslogTrapTcpLim OBJECT-TYPE
    SYNTAX  INTEGER {
        enabled(1),
        disabled(2)
        }
    ACCESS  read-only
    STATUS  mandatory
    DESCRIPTION
        "Enable or disable TCP rate limiting related syslog and SNMP trap,
         as currently configured in the current_configuration block."
    ::= { agLog 40 }

agNewCfgSyslogTrapOspf OBJECT-TYPE
    SYNTAX  INTEGER {
        enabled(1),
        disabled(2)
        }
    ACCESS  read-write
    STATUS  mandatory
    DESCRIPTION
        "Enable or disable OSPF related syslog and SNMP trap, 
         in the new_configuration block."
    ::= { agLog 41 }

agCurCfgSyslogTrapOspf OBJECT-TYPE
    SYNTAX  INTEGER {
        enabled(1),
        disabled(2)
        }
    ACCESS  read-only
    STATUS  mandatory
    DESCRIPTION
        "Enable or disable OSPF related syslog and SNMP trap,
         as currently configured in the current_configuration block."
    ::= { agLog 42 }


-- Trap host table
agTrapHostTableMaxEnt OBJECT-TYPE
    SYNTAX  INTEGER
    ACCESS  read-only
    STATUS  mandatory
    DESCRIPTION
        "The maximum number of rows in the trap host table."
    ::= { agTrapHost 1 }

agCurCfgTrapHostTable OBJECT-TYPE
    SYNTAX  SEQUENCE OF AgCurCfgTrapHostEntry
    ACCESS  not-accessible
    STATUS  mandatory
    DESCRIPTION
        "The table of trap hosts which to send SNMP traps in the 
         current_configuration block."
    ::= { agTrapHost 2 }

agCurCfgTrapHostEntry OBJECT-TYPE
    SYNTAX  AgCurCfgTrapHostEntry
    ACCESS  not-accessible
    STATUS  mandatory
    DESCRIPTION
        "A row in the trap host table in the current_configuration block."
    INDEX   { agCurCfgTrapHostIndx }
    ::= { agCurCfgTrapHostTable 1 }

AgCurCfgTrapHostEntry ::= SEQUENCE {
    agCurCfgTrapHostIndx            INTEGER,
    agCurCfgTrapHostIpAddr          IpAddress,
    agCurCfgTrapHostCommString      DisplayString
    }

agCurCfgTrapHostIndx OBJECT-TYPE
    SYNTAX  INTEGER  (1..255)
    ACCESS  read-only
    STATUS  mandatory
    DESCRIPTION
        "The index of the row in trap host table."
    ::= { agCurCfgTrapHostEntry 1 }

agCurCfgTrapHostIpAddr OBJECT-TYPE
    SYNTAX  IpAddress
    ACCESS  read-only
    STATUS  mandatory
    DESCRIPTION
        "The IP address of a trap host."
    ::= { agCurCfgTrapHostEntry 2 }

agCurCfgTrapHostCommString OBJECT-TYPE
    SYNTAX  DisplayString (SIZE (0..32))
    ACCESS  read-only
    STATUS  mandatory
    DESCRIPTION
        "The SNMP community string to use with the trap host"
    ::= { agCurCfgTrapHostEntry 3 }

agNewCfgTrapHostTable OBJECT-TYPE
    SYNTAX  SEQUENCE OF AgNewCfgTrapHostEntry
    ACCESS  not-accessible
    STATUS  mandatory
    DESCRIPTION
        "The table of trap hosts which to send SNMP traps in the
          new_configuration block."
    ::= { agTrapHost 3 }

agNewCfgTrapHostEntry OBJECT-TYPE
    SYNTAX  AgNewCfgTrapHostEntry
    ACCESS  not-accessible
    STATUS  mandatory
    DESCRIPTION
        "A row in the trap host table in the new_configuration block."
    INDEX   { agNewCfgTrapHostIndx }
    ::= { agNewCfgTrapHostTable 1 }

AgNewCfgTrapHostEntry ::= SEQUENCE {
    agNewCfgTrapHostIndx            INTEGER,
    agNewCfgTrapHostIpAddr          IpAddress,
    agNewCfgTrapHostCommString      DisplayString
    }

agNewCfgTrapHostIndx OBJECT-TYPE
    SYNTAX  INTEGER  (1..255)
    ACCESS  read-only
    STATUS  mandatory
    DESCRIPTION
        "The index of the row in trap host table."
    ::= { agNewCfgTrapHostEntry 1 }

agNewCfgTrapHostIpAddr OBJECT-TYPE
    SYNTAX  IpAddress
    ACCESS  read-write
    STATUS  mandatory
    DESCRIPTION
        "The IP address of a trap host."
    ::= { agNewCfgTrapHostEntry 2 }

agNewCfgTrapHostCommString OBJECT-TYPE
    SYNTAX  DisplayString (SIZE (0..32))
    ACCESS  read-write
    STATUS  mandatory
    DESCRIPTION
        "The SNMP community string to use with the trap host"
    ::= { agNewCfgTrapHostEntry 3 }

-- TFTP Config
agTftpServer OBJECT-TYPE
    SYNTAX  DisplayString (SIZE(0..64))
    ACCESS  read-write
    STATUS  mandatory
    DESCRIPTION
        "The TFTP server IP address or domain name."
    ::= { agTftp 1 }

agTftpImage OBJECT-TYPE
    SYNTAX  INTEGER {
        image1(2),
        image2(3)
        }
    ACCESS  read-write
    STATUS  mandatory
    DESCRIPTION
        "Whether the image file should be loaded in image1 or image2 in flash."
    ::= { agTftp 2 }

agTftpImageFileName OBJECT-TYPE
    SYNTAX  DisplayString (SIZE(0..128))
    ACCESS  read-write
    STATUS  mandatory
    DESCRIPTION
        "The image file name to be downloaded."
    ::= { agTftp 3 }

agTftpCfgFileName OBJECT-TYPE
    SYNTAX  DisplayString (SIZE(0..128))
    ACCESS  read-write
    STATUS  mandatory
    DESCRIPTION
        "The configuration file name."
    ::= { agTftp 4 }

agTftpDumpFileName OBJECT-TYPE
    SYNTAX  DisplayString (SIZE(0..128))
    ACCESS  read-write
    STATUS  mandatory
    DESCRIPTION
        "The file name for core dump."
    ::= { agTftp 5 }

agTftpAction OBJECT-TYPE
    SYNTAX  INTEGER {
        other(1),
        img-get(2),
        cfg-get(3),
        cfg-put(4),
        dump-put(5)
        }
    ACCESS  read-write
    STATUS  mandatory
    DESCRIPTION
        "This is an action object to perform various TFTP Get or Put functions.
         The TFTP sever is specified in agTftpServer object.
	 img-get(2) - Download switch image from a specified image
                      file (agTftpImageFileName) on the TFTP server to
	              the destinated storage (agTftpImage).
	 cfg-get(3) - Download switch configuration from a specified
                      file (agTftpCfgFileName) on the TFTP server.
	 cfg-put(4) - Upload switch configuration to a specified
                      file (agTftpCfgFileName) on the TFTP server.
	 dump-put(5)- Download switch core dump to a specified
                      file (agTftpDumpFileName) on the TFTP server.

         other(1) is returned always when read."
    ::= { agTftp 6 }

agTftpLastActionStatus OBJECT-TYPE
    SYNTAX  DisplayString (SIZE(0..128))
    ACCESS  read-only
    STATUS  mandatory
    DESCRIPTION
        "The recorded status of the previous TFTP activity."
    ::= { agTftp 7 }

agTftpPort OBJECT-TYPE
    SYNTAX  INTEGER {
        data(1),
        mgmt(2)
        }
    ACCESS  read-write
    STATUS  mandatory
    DESCRIPTION
        "Specify whether the TFTP operation should nbe performed over the 
         data port or the management port."
    ::= { agTftp 8 }

-- Agent Port Table

agPortTableMaxEnt OBJECT-TYPE
    SYNTAX  INTEGER
    ACCESS  read-only
    STATUS  mandatory
    DESCRIPTION
        "The maximum number of rows in the port configuration host table."
    ::= { agPortConfig 1 }

agPortCurCfgTable OBJECT-TYPE
    SYNTAX  SEQUENCE OF AgPortCurCfgTableEntry
    ACCESS  not-accessible
    STATUS  mandatory
    DESCRIPTION
        "The table of port configuration in the current_configuration block."
    ::= { agPortConfig 2 }

agPortCurCfgTableEntry OBJECT-TYPE
    SYNTAX  AgPortCurCfgTableEntry
    ACCESS  not-accessible
    STATUS  mandatory
    DESCRIPTION
        "A row in the port table in the current_configuration block."
    INDEX   { agPortCurCfgIndx }
    ::= { agPortCurCfgTable 1 }

AgPortCurCfgTableEntry ::= SEQUENCE {
    agPortCurCfgIndx           INTEGER,
    agPortCurCfgState          INTEGER,
    agPortCurCfgVlanTag        INTEGER,
    agPortCurCfgStp            INTEGER,
    agPortCurCfgRmon           INTEGER,
    agPortCurCfgPVID           INTEGER,
    agPortCurCfgFastEthAutoNeg INTEGER,
    agPortCurCfgFastEthSpeed   INTEGER,
    agPortCurCfgFastEthMode    INTEGER,
    agPortCurCfgFastEthFctl    INTEGER,
    agPortCurCfgGigEthAutoNeg  INTEGER,
    agPortCurCfgGigEthFctl     INTEGER,
    agPortCurCfgPortName       DisplayString,
    agPortCurCfgBwmContract    INTEGER,
    agPortCurCfgDiscardNonIPs  INTEGER,
    agPortCurCfgLinkTrap       INTEGER
    }

agPortCurCfgIndx OBJECT-TYPE
    SYNTAX  INTEGER  (1..255)
    ACCESS  read-only
    STATUS  mandatory
    DESCRIPTION
        "The index of the row in port configurations table."
    ::= { agPortCurCfgTableEntry 1 }

agPortCurCfgState OBJECT-TYPE
    SYNTAX  INTEGER {
        enabled(2),
        disabled(3)
	}
    ACCESS  read-only
    STATUS  mandatory
    DESCRIPTION
        "This is the state of the port."
    ::= { agPortCurCfgTableEntry 2 }

agPortCurCfgVlanTag OBJECT-TYPE
    SYNTAX  INTEGER {
        tagged(2),
        untagged(3)
        }
    ACCESS  read-only
    STATUS  mandatory
    DESCRIPTION
        "This is VLAN tag state of the port"
    ::= { agPortCurCfgTableEntry 3 }

agPortCurCfgStp OBJECT-TYPE
    SYNTAX  INTEGER {
        on(2),
        off(3)
        }
    ACCESS  read-only
    STATUS  mandatory
    DESCRIPTION
        "This object is used to turn Spanning Tree on or off for the port."
    ::= { agPortCurCfgTableEntry 4 }

agPortCurCfgRmon OBJECT-TYPE
    SYNTAX  INTEGER {
        on(2),
        off(3)
        }
    ACCESS  read-only
    STATUS  mandatory
    DESCRIPTION
        "This object is used to turn RMON on or off on the port."
   ::= { agPortCurCfgTableEntry 5 }

agPortCurCfgPVID OBJECT-TYPE
    SYNTAX  INTEGER (1..4093)
    ACCESS  read-only
    STATUS  mandatory
    DESCRIPTION
        "The default VLAN ID for the port."
    ::= { agPortCurCfgTableEntry 6 }

agPortCurCfgFastEthAutoNeg OBJECT-TYPE
    SYNTAX  INTEGER {
        on(2),
        off(3)
        }
    ACCESS  read-only
    STATUS  mandatory
    DESCRIPTION
        "This object is used to turn the autonegotiation on or off
         for fast Ethernet connection."
    ::= { agPortCurCfgTableEntry 7 }

agPortCurCfgFastEthSpeed OBJECT-TYPE
    SYNTAX  INTEGER {
        mbs10(2),
        mbs100(3),
        mbs10or100(4)
        }
    ACCESS  read-only
    STATUS  mandatory
    DESCRIPTION
        "Selects the port speed for fast Ethernet connection."
    ::= { agPortCurCfgTableEntry 8 }

agPortCurCfgFastEthMode OBJECT-TYPE
    SYNTAX  INTEGER {
        full-duplex(2),
        half-duplex(3),
        full-or-half-duplex(4)
        }
    ACCESS  read-only
    STATUS  mandatory
    DESCRIPTION
        "This object is used to select port mode for fast Ethernet connection."
    ::= { agPortCurCfgTableEntry 9 }

agPortCurCfgFastEthFctl OBJECT-TYPE
    SYNTAX  INTEGER {
        transmit(2),
        receive(3),
        both(4),
        none(5)
        }
    ACCESS  read-only
    STATUS  mandatory
    DESCRIPTION
        "Selects the port flow control for fast Ethernet connection."
    ::= { agPortCurCfgTableEntry 10 }

agPortCurCfgGigEthAutoNeg OBJECT-TYPE
    SYNTAX  INTEGER {
        on(2),
        off(3)
        }
    ACCESS  read-only
    STATUS  mandatory
    DESCRIPTION
        "This object is used to turn the autonegotiation on or off
         for gigabit Ethernet connection."
    ::= { agPortCurCfgTableEntry 11 }

agPortCurCfgGigEthFctl OBJECT-TYPE
    SYNTAX  INTEGER {
        transmit(2),
        receive(3),
        both(4),
        none(5)
        }
    ACCESS  read-only
    STATUS  mandatory
    DESCRIPTION
        "This object is used to select port flow control for
         gigabit Ethernet connection."
    ::= { agPortCurCfgTableEntry 12 }

agPortCurCfgPortName	OBJECT-TYPE
    SYNTAX  DisplayString (SIZE(0..63))
    ACCESS  read-only
    STATUS  mandatory
    DESCRIPTION
        "The switch port name."
    ::= { agPortCurCfgTableEntry 13 }

agPortCurCfgBwmContract OBJECT-TYPE
    SYNTAX  INTEGER
    ACCESS  read-only
    STATUS  mandatory
    DESCRIPTION
        "The switch port Bandwidth Management contract number."
    ::= { agPortCurCfgTableEntry 14 }

agPortCurCfgDiscardNonIPs OBJECT-TYPE
    SYNTAX  INTEGER {
        enabled(2),
        disabled(3)
        }
    ACCESS  read-only
    STATUS  mandatory
    DESCRIPTION
        "Enable or disable to discard all non-IP traffic on the switch port."
    ::= { agPortCurCfgTableEntry 15 }

agPortCurCfgLinkTrap OBJECT-TYPE
    SYNTAX  INTEGER {
	enabled(1),
	disabled(2)
    }
    ACCESS  read-only
    STATUS  mandatory
    DESCRIPTION
        "Indicates whether linkUp/linkDown traps should be
        generated for this interface.

        By default, this object should have the value
        enabled(1) for interfaces which do not operate on
        'top' of any other interface (as defined in the
        ifStackTable), and disabled(2) otherwise."
    ::= { agPortCurCfgTableEntry 16 }

agPortNewCfgTable OBJECT-TYPE
    SYNTAX  SEQUENCE OF AgPortNewCfgTableEntry
    ACCESS  not-accessible
    STATUS  mandatory
    DESCRIPTION
        "The table of port configuration in the new_configuration block."
    ::= { agPortConfig 3 }

agPortNewCfgTableEntry OBJECT-TYPE
    SYNTAX  AgPortNewCfgTableEntry
    ACCESS  not-accessible
    STATUS  mandatory
    DESCRIPTION
        "A row in the port configuration table in the new_configuration block."
    INDEX   { agPortNewCfgIndx }
    ::= { agPortNewCfgTable 1 }

AgPortNewCfgTableEntry ::= SEQUENCE {
    agPortNewCfgIndx           INTEGER,
    agPortNewCfgState          INTEGER,
    agPortNewCfgVlanTag        INTEGER,
    agPortNewCfgStp            INTEGER,
    agPortNewCfgRmon           INTEGER,
    agPortNewCfgPVID           INTEGER,
    agPortNewCfgFastEthAutoNeg INTEGER,
    agPortNewCfgFastEthSpeed   INTEGER,
    agPortNewCfgFastEthMode    INTEGER,
    agPortNewCfgFastEthFctl    INTEGER,
    agPortNewCfgGigEthAutoNeg  INTEGER,
    agPortNewCfgGigEthFctl     INTEGER,
    agPortNewCfgPortName       DisplayString,
    agPortNewCfgBwmContract    INTEGER,
    agPortNewCfgDiscardNonIPs  INTEGER,
    agPortNewCfgLinkTrap       INTEGER
    }

agPortNewCfgIndx OBJECT-TYPE
    SYNTAX  INTEGER  (1..255)
    ACCESS  read-only
    STATUS  mandatory
    DESCRIPTION
        "The index of the row in port configurations table."
    ::= { agPortNewCfgTableEntry 1 }

agPortNewCfgState OBJECT-TYPE
    SYNTAX  INTEGER {
        enabled(2),
        disabled(3)
        }
    ACCESS  read-write
    STATUS  mandatory
    DESCRIPTION
        "This is the state of the port."
    ::= { agPortNewCfgTableEntry 2 }

agPortNewCfgVlanTag OBJECT-TYPE
    SYNTAX  INTEGER {
        tagged(2),
        untagged(3)
        }
    ACCESS  read-write
    STATUS  mandatory
    DESCRIPTION
        "This is VLAN tag state of the port"
    ::= { agPortNewCfgTableEntry 3 }

agPortNewCfgStp OBJECT-TYPE
    SYNTAX  INTEGER {
        on(2),
        off(3)
        }
    ACCESS  read-write
    STATUS  mandatory
    DESCRIPTION
        "This object is used to turn Spanning Tree on or off for the port."
    ::= { agPortNewCfgTableEntry 4 }

agPortNewCfgRmon OBJECT-TYPE
    SYNTAX  INTEGER {
        on(2),
        off(3)
        }
    ACCESS  read-write
    STATUS  mandatory
    DESCRIPTION
        "This object is used to turn RMON on or off on the port."
    ::= { agPortNewCfgTableEntry 5 }

agPortNewCfgPVID OBJECT-TYPE
    SYNTAX  INTEGER (1..4093)
    ACCESS  read-write
    STATUS  mandatory
    DESCRIPTION
        "The default VLAN ID for the port."
    ::= { agPortNewCfgTableEntry 6 }

agPortNewCfgFastEthAutoNeg OBJECT-TYPE
    SYNTAX  INTEGER {
        on(2),
        off(3)
        }
    ACCESS  read-write
    STATUS  mandatory
    DESCRIPTION
        "This object is used to turn the autonegotiation on or off
         for fast Ethernet connection."
    ::= { agPortNewCfgTableEntry 7 }

agPortNewCfgFastEthSpeed OBJECT-TYPE
    SYNTAX  INTEGER {
        mbs10(2),
        mbs100(3),
        mbs10or100(4)
        }
    ACCESS  read-write
    STATUS  mandatory
    DESCRIPTION
        "Selects the port speed for fast Ethernet connection."
    ::= { agPortNewCfgTableEntry 8 }
 
agPortNewCfgFastEthMode OBJECT-TYPE
    SYNTAX  INTEGER {
        full-duplex(2),
        half-duplex(3),
        full-or-half-duplex(4)
        }
    ACCESS  read-write
    STATUS  mandatory
    DESCRIPTION
        "This object is used to select port mode for fast Ethernet connection."
    ::= { agPortNewCfgTableEntry 9 }

agPortNewCfgFastEthFctl OBJECT-TYPE
    SYNTAX  INTEGER {
        transmit(2),
        receive(3),
        both(4),
        none(5)
        }
    ACCESS  read-write
    STATUS  mandatory
    DESCRIPTION
        "Selects the port flow control for fast Ethernet connection."
    ::= { agPortNewCfgTableEntry 10 }

agPortNewCfgGigEthAutoNeg OBJECT-TYPE
    SYNTAX  INTEGER {
        on(2),
        off(3)
        }
    ACCESS  read-write
    STATUS  mandatory
    DESCRIPTION
        "This object is used to turn the autonegotiation on or off
         for gigabit Ethernet connection."
    ::= { agPortNewCfgTableEntry 11 }

agPortNewCfgGigEthFctl OBJECT-TYPE
    SYNTAX  INTEGER {
        transmit(2),
        receive(3),
        both(4),
        none(5)
       }
    ACCESS  read-write
    STATUS  mandatory
    DESCRIPTION
        "This object is used to select port flow control for
         gigabit Ethernet connection."
    ::= { agPortNewCfgTableEntry 12 }

agPortNewCfgPortName	OBJECT-TYPE
    SYNTAX  DisplayString (SIZE(0..63))
    ACCESS  read-write
    STATUS  mandatory
    DESCRIPTION
        "The switch port name."
    ::= { agPortNewCfgTableEntry 13 }

agPortNewCfgBwmContract OBJECT-TYPE
    SYNTAX  INTEGER 
    ACCESS  read-write
    STATUS  mandatory
    DESCRIPTION
        "The switch port Bandwidth Management contract number."
    ::= { agPortNewCfgTableEntry 14 }

agPortNewCfgDiscardNonIPs OBJECT-TYPE
    SYNTAX  INTEGER {
        enabled(2),
        disabled(3)
        }
    ACCESS  read-write
    STATUS  mandatory
    DESCRIPTION
        "Enable or disable to discard all non-IP traffic on the switch port."
    ::= { agPortNewCfgTableEntry 15 }

agPortNewCfgLinkTrap OBJECT-TYPE
    SYNTAX  INTEGER {
	enabled(1),
	disabled(2)
    }
    ACCESS  read-write
    STATUS  mandatory 
    DESCRIPTION
        "Indicates whether linkUp/linkDown traps should be
        generated for this interface.

        By default, this object should have the value
        enabled(1) for interfaces which do not operate on
        'top' of any other interface (as defined in the
        ifStackTable), and disabled(2) otherwise."
    ::= { agPortNewCfgTableEntry 16 }

-- RADIUS Configuration 
 
radCurCfgPrimaryIpAddr OBJECT-TYPE
    SYNTAX  IpAddress
    ACCESS  read-only
    STATUS  mandatory
    DESCRIPTION
        "The IP address of the Primary RADIUS server."
    ::= { agRadiusConfig 1 }

radNewCfgPrimaryIpAddr OBJECT-TYPE
    SYNTAX  IpAddress
    ACCESS  read-write
    STATUS  mandatory
    DESCRIPTION
        "The IP address of the Primary RADIUS server."
    ::= { agRadiusConfig 2 }

radCurCfgSecondaryIpAddr OBJECT-TYPE
    SYNTAX  IpAddress
    ACCESS  read-only
    STATUS  mandatory
    DESCRIPTION
        "The IP address of the Secondary RADIUS server."
    ::= { agRadiusConfig 3 }

radNewCfgSecondaryIpAddr OBJECT-TYPE
    SYNTAX  IpAddress
    ACCESS  read-write
    STATUS  mandatory
    DESCRIPTION
        "The IP address of the Secondary RADIUS server."
    ::= { agRadiusConfig 4 }

radCurCfgPort OBJECT-TYPE
    SYNTAX  INTEGER  (1500..3000)
    ACCESS  read-only
    STATUS  mandatory
    DESCRIPTION
        "Specify the RADIUS port number."
    ::= { agRadiusConfig 5 }

radNewCfgPort OBJECT-TYPE
    SYNTAX  INTEGER  (1500..3000)
    ACCESS  read-write
    STATUS  mandatory
    DESCRIPTION
        "Speicfy the RADIUS port number."
    ::= { agRadiusConfig 6 }

radCurCfgTimeout OBJECT-TYPE
    SYNTAX  INTEGER  (1..10)
    ACCESS  read-only
    STATUS  mandatory
    DESCRIPTION
        "The maximum number of seconds before resending authentication
         to RADIUS server."
    ::= { agRadiusConfig 7 }

radNewCfgTimeout OBJECT-TYPE
    SYNTAX  INTEGER  (1..10)
    ACCESS  read-write
    STATUS  mandatory
    DESCRIPTION
        "The maximum number of seconds before resending authentication
         to RADIUS server."
    ::= { agRadiusConfig 8 }

radCurCfgRetries OBJECT-TYPE
    SYNTAX  INTEGER  (1..3)
    ACCESS  read-only
    STATUS  mandatory
    DESCRIPTION
        "Number of retries to the RADIUS server."
    ::= { agRadiusConfig 9 }

radNewCfgRetries OBJECT-TYPE
    SYNTAX  INTEGER  (1..3)
    ACCESS  read-write
    STATUS  mandatory
    DESCRIPTION
        "Number of retries to the RADIUS server."
    ::= { agRadiusConfig 10 }

radCurCfgState OBJECT-TYPE
    SYNTAX  INTEGER {
        enabled(2),
        disabled(3)
        }
    ACCESS  read-only
    STATUS  mandatory
    DESCRIPTION
        "Enable or disbale RADIUS authentication."
    ::= { agRadiusConfig 11 }

radNewCfgState OBJECT-TYPE
    SYNTAX  INTEGER {
        enabled(2),
        disabled(3)
        }
    ACCESS  read-write
    STATUS  mandatory
    DESCRIPTION
        "Enable or disable RADIUS authentication."
    ::= { agRadiusConfig 12 }

radCurCfgAuthenString OBJECT-TYPE
    SYNTAX  DisplayString (SIZE(0..32))
    ACCESS  read-only
    STATUS  mandatory
    DESCRIPTION
        "The RADIUS authentication string."
    ::= { agRadiusConfig 13 }

radNewCfgAuthenString OBJECT-TYPE
    SYNTAX  DisplayString (SIZE(0..32))
    ACCESS  read-write
    STATUS  mandatory
    DESCRIPTION
        "The RADIUS authentication string."
    ::= { agRadiusConfig 14 }

radCurCfgTelnet OBJECT-TYPE
    SYNTAX  INTEGER {
        enabled(1),
        disabled(2)
        }
    ACCESS  read-only
    STATUS  mandatory
    DESCRIPTION
        "Enable or disbale RADIUS backdoor for telnet."
    ::= { agRadiusConfig 15 }

radNewCfgTelnet OBJECT-TYPE
    SYNTAX  INTEGER {
        enabled(1),
        disabled(2)
        }
    ACCESS  read-write
    STATUS  mandatory
    DESCRIPTION
        "Enable or disable RADIUS backdoor for telnet."
    ::= { agRadiusConfig 16 }

-- NTP Configuration 
agCurCfgNTPServer OBJECT-TYPE
    SYNTAX  IpAddress
    ACCESS  read-only
    STATUS  mandatory
    DESCRIPTION
        "The NTP Server Address."
    ::= { agNTP 1 }

agNewCfgNTPServer OBJECT-TYPE
    SYNTAX  IpAddress
    ACCESS  read-write
    STATUS  mandatory
    DESCRIPTION
        "The NTP Server Address."
    ::= { agNTP 2 }

agCurCfgNTPResyncInterval OBJECT-TYPE
    SYNTAX  INTEGER (1..2880)
    ACCESS  read-only
    STATUS  mandatory
    DESCRIPTION
        "The NTP Server resync interval in minutes."
    ::= { agNTP 3 }

agNewCfgNTPResyncInterval OBJECT-TYPE
    SYNTAX  INTEGER (1..2880)
    ACCESS  read-write
    STATUS  mandatory
    DESCRIPTION
        "The NTP Server resync interval in minutes."
    ::= { agNTP 4 }

agCurCfgNTPTzoneHHMM OBJECT-TYPE
    SYNTAX  DisplayString (SIZE(0..6))
    ACCESS  read-only
    STATUS  mandatory
    DESCRIPTION
        "The NTP Server timezone offset from GMT formatted as (+/-)HH:MM."
    ::= { agNTP 5 }

agNewCfgNTPTzoneHHMM OBJECT-TYPE
    SYNTAX  DisplayString (SIZE(0..6))
    ACCESS  read-write
    STATUS  mandatory
    DESCRIPTION
        "The NTP Server timezone offset from GMT formatted as (+/-)HH:MM.
         The valid range is from -12:59 to +12:59."
    ::= { agNTP 6 }

agCurCfgNTPDlight OBJECT-TYPE
    SYNTAX  INTEGER {
        enabled(1),
        disabled(2)
        }
    ACCESS  read-only
    STATUS  mandatory
    DESCRIPTION
        "Enable/disable daylight savings time."
    ::= { agNTP 7 }

agNewCfgNTPDlight OBJECT-TYPE
    SYNTAX  INTEGER {
        enabled(1),
        disabled(2)
        }
    ACCESS  read-write
    STATUS  mandatory
    DESCRIPTION
        "Enable/disable daylight savings time."
    ::= { agNTP 8 }

agCurCfgNTPService OBJECT-TYPE
    SYNTAX  INTEGER {
        enabled(1),
        disabled(2)
        }
    ACCESS  read-only
    STATUS  mandatory
    DESCRIPTION
        "Enable/disable NTP Service."
    ::= { agNTP 9 }

agNewCfgNTPService OBJECT-TYPE
    SYNTAX  INTEGER {
        enabled(1),
        disabled(2)
        }
    ACCESS  read-write
    STATUS  mandatory
    DESCRIPTION
        "Enable/disable NTP Service."
    ::= { agNTP 10 }

-- APPLY Configuration
agApplyPending OBJECT-TYPE
    SYNTAX  INTEGER {
        applyNeeded(2),
        noApplyNeeded(3)
        }
    ACCESS  read-only
    STATUS  mandatory
    DESCRIPTION
        "This object, when read, gives the user information
         whether an apply action is needed and that the configuration
         has been chaged by the user actions. The user then can
         apply the changes by setting proper value to the object
         agApplyConfiguration described above."
    ::= { agApply 1 }

agApplyConfig OBJECT-TYPE
    SYNTAX  INTEGER {
        apply(1), 
        idle(2),
        inprogress(3),
        complete(4),
        failed(5)
        }
    ACCESS  read-write
    STATUS  mandatory
    DESCRIPTION
         "When this object is read the current state is returned.
          idle(3) indicates that there is no apply in progess.
          complete(5) indicates that the last apply operation is completed.
          Setting the value to apply(1), will write all the changes made
          since the last apply to the current configuration block.
	  If the apply is successful this variable will return the state
          'complete' else it will return 'failed'. In case of failure,
          to read the reason for failure use the agApplyTable.
          Once the operation is completed or the agApplyTable is read in case
          of failure, the apply buffer needs to be freed and the agApplyState 
          should be set back to 'idle' state so others can issue the apply 
          command via SNMP."
    ::= { agApply 2 }

agApplyTableSize OBJECT-TYPE
    SYNTAX  INTEGER
    ACCESS  read-only
    STATUS  mandatory
    DESCRIPTION
        "The number of strings in the apply table."
    ::= { agApply 4 }

agApplyTable OBJECT-TYPE
    SYNTAX  SEQUENCE OF AgApplyTableEntry
    ACCESS  not-accessible
    STATUS  mandatory
    DESCRIPTION
        "The table of URL path for URL load balancing in the current_config."
    ::= { agApply 5 }

agApplyTableEntry OBJECT-TYPE
    SYNTAX  AgApplyTableEntry
    ACCESS  not-accessible
    STATUS  mandatory
    DESCRIPTION
        "Information about an URL path for URL load balancing."
    INDEX   { agApplyIndex }
    ::= { agApplyTable 1 }

AgApplyTableEntry ::= SEQUENCE {
    agApplyIndex      INTEGER,
    agApplyString     OCTET STRING
    }

agApplyIndex OBJECT-TYPE
    SYNTAX  INTEGER
    ACCESS  read-only
    STATUS  mandatory
    DESCRIPTION
        "The table index."
    ::= { agApplyTableEntry 1 }

agApplyString OBJECT-TYPE
    SYNTAX  OCTET STRING
    ACCESS  read-only
    STATUS  mandatory
    DESCRIPTION
        "A string in the apply table."
    ::= { agApplyTableEntry 2 }

-- Mgmt Port Config

agMgmtCurCfgIpAddr OBJECT-TYPE
    SYNTAX  IpAddress
    ACCESS  read-only
    STATUS  mandatory
    DESCRIPTION
        "The IP address of the management port."
    ::= { agMgmt 1 }

agMgmtNewCfgIpAddr OBJECT-TYPE
    SYNTAX  IpAddress
    ACCESS  read-write
    STATUS  mandatory
    DESCRIPTION
        "The IP address of the management port."
    ::= { agMgmt 2 }

agMgmtCurCfgMask OBJECT-TYPE
    SYNTAX  IpAddress
    ACCESS  read-only
    STATUS  mandatory
    DESCRIPTION
        "The subnet mask of the management port."
    ::= { agMgmt 3 }

agMgmtNewCfgMask OBJECT-TYPE
    SYNTAX  IpAddress
    ACCESS  read-write
    STATUS  mandatory
    DESCRIPTION
        "The subnet mask of the management port."
    ::= { agMgmt 4 }

agMgmtCurCfgBroadcast OBJECT-TYPE
    SYNTAX  IpAddress
    ACCESS  read-only
    STATUS  mandatory
    DESCRIPTION
        "The broadcast address of the management port."
    ::= { agMgmt 5 }

agMgmtNewCfgBroadcast OBJECT-TYPE
    SYNTAX  IpAddress
    ACCESS  read-write
    STATUS  mandatory
    DESCRIPTION
        "The broadcast address of the management port."
    ::= { agMgmt 6 }

agMgmtCurCfgGateway OBJECT-TYPE
    SYNTAX  IpAddress
    ACCESS  read-only
    STATUS  mandatory
    DESCRIPTION
        "The default gateway for the management port."
    ::= { agMgmt 7 }

agMgmtNewCfgGateway OBJECT-TYPE
    SYNTAX  IpAddress
    ACCESS  read-write
    STATUS  mandatory
    DESCRIPTION
        "The default gateway for the management port."
    ::= { agMgmt 8 }

agMgmtCurCfgState OBJECT-TYPE
    SYNTAX  INTEGER {
        enabled(1),
        disabled(2)
        }
    ACCESS  read-only
    STATUS  mandatory
    DESCRIPTION
        "Enable/disable management port."
   ::= { agMgmt 9 } 

agMgmtNewCfgState OBJECT-TYPE
    SYNTAX  INTEGER {
        enabled(1),
        disabled(2)
        }
    ACCESS  read-write
    STATUS  mandatory
    DESCRIPTION
        "Enable/disable management port."
   ::= { agMgmt 10 } 

agMgmtCurCfgNtp OBJECT-TYPE
    SYNTAX  INTEGER {
        data(1),
        mgmt(2)
        }
    ACCESS  read-only
    STATUS  mandatory
    DESCRIPTION
        "Specifies NTP access is over management port or data port."
   ::= { agMgmt 11 } 

agMgmtNewCfgNtp OBJECT-TYPE
    SYNTAX  INTEGER {
        data(1),
        mgmt(2)
        }
    ACCESS  read-write
    STATUS  mandatory
    DESCRIPTION
        "Specifies NTP access is over management port or data port."
   ::= { agMgmt 12 } 

agMgmtCurCfgRadius OBJECT-TYPE
    SYNTAX  INTEGER {
        data(1),
        mgmt(2)
        }
    ACCESS  read-only
    STATUS  mandatory
    DESCRIPTION
        "Specifies RADIUS server access is over management port or data port."
   ::= { agMgmt 13 } 

agMgmtNewCfgRadius OBJECT-TYPE
    SYNTAX  INTEGER {
        data(1),
        mgmt(2)
        }
    ACCESS  read-write
    STATUS  mandatory
    DESCRIPTION
        "Specifies RADIUS server access is over management port or data port."
   ::= { agMgmt 14 } 

agMgmtCurCfgSmtp OBJECT-TYPE
    SYNTAX  INTEGER {
        data(1),
        mgmt(2)
        }
    ACCESS  read-only
    STATUS  mandatory
    DESCRIPTION
        "Specifies SMTP access is over management port or data port."
   ::= { agMgmt 15 } 

agMgmtNewCfgSmtp OBJECT-TYPE
    SYNTAX  INTEGER {
        data(1),
        mgmt(2)
        }
    ACCESS  read-write
    STATUS  mandatory
    DESCRIPTION
        "Specifies SMTP access is over management port or data port."
   ::= { agMgmt 16 } 

agMgmtCurCfgSnmp OBJECT-TYPE
    SYNTAX  INTEGER {
        data(1),
        mgmt(2)
        }
    ACCESS  read-only
    STATUS  mandatory
    DESCRIPTION
        "Specifies SNMP trap host access is over management port or data port."
   ::= { agMgmt 17 } 

agMgmtNewCfgSnmp OBJECT-TYPE
    SYNTAX  INTEGER {
        data(1),
        mgmt(2)
        }
    ACCESS  read-write
    STATUS  mandatory
    DESCRIPTION
        "Specifies SNMP trap host access is over management port or data port."
   ::= { agMgmt 18 } 

agMgmtCurCfgSyslog OBJECT-TYPE
    SYNTAX  INTEGER {
        data(1),
        mgmt(2)
        }
    ACCESS  read-only
    STATUS  mandatory
    DESCRIPTION
        "Specifies syslog host access is over management port or data port."
   ::= { agMgmt 19 } 

agMgmtNewCfgSyslog OBJECT-TYPE
    SYNTAX  INTEGER {
        data(1),
        mgmt(2)
        }
    ACCESS  read-write
    STATUS  mandatory
    DESCRIPTION
        "Specifies syslog host access is over management port or data port."
   ::= { agMgmt 20 } 

agMgmtCurCfgTftp OBJECT-TYPE
    SYNTAX  INTEGER {
        data(1),
        mgmt(2)
        }
    ACCESS  read-only
    STATUS  mandatory
    DESCRIPTION
        "Specifies TFTP access is over management port or data port."
   ::= { agMgmt 21 } 

agMgmtNewCfgTftp OBJECT-TYPE
    SYNTAX  INTEGER {
        data(1),
        mgmt(2)
        }
    ACCESS  read-write
    STATUS  mandatory
    DESCRIPTION
        "Specifies TFTP access is over management port or data port."
   ::= { agMgmt 22 } 

agMgmtCurCfgDns OBJECT-TYPE
    SYNTAX  INTEGER {
        data(1),
        mgmt(2)
        }
    ACCESS  read-only
    STATUS  mandatory
    DESCRIPTION
        "Specifies DNS access is over management port or data port."
   ::= { agMgmt 24 } 

agMgmtNewCfgDns OBJECT-TYPE
    SYNTAX  INTEGER {
        data(1),
        mgmt(2)
        }
    ACCESS  read-write
    STATUS  mandatory
    DESCRIPTION
        "Specifies DNS access is over management port or data port."
   ::= { agMgmt 25 } 

agMgmtPort   OBJECT IDENTIFIER ::= { agMgmt 23 }

agMgmtPortCurCfgSpeed OBJECT-TYPE
    SYNTAX  INTEGER {
        mbs10(1),
        mbs100(2),
        any(3)
        }
    ACCESS  read-only
    STATUS  mandatory
    DESCRIPTION
        "Set Management port link speed."
   ::= { agMgmtPort 1 } 

agMgmtPortNewCfgSpeed OBJECT-TYPE
    SYNTAX  INTEGER {
        mbs10(1),
        mbs100(2),
        any(3)
        }
    ACCESS  read-write
    STATUS  mandatory
    DESCRIPTION
        "Set Management port link speed."
   ::= { agMgmtPort 2 } 

agMgmtPortCurCfgMode OBJECT-TYPE
    SYNTAX  INTEGER {
        full(1),
        half(2),
        any(3)
        }
    ACCESS  read-only
    STATUS  mandatory
    DESCRIPTION
        "Set Management port full or half duplex mode."
   ::= { agMgmtPort 3 } 

agMgmtPortNewCfgMode OBJECT-TYPE
    SYNTAX  INTEGER {
        full(1),
        half(2),
        any(3)
        }
    ACCESS  read-write
    STATUS  mandatory
    DESCRIPTION
        "Set Management port full or half duplex mode."
   ::= { agMgmtPort 4 } 

agMgmtPortCurCfgAuto OBJECT-TYPE
    SYNTAX  INTEGER {
        on(1),
        off(2)
        }
    ACCESS  read-only
    STATUS  mandatory
    DESCRIPTION
        "Set Management port autonegotiation."
   ::= { agMgmtPort 5 } 

agMgmtPortNewCfgAuto OBJECT-TYPE
    SYNTAX  INTEGER {
        on(1),
        off(2)
        }
    ACCESS  read-write
    STATUS  mandatory
    DESCRIPTION
        "Set Management port autonegotiation."
   ::= { agMgmtPort 6 } 

-- Statistics Group

-- Packet Statistics Group
-- This group represents Packet Statistics information
 
pktStatsAllocs OBJECT-TYPE
    SYNTAX  Counter
    ACCESS  read-only
    STATUS  mandatory
    DESCRIPTION
        "Total number of packet allocations from the packet buffer pool by 
         the TCP/IP protocol stack."
    ::= { pktStats 1 }
 
pktStatsFrees OBJECT-TYPE
    SYNTAX  Counter
    ACCESS  read-only
    STATUS  mandatory
    DESCRIPTION
        "Total number of times the packet buffers are freed(released) to the
         packet buffer pool by the TCP/IP protocol stack."
    ::= { pktStats 2 }
 
pktStatsAllocFails OBJECT-TYPE
    SYNTAX  Counter
    ACCESS  read-only
    STATUS  mandatory
    DESCRIPTION
        "Total number of packet allocation failures from the packet buffer 
         pool by the TCP/IP protocol stack."
    ::= { pktStats 3}
 
pktStatsMediums OBJECT-TYPE
    SYNTAX  Gauge
    ACCESS  read-only
    STATUS  mandatory
    DESCRIPTION
        "Total number of packet allocations with size greater than 128 bytes
         and less than or equal to 1536 bytes from the packet buffer pool by 
         the TCP/IP protocol stack."
    ::= { pktStats 4}

pktStatsJumbos OBJECT-TYPE
    SYNTAX  Gauge
    ACCESS  read-only
    STATUS  mandatory
    DESCRIPTION
        "Total number of packet allocations with size larger than 1536 bytes 
         from the packet buffer pool by the TCP/IP protocol stack."
    ::= { pktStats 5}
 
pktStatsSmalls OBJECT-TYPE
    SYNTAX  Gauge
    ACCESS  read-only
    STATUS  mandatory
    DESCRIPTION
        "Total number of packet allocations with size less than or eqaul to 
         128 bytes from the packet buffer pool by the TCP/IP protocol stack."
    ::= { pktStats 6}

pktStatsMediumsHiWatermark OBJECT-TYPE
    SYNTAX  Counter
    ACCESS  read-only
    STATUS  mandatory
    DESCRIPTION
        "The highest number of packet allocations with size greater than 
         128 bytes and less than or equal to 1536 bytes from the packet 
         buffer pool by the TCP/IP protocol stack."
    ::= { pktStats 7}

pktStatsJumbosHiWatermark OBJECT-TYPE
    SYNTAX  Counter
    ACCESS  read-only
    STATUS  mandatory
    DESCRIPTION
        "The highest number of packet allocations with size larger than 
         1536 bytes from the packet buffer pool by the TCP/IP protocol stack."
    ::= { pktStats 8}

pktStatsSmallsHiWatermark OBJECT-TYPE
    SYNTAX  Counter
    ACCESS  read-only
    STATUS  mandatory
    DESCRIPTION
        "The highest number of packet allocations with size less than or 
         eqaul to 128 bytes from the packet buffer pool by the TCP/IP 
         protocol stack."
    ::= { pktStats 9}

pktStatsDiscards OBJECT-TYPE
    SYNTAX  Counter
    ACCESS  read-only
    STATUS  mandatory
    DESCRIPTION
        "The total number of packets which were chosen to be discarded because 
         the number of buffers available in the packet buffer pool is low."
    ::= { pktStats 10}
 
-- MP CPU Statisitics Group
 
mpCpuStatsUtil1Second OBJECT-TYPE
    SYNTAX  INTEGER 
    ACCESS  read-only
    STATUS  mandatory
    DESCRIPTION
        "The utilization of MP CPU over 1 second. It shows the percentage."
    ::= { mpCpuStats 1}
 
mpCpuStatsUtil4Seconds OBJECT-TYPE
    SYNTAX  INTEGER 
    ACCESS  read-only
    STATUS  mandatory
    DESCRIPTION
        "The utilization of MP CPU  over 4 seconds. 
	 It shows the percentage."
    ::= { mpCpuStats 2}
 
mpCpuStatsUtil64Seconds OBJECT-TYPE
    SYNTAX  INTEGER 
    ACCESS  read-only
    STATUS  mandatory
    DESCRIPTION
        "The utilization of MP CPU over 64 seconds. 
	 It shows the percentage."
    ::= { mpCpuStats 3}
 
--
-- Port statistics table
--
portStatsTable OBJECT-TYPE
    SYNTAX  SEQUENCE OF PortStatsTableEntry
    ACCESS  not-accessible
    STATUS  mandatory
    DESCRIPTION
        "The table of port statistics."
    ::= { portStats 1 }

portStatsTableEntry OBJECT-TYPE
    SYNTAX  PortStatsTableEntry
    ACCESS  not-accessible
    STATUS  mandatory
    DESCRIPTION
        "A row in the port stats table."
    INDEX   { portStatsIndx }
    ::= { portStatsTable 1 }

PortStatsTableEntry ::=
    SEQUENCE {
	portStatsIndx
	    INTEGER,
	portStatsPhyIfInOctets
	    Counter,
	portStatsPhyIfInUcastPkts
	    Counter,
	portStatsPhyIfInNUcastPkts
	    Counter,
	portStatsPhyIfInDiscards
	    Counter,
	portStatsPhyIfInErrors
	    Counter,
	portStatsPhyIfInUnknownProtos
	    Counter,
	portStatsPhyIfOutOctets
	    Counter,
	portStatsPhyIfOutUcastPkts
	    Counter,
	portStatsPhyIfOutNUcastPkts
	    Counter,
	portStatsPhyIfOutDiscards
	    Counter,
	portStatsPhyIfOutErrors
	    Counter,
	portStatsPhyIfOutQLen
	    Gauge,
        portStatsPhyIfInBroadcastPkts
            Counter,
        portStatsPhyIfOutBroadcastPkts
            Counter,
	portStatsClear
            INTEGER
    }

portStatsIndx OBJECT-TYPE
    SYNTAX  INTEGER  (1..255)
    ACCESS  read-only
    STATUS  mandatory
    DESCRIPTION
        "The port index."
    ::= { portStatsTableEntry 1 }

portStatsPhyIfInOctets OBJECT-TYPE
    SYNTAX  Counter
    ACCESS  read-only
    STATUS  mandatory
    DESCRIPTION
	    "The total number of octets received on the
	    interface, including framing characters."
    ::= { portStatsTableEntry 2 }

portStatsPhyIfInUcastPkts OBJECT-TYPE
    SYNTAX  Counter
    ACCESS  read-only
    STATUS  mandatory
    DESCRIPTION
	    "The number of subnetwork-unicast packets
	    delivered to a higher-layer protocol."
    ::= { portStatsTableEntry 3 }

portStatsPhyIfInNUcastPkts OBJECT-TYPE
    SYNTAX  Counter
    ACCESS  read-only
    STATUS  mandatory
    DESCRIPTION
	    "The number of non-unicast (i.e., subnetwork-
	    broadcast or subnetwork-multicast) packets
	    delivered to a higher-layer protocol."
    ::= { portStatsTableEntry 4 }

portStatsPhyIfInDiscards OBJECT-TYPE
    SYNTAX  Counter
    ACCESS  read-only
    STATUS  mandatory
    DESCRIPTION
	    "The number of inbound packets which were chosen
	    to be discarded even though no errors had been
	    detected to prevent their being deliverable to a
	    higher-layer protocol.  One possible reason for
	    discarding such a packet could be to free up
	    buffer space."
    ::= { portStatsTableEntry 5 }

portStatsPhyIfInErrors OBJECT-TYPE
    SYNTAX  Counter
    ACCESS  read-only
    STATUS  mandatory
    DESCRIPTION
	    "The number of inbound packets that contained
	    errors preventing them from being deliverable to a
	    higher-layer protocol."
    ::= { portStatsTableEntry 6 }

portStatsPhyIfInUnknownProtos OBJECT-TYPE
    SYNTAX  Counter
    ACCESS  read-only
    STATUS  mandatory
    DESCRIPTION
	    "The number of packets received via the interface
	    which were discarded because of an unknown or
	    unsupported protocol."
    ::= { portStatsTableEntry 7 }

portStatsPhyIfOutOctets OBJECT-TYPE
    SYNTAX  Counter
    ACCESS  read-only
    STATUS  mandatory
    DESCRIPTION
	    "The total number of octets transmitted out of the
	    interface, including framing characters."
    ::= { portStatsTableEntry 8 }

portStatsPhyIfOutUcastPkts OBJECT-TYPE
    SYNTAX  Counter
    ACCESS  read-only
    STATUS  mandatory
    DESCRIPTION
	    "The total number of packets that higher-level
	    protocols requested be transmitted to a
	    subnetwork-unicast address, including those that
	    were discarded or not sent."
    ::= { portStatsTableEntry 9 }

portStatsPhyIfOutNUcastPkts OBJECT-TYPE
    SYNTAX  Counter
    ACCESS  read-only
    STATUS  mandatory
    DESCRIPTION
	    "The total number of packets that higher-level
	    protocols requested be transmitted to a non-
	    unicast (i.e., a subnetwork-broadcast or
	    subnetwork-multicast) address, including those
	    that were discarded or not sent."
    ::= { portStatsTableEntry 10 }

portStatsPhyIfOutDiscards OBJECT-TYPE
    SYNTAX  Counter
    ACCESS  read-only
    STATUS  mandatory
    DESCRIPTION
	    "The number of outbound packets which were chosen
	    to be discarded even though no errors had been
	    detected to prevent their being transmitted.  One
	    possible reason for discarding such a packet could
	    be to free up buffer space."
    ::= { portStatsTableEntry 11 }

portStatsPhyIfOutErrors OBJECT-TYPE
    SYNTAX  Counter
    ACCESS  read-only
    STATUS  mandatory
    DESCRIPTION
	    "The number of outbound packets that could not be
	    transmitted because of errors."
    ::= { portStatsTableEntry 12 }

portStatsPhyIfOutQLen OBJECT-TYPE
    SYNTAX  Gauge
    ACCESS  read-only
    STATUS  mandatory
    DESCRIPTION
	    "The length of the output packet queue (in
	    packets)."
    ::= { portStatsTableEntry 13 }

portStatsPhyIfInBroadcastPkts OBJECT-TYPE
    SYNTAX  Counter
    ACCESS  read-only
    STATUS  mandatory 
    DESCRIPTION
            "The number of packets, delivered by this sub-layer to
            a higher (sub-)layer, which were addressed to a
            broadcast address at this sub-layer."
    ::= { portStatsTableEntry 14 }

portStatsPhyIfOutBroadcastPkts OBJECT-TYPE
    SYNTAX  Counter
    ACCESS  read-only
    STATUS  mandatory 
    DESCRIPTION
	    "The total number of packets that higher-level
            protocols requested be transmitted, and which were
            addressed to a broadcast address at this sub-layer,
            including those that were discarded or not sent."
    ::= { portStatsTableEntry 15 }

portStatsClear OBJECT-TYPE
    SYNTAX  INTEGER {
        ok(1),
        clear(2)
        }
    ACCESS  read-write
    STATUS  mandatory 
    DESCRIPTION
	    "Setting this value to clear(2) clears the stats for this port."
    ::= { portStatsTableEntry 16 }

agDiffState OBJECT-TYPE
    SYNTAX  INTEGER {
        diff(1), 
        flashdiff(2),
        idle(3),
        inprogress(4),
        complete(5)
        }
    ACCESS  read-write
    STATUS  mandatory
    DESCRIPTION
         "When this object is read the current state is returned.
          idle(3) indicates that there is no diff in progess.
          complete(5) indicates that the last diff operation is completed.
          Setting the value to diff(1), will start a new diff operation
          Diff compares the new configuration with the current configuration
          and shows the pending configuration changes. 
          Setting the value to flashdiff(1), will start a new diff operation.
          flashdiff compares new configuration with the flash configuration.
          To read the configuration changes use the agDiffTable once the
          state of this variable returns complete.
          Once the agDiffTable is read the state should be set back to 'idle'
          which frees the diff buffer and others can issue a diff command via
          SNMP."
    ::= { agDiff 2 }

agDiffTableSize OBJECT-TYPE
    SYNTAX  INTEGER
    ACCESS  read-only
    STATUS  mandatory
    DESCRIPTION
        "The number of strings in the diff table."
    ::= { agDiff 3 }

agDiffTable OBJECT-TYPE
    SYNTAX  SEQUENCE OF AgDiffTableEntry
    ACCESS  not-accessible
    STATUS  mandatory
    DESCRIPTION
        "The table of diff strings."
    ::= { agDiff 4 }

agDiffTableEntry OBJECT-TYPE
    SYNTAX  AgDiffTableEntry
    ACCESS  not-accessible
    STATUS  mandatory
    DESCRIPTION
        "An entry in the diff table."
    INDEX   { agDiffIndex }
    ::= { agDiffTable 1 }

AgDiffTableEntry ::= SEQUENCE {
    agDiffIndex      INTEGER,
    agDiffString     OCTET STRING
    }

agDiffIndex OBJECT-TYPE
    SYNTAX  INTEGER
    ACCESS  read-only
    STATUS  mandatory
    DESCRIPTION
        "The table index."
    ::= { agDiffTableEntry 1 }

agDiffString OBJECT-TYPE
    SYNTAX  OCTET STRING
    ACCESS  read-only
    STATUS  mandatory
    DESCRIPTION
        "A string in the diff table."
    ::= { agDiffTableEntry 2 }

-- Config Dump 
agCfgDumpState OBJECT-TYPE
    SYNTAX  INTEGER {
        dump(1), 
        idle(2),
        inprogress(3),
        complete(4)
        }
    ACCESS  read-write
    STATUS  mandatory
    DESCRIPTION
         "When this object is read the current state is returned.
          idle(2) indicates that there is no dump in progess.
          complete(4) indicates that the last dump operation is completed.
          Setting the value to dump(1), will start a new dump operation
          Dump will show the current configuration.
          To read the configuration dump use the agCfgDumpTable once the
          state of this variable returns complete.
          Once the agCfgDumpTable is read the state should be set back to 
          'idle' which frees the dump buffer and others can issue a dump 
          command via SNMP."
    ::= { agCfgDump 2 }

agCfgDumpTableSize OBJECT-TYPE
    SYNTAX  INTEGER
    ACCESS  read-only
    STATUS  mandatory
    DESCRIPTION
        "The number of strings in the dump table."
    ::= { agCfgDump 3 }

agCfgDumpTable OBJECT-TYPE
    SYNTAX  SEQUENCE OF AgCfgDumpTableEntry
    ACCESS  not-accessible
    STATUS  mandatory
    DESCRIPTION
        "The table of dump strings."
    ::= { agCfgDump 4 }

agCfgDumpTableEntry OBJECT-TYPE
    SYNTAX  AgCfgDumpTableEntry
    ACCESS  not-accessible
    STATUS  mandatory
    DESCRIPTION
        "An entry in the dump table."
    INDEX   { agCfgDumpIndex }
    ::= { agCfgDumpTable 1 }

AgCfgDumpTableEntry ::= SEQUENCE {
    agCfgDumpIndex      INTEGER,
    agCfgDumpString     OCTET STRING
    }

agCfgDumpIndex OBJECT-TYPE
    SYNTAX  INTEGER
    ACCESS  read-only
    STATUS  mandatory
    DESCRIPTION
        "The table index."
    ::= { agCfgDumpTableEntry 1 }

agCfgDumpString OBJECT-TYPE
    SYNTAX  OCTET STRING
    ACCESS  read-only
    STATUS  mandatory
    DESCRIPTION
        "A string in the dump table."
    ::= { agCfgDumpTableEntry 2 }

-- SP Statistics 

-- SP CPU utilization table

spStatsCpuUtilTable OBJECT-TYPE
    SYNTAX  SEQUENCE OF SpStatsCpuUtilTableEntry 
    ACCESS  not-accessible
    STATUS  mandatory
    DESCRIPTION
        "The table of SP CPU utilization."
    ::= { spStats 1 }

spStatsCpuUtilTableEntry OBJECT-TYPE
    SYNTAX  SpStatsCpuUtilTableEntry
    ACCESS  not-accessible
    STATUS  mandatory
    DESCRIPTION
        "A row in the SP CPU utilization table."
    INDEX   { spStatsCpuUtilSpIndex }
    ::= { spStatsCpuUtilTable 1 }

SpStatsCpuUtilTableEntry ::= SEQUENCE {
    spStatsCpuUtilSpIndex    INTEGER,
    spStatsCpuUtil1Second    INTEGER,
    spStatsCpuUtil4Seconds   INTEGER,
    spStatsCpuUtil64Seconds  INTEGER
    }

spStatsCpuUtilSpIndex OBJECT-TYPE
    SYNTAX  INTEGER
    ACCESS  read-only
    STATUS  mandatory
    DESCRIPTION
        "The SP index."
    ::= { spStatsCpuUtilTableEntry 1 }

spStatsCpuUtil1Second OBJECT-TYPE
    SYNTAX  INTEGER 
    ACCESS  read-only
    STATUS  mandatory
    DESCRIPTION
        "The utilization of this SP over 1 second. It shows the percentage."
    ::= { spStatsCpuUtilTableEntry 2 }
 
spStatsCpuUtil4Seconds OBJECT-TYPE
    SYNTAX  INTEGER 
    ACCESS  read-only
    STATUS  mandatory
    DESCRIPTION
        "The utilization of this SP over 4 seconds. It shows the percentage."
    ::= { spStatsCpuUtilTableEntry 3 }
 
spStatsCpuUtil64Seconds OBJECT-TYPE
    SYNTAX  INTEGER 
    ACCESS  read-only
    STATUS  mandatory
    DESCRIPTION
        "The utilization of this SP over 64 seconds. It shows the percentage."
    ::= { spStatsCpuUtilTableEntry 4 }

-- SP Maintenance Statistics

spMaintStatsTable OBJECT-TYPE
    SYNTAX  SEQUENCE OF SpMaintStatsTableEntry 
    ACCESS  not-accessible
    STATUS  mandatory
    DESCRIPTION
        "The table of SP maintenance statistics."
    ::= { spStats 2 }

spMaintStatsTableEntry OBJECT-TYPE
    SYNTAX  SpMaintStatsTableEntry
    ACCESS  not-accessible
    STATUS  mandatory
    DESCRIPTION
        "A row in the SP maintenance statistics table."
    INDEX   { spMaintStatsSpIndex }
    ::= { spMaintStatsTable 1 }

SpMaintStatsTableEntry ::= SEQUENCE {
    spMaintStatsSpIndex           INTEGER,
    spMaintStatsPfdbFreeEmpty     Counter,
    spMaintStatsResolveErrNoddw   Counter,
    spMaintStatsLearnErrNoddw     Counter,
    spMaintStatsAgeMPNoddw        Counter,
    spMaintStatsDeleteMiss        Counter,
    spMaintStatsRecvLetErrorsMP   Counter,
    spMaintStatsRecvLetErrorsSP1  Counter,
    spMaintStatsRecvLetErrorsSP2  Counter,
    spMaintStatsRecvLetErrorsSP3  Counter,
    spMaintStatsRecvLetErrorsSP4  Counter,
    spMaintStatsSendLetFailsMP    Counter,
    spMaintStatsSendLetFailsSP1   Counter,
    spMaintStatsSendLetFailsSP2   Counter,
    spMaintStatsSendLetFailsSP3   Counter,
    spMaintStatsSendLetFailsSP4   Counter,
    spMaintStatsRecvLetSuccessMP  Counter,
    spMaintStatsRecvLetSuccessSP1 Counter,
    spMaintStatsRecvLetSuccessSP2 Counter,
    spMaintStatsRecvLetSuccessSP3 Counter,
    spMaintStatsRecvLetSuccessSP4 Counter,
    spMaintStatsSendLetSuccessMP  Counter,
    spMaintStatsSendLetSuccessSP1 Counter,
    spMaintStatsSendLetSuccessSP2 Counter,
    spMaintStatsSendLetSuccessSP3 Counter,
    spMaintStatsSendLetSuccessSP4 Counter
    }

spMaintStatsSpIndex OBJECT-TYPE
    SYNTAX  INTEGER
    ACCESS  read-only
    STATUS  mandatory
    DESCRIPTION
        "The SP index."
    ::= { spMaintStatsTableEntry 1 }

spMaintStatsPfdbFreeEmpty OBJECT-TYPE
    SYNTAX  Counter
    ACCESS  read-only
    STATUS  mandatory
    DESCRIPTION
        "The number of times the attempts were made to add entries to an
         already full FDB."
    ::= { spMaintStatsTableEntry 2 }

spMaintStatsResolveErrNoddw OBJECT-TYPE
    SYNTAX  Counter
    ACCESS  read-only
    STATUS  mandatory
    DESCRIPTION
        "The number of times MAC address resolution failed because there were
         no DMA descriptors."
    ::= { spMaintStatsTableEntry 3 }

spMaintStatsLearnErrNoddw OBJECT-TYPE
    SYNTAX  Counter
    ACCESS  read-only
    STATUS  mandatory
    DESCRIPTION
        "The number of times MAC address learn failed because there were
         no DMA descriptors."
    ::= { spMaintStatsTableEntry 4 }

spMaintStatsAgeMPNoddw OBJECT-TYPE
    SYNTAX  Counter
    ACCESS  read-only
    STATUS  mandatory
    DESCRIPTION
        "The number of times MAC address aging failed because there were
         no DMA descriptors."
    ::= { spMaintStatsTableEntry 5 }

spMaintStatsDeleteMiss OBJECT-TYPE
    SYNTAX  Counter
    ACCESS  read-only
    STATUS  mandatory
    DESCRIPTION
        "The number of times MAC address could not be found."
    ::= { spMaintStatsTableEntry 6 }

spMaintStatsRecvLetErrorsMP OBJECT-TYPE
    SYNTAX  Counter
    ACCESS  read-only
    STATUS  mandatory
    DESCRIPTION
        "The number of receive letter errors from MP."
    ::= { spMaintStatsTableEntry 7 }

spMaintStatsRecvLetErrorsSP1 OBJECT-TYPE
    SYNTAX  Counter
    ACCESS  read-only
    STATUS  mandatory
    DESCRIPTION
        "The number of receive letter errors from SP1. 
         If the current table index is the same as the SP number then a value 
         of 0 is returned."
    ::= { spMaintStatsTableEntry 8 }

spMaintStatsRecvLetErrorsSP2 OBJECT-TYPE
    SYNTAX  Counter
    ACCESS  read-only
    STATUS  mandatory
    DESCRIPTION
        "The number of receive letter errors from SP2. 
         If the current table index is the same as the SP number then a value 
         of 0 is returned."
    ::= { spMaintStatsTableEntry 9 }

spMaintStatsRecvLetErrorsSP3 OBJECT-TYPE
    SYNTAX  Counter
    ACCESS  read-only
    STATUS  mandatory
    DESCRIPTION
        "The number of receive letter errors from SP3. 
         If the current table index is the same as the SP number then a value 
         of 0 is returned."
    ::= { spMaintStatsTableEntry 10 }

spMaintStatsRecvLetErrorsSP4 OBJECT-TYPE
    SYNTAX  Counter
    ACCESS  read-only
    STATUS  mandatory
    DESCRIPTION
        "The number of receive letter errors from SP4.
         If the current table index is the same as the SP number then a value 
         of 0 is returned."
    ::= { spMaintStatsTableEntry 11 }

spMaintStatsSendLetFailsMP OBJECT-TYPE
    SYNTAX  Counter
    ACCESS  read-only
    STATUS  mandatory
    DESCRIPTION
        "The number of send letter failures to MP."
    ::= { spMaintStatsTableEntry 12 }

spMaintStatsSendLetFailsSP1 OBJECT-TYPE
    SYNTAX  Counter
    ACCESS  read-only
    STATUS  mandatory
    DESCRIPTION
        "The number of send letter failures to SP1.
         If the current table index is the same as the SP number then a value 
         of 0 is returned."
    ::= { spMaintStatsTableEntry 13 }

spMaintStatsSendLetFailsSP2 OBJECT-TYPE
    SYNTAX  Counter
    ACCESS  read-only
    STATUS  mandatory
    DESCRIPTION
        "The number of send letter failures to SP2.
         If the current table index is the same as the SP number then a value 
         of 0 is returned."
    ::= { spMaintStatsTableEntry 14 }

spMaintStatsSendLetFailsSP3 OBJECT-TYPE
    SYNTAX  Counter
    ACCESS  read-only
    STATUS  mandatory
    DESCRIPTION
        "The number of send letter failures to SP3.
         If the current table index is the same as the SP number then a value 
         of 0 is returned."
    ::= { spMaintStatsTableEntry 15 }

spMaintStatsSendLetFailsSP4 OBJECT-TYPE
    SYNTAX  Counter
    ACCESS  read-only
    STATUS  mandatory
    DESCRIPTION
        "The number of send letter failures to SP4.
         If the current table index is the same as the SP number then a value 
         of 0 is returned."
    ::= { spMaintStatsTableEntry 16 }

spMaintStatsRecvLetSuccessMP OBJECT-TYPE
    SYNTAX  Counter
    ACCESS  read-only
    STATUS  mandatory
    DESCRIPTION
        "The number of receive letter success from MP."
    ::= { spMaintStatsTableEntry 17 }

spMaintStatsRecvLetSuccessSP1 OBJECT-TYPE
    SYNTAX  Counter
    ACCESS  read-only
    STATUS  mandatory
    DESCRIPTION
        "The number of receive letter success from SP1.
         If the current table index is the same as the SP number then a value 
         of 0 is returned."
    ::= { spMaintStatsTableEntry 18 }

spMaintStatsRecvLetSuccessSP2 OBJECT-TYPE
    SYNTAX  Counter
    ACCESS  read-only
    STATUS  mandatory
    DESCRIPTION
        "The number of receive letter success from SP2.
         If the current table index is the same as the SP number then a value 
         of 0 is returned."
    ::= { spMaintStatsTableEntry 19 }

spMaintStatsRecvLetSuccessSP3 OBJECT-TYPE
    SYNTAX  Counter
    ACCESS  read-only
    STATUS  mandatory
    DESCRIPTION
        "The number of receive letter success from SP3.
         If the current table index is the same as the SP number then a value 
         of 0 is returned."
    ::= { spMaintStatsTableEntry 20 }

spMaintStatsRecvLetSuccessSP4 OBJECT-TYPE
    SYNTAX  Counter
    ACCESS  read-only
    STATUS  mandatory
    DESCRIPTION
        "The number of receive letter success from SP4.
         If the current table index is the same as the SP number then a value 
         of 0 is returned."
    ::= { spMaintStatsTableEntry 21 }

spMaintStatsSendLetSuccessMP OBJECT-TYPE
    SYNTAX  Counter
    ACCESS  read-only
    STATUS  mandatory
    DESCRIPTION
        "The number of send letter success to MP."
    ::= { spMaintStatsTableEntry 22 }

spMaintStatsSendLetSuccessSP1 OBJECT-TYPE
    SYNTAX  Counter
    ACCESS  read-only
    STATUS  mandatory
    DESCRIPTION
        "The number of send letter success to SP1.
         If the current table index is the same as the SP number then a value 
         of 0 is returned."
    ::= { spMaintStatsTableEntry 23 }

spMaintStatsSendLetSuccessSP2 OBJECT-TYPE
    SYNTAX  Counter
    ACCESS  read-only
    STATUS  mandatory
    DESCRIPTION
        "The number of send letter success to SP2.
         If the current table index is the same as the SP number then a value 
         of 0 is returned."
    ::= { spMaintStatsTableEntry 24 }

spMaintStatsSendLetSuccessSP3 OBJECT-TYPE
    SYNTAX  Counter
    ACCESS  read-only
    STATUS  mandatory
    DESCRIPTION
        "The number of send letter success to SP3.
         If the current table index is the same as the SP number then a value 
         of 0 is returned."
    ::= { spMaintStatsTableEntry 25 }

spMaintStatsSendLetSuccessSP4 OBJECT-TYPE
    SYNTAX  Counter
    ACCESS  read-only
    STATUS  mandatory
    DESCRIPTION
        "The number of send letter success to SP4.
         If the current table index is the same as the SP number then a value 
         of 0 is returned."
    ::= { spMaintStatsTableEntry 26 }

-- Management Port Statistics

mgmtStatsRxpackets OBJECT-TYPE
    SYNTAX  Counter
    ACCESS  read-only
    STATUS  mandatory
    DESCRIPTION
        "Total number of packet allocations from the packet buffer pool by 
         the TCP/IP protocol stack."
    ::= { mgmtStats 1 }
 
mgmtStatsRxErrors OBJECT-TYPE
    SYNTAX  Counter
    ACCESS  read-only
    STATUS  mandatory
    DESCRIPTION
	    "The number of inbound packets that contained
	     errors preventing them from being deliverable to a
	     higher-layer protocol."
    ::= { mgmtStats 2 }
 
mgmtStatsRxDropped OBJECT-TYPE
    SYNTAX  Counter
    ACCESS  read-only
    STATUS  mandatory
    DESCRIPTION
	    "The number of inbound packets that were dropped."
    ::= { mgmtStats 3 }
 
mgmtStatsRxOverruns OBJECT-TYPE
    SYNTAX  Counter
    ACCESS  read-only
    STATUS  mandatory
    DESCRIPTION
	    "The number of data overruns over this link."
    ::= { mgmtStats 4 }
 
mgmtStatsRxFrame OBJECT-TYPE
    SYNTAX  Counter
    ACCESS  read-only
    STATUS  mandatory
    DESCRIPTION
	    "The number of frames received on this link."
    ::= { mgmtStats 5 }
 
mgmtStatsTxpackets OBJECT-TYPE
    SYNTAX  Counter
    ACCESS  read-only
    STATUS  mandatory
    DESCRIPTION
        "Total number of packet allocations from the packet buffer pool by 
         the TCP/IP protocol stack."
    ::= { mgmtStats 6 }
 
mgmtStatsTxErrors OBJECT-TYPE
    SYNTAX  Counter
    ACCESS  read-only
    STATUS  mandatory
    DESCRIPTION
	    "The number of outbound packets that contained
	     errors preventing them from being deliverable to a
	     higher-layer protocol."
    ::= { mgmtStats 7 }
 
mgmtStatsTxDropped OBJECT-TYPE
    SYNTAX  Counter
    ACCESS  read-only
    STATUS  mandatory
    DESCRIPTION
	    "The number of outbound packets that were dropped."
    ::= { mgmtStats 8 }
 
mgmtStatsTxOverruns OBJECT-TYPE
    SYNTAX  Counter
    ACCESS  read-only
    STATUS  mandatory
    DESCRIPTION
	    "The number of data overruns over this link."
    ::= { mgmtStats 9 }
 
mgmtStatsTxCarrier OBJECT-TYPE
    SYNTAX  Counter
    ACCESS  read-only
    STATUS  mandatory
    DESCRIPTION
 	"The number of times that the carrier sense
         condition was lost or never asserted when
         attempting to transmit a frame on a this
         interface."
    ::= { mgmtStats 10 }
 
mgmtStatsTxCollisions OBJECT-TYPE
    SYNTAX  Counter
    ACCESS  read-only
    STATUS  mandatory
    DESCRIPTION
	    "The number of collisions on this outbound segment."
    ::= { mgmtStats 11 }
 
mgmtStatsTxQueueLen OBJECT-TYPE
    SYNTAX  Counter
    ACCESS  read-only
    STATUS  mandatory
    DESCRIPTION
	    "The length of the TCP transmit queue." 
    ::= { mgmtStats 12 }

-- Management Port Infor
mgmtPortInfoSpeed OBJECT-TYPE
    SYNTAX  INTEGER {
        mbs10(1),
        mbs100(2),
        any(3)
        }
    ACCESS  read-only
    STATUS  mandatory
    DESCRIPTION
        "The current operational speed of the management port."
    ::= { mgmtInfo 1 }

mgmtPortInfoMode OBJECT-TYPE
    SYNTAX  INTEGER {
        full-duplex(1),
        half-duplex(2),
        any(3)
        }
    ACCESS  read-only
    STATUS  mandatory
    DESCRIPTION
        "The current operational mode of the management port."
    ::= { mgmtInfo 2 }

mgmtPortInfoLink OBJECT-TYPE
    SYNTAX  INTEGER {
        up(1),
        down(2),
        disabled(3)
        }
     ACCESS  read-only
     STATUS  mandatory
     DESCRIPTION
         "The current operational link status of the management port."
     ::= { mgmtInfo 3 }
 
END
