SALIX-DS1-MIB DEFINITIONS ::= BEGIN

IMPORTS
   MODULE-IDENTITY, OBJECT-TYPE, IpAddress,
   NOTIFICATION-TYPE                         FROM SNMPv2-SMI

   MODULE-COMPLIANCE, OBJECT-GROUP           FROM SNMPv2-CONF
         
   DisplayString, TruthValue, DateAndTime                 FROM SNMPv2-TC
         
   atmfM4TrapAlarmSeverity                   FROM ATM-FORUM-M4-MIB
         
   entPhysicalIndex                          FROM ENTITY-MIB      
         
   dsx1ConfigEntry                           FROM DS1-MIB

   salixGeneric                              FROM SALIX-MIB;

salixDsx1MIB MODULE-IDENTITY
     LAST-UPDATED "9907080000Z"
     ORGANIZATION "SALIX Technologies"
     CONTACT-INFO "904 Wind River Lane
                   Suite 101
                   Gaithersburg, MD  20878
                   (301)-417-0017"
     DESCRIPTION  "The MIB describing objects relating to DS1 interfaces, specifically 
                   items that augment objects from the DS1-MIB"
     ::= { salixGeneric 7 }
     
   salixDsx1MIBObjects OBJECT IDENTIFIER ::= { salixDsx1MIB 1 }
   salixDsx1MIBTraps   OBJECT IDENTIFIER ::= { salixDsx1MIB 2 }
   salixDsx1MIBCompliance OBJECT IDENTIFIER ::= { salixDsx1MIB 3 }       
   salixDsx1MIBTrapPrefix OBJECT IDENTIFIER ::= { salixDsx1MIBTraps 0}

  salixDsx1ConfigTable OBJECT-TYPE
       SYNTAX     SEQUENCE OF    SalixDsx1ConfigEntry
       MAX-ACCESS not-accessible
       STATUS     current
       DESCRIPTION
            "The SALIX DS1 config table  This table augments the
             dsx1ConfigTable defined in the DS1 MIB."
       ::= { salixDsx1MIBObjects 1 }

  salixDsx1ConfigEntry OBJECT-TYPE
       SYNTAX     SalixDsx1ConfigEntry
       MAX-ACCESS not-accessible
       STATUS     current
       DESCRIPTION
            "An entry in the SALIX DS1 config table.  This entry 
             containts SALIX specific DS1 configuration objects"
       AUGMENTS { dsx1ConfigEntry }
       ::= { salixDsx1ConfigTable 1 }

  SalixDsx1ConfigEntry ::= SEQUENCE {
            salixDsx1ContinuityTestType                   INTEGER,
            salixDsx1DChannelPresent                      TruthValue,
            salixDsx1AutoInitiateState                    TruthValue,
            salixDsx1DChannelMode                         INTEGER,
            salixDsx1RobbedBitSignalling                  INTEGER,
            salixDsx1TDMEchoCancellation                  INTEGER
       } 
       
   salixDsx1ContinuityTestType OBJECT-TYPE
      SYNTAX      INTEGER { loopback(1),
                            transponder(2) }
      MAX-ACCESS  read-write
      STATUS      current
      DESCRIPTION
         "The type of continuity test that should be setup.  An entry exists for 
          every DS1 in the system.  This object is 
          consulted when IPDC is requested to setup a continuity test.  Since
          this value is specified in SGCP, it is not consulted if the SGCP 
          protocol is used.  Writing to this value has the effect that it changes
          the continuity test type for any subsequently setup continuity tests.  Any
          tests currently in progress are not effected by changing this object."
      ::= { salixDsx1ConfigEntry 1 }

   salixDsx1DChannelPresent OBJECT-TYPE
      SYNTAX      TruthValue
      MAX-ACCESS  read-write
      STATUS      current
      DESCRIPTION
         "An indication of whether channel 24 of the DS1 is reserved for D channel
          signaling."
      DEFVAL { false }
      ::= { salixDsx1ConfigEntry 2 }

   salixDsx1AutoInitiateState OBJECT-TYPE
      SYNTAX      TruthValue
      MAX-ACCESS  read-write
      STATUS      current
      DESCRIPTION
         "An indication of whether the D channel data link control (layer 2)
          should be initiated automatically during DS1 initialization or 
          brought up on demand.  This attribute is only relevant if 
          salixDsx1DChannelPresent is 'true'."          
      DEFVAL { false }
      ::= { salixDsx1ConfigEntry 3 }
      
   salixDsx1DChannelMode OBJECT-TYPE
      SYNTAX      INTEGER { userMode(1),
                            networkMode(2) }
      MAX-ACCESS  read-write
      STATUS      current
      DESCRIPTION
         "An indication of whether the D Channel (if present) on the given
          DS1 should be configured as 'user mode' or as 'network mode'.   
          This attributes is only used if the salixDsx1DChannelPresent field
          is set to 'true'"          
      DEFVAL { userMode }
      ::= { salixDsx1ConfigEntry 4 }

   salixDsx1RobbedBitSignalling OBJECT-TYPE
      SYNTAX      INTEGER { none(0),
                            onHook(1),
                            offHook(2),
                            ringing(3) }                            
      MAX-ACCESS  read-write
      STATUS      current
      DESCRIPTION
         "An indication of whether the 'ABCD' bits of the DS0s in the DS1
          should be configured for robbed bit signalling."
      DEFVAL { none }
      ::= { salixDsx1ConfigEntry 5 }

   salixDsx1TDMEchoCancellation OBJECT-TYPE
      SYNTAX      INTEGER  { none(0),
                             echoCancel16ms(1),
                             echoCancel32ms(2),     
                             echoCancel63ms(3) }       
      MAX-ACCESS  read-write
      STATUS      current
      DESCRIPTION
         "An indication of whether echo cancellation should be applied
          to the DS0s in the DS1.
            echoCancel16ms - 16 millisecond echo cancellation tail length
            echoCancel32ms - 32 millisecond echo cancellation tail length
            echoCancel63ms - 63 millisecond echo cancellation tail length"
      DEFVAL { none }
      ::= { salixDsx1ConfigEntry 7 }

      
-- Conformance Statements

salixDs1Groups      OBJECT IDENTIFIER  ::= { salixDsx1MIBCompliance 1 }
salixDs1Compliances OBJECT IDENTIFIER  ::= { salixDsx1MIBCompliance 2 }

   salixDs1Group OBJECT-GROUP
      OBJECTS {
         salixDsx1ContinuityTestType
      }
      STATUS         current
      DESCRIPTION    "Salix DS1 Objects Group"
      ::= { salixDs1Groups 1}
      
      
-- Compliance Statements

salixDs1Compliance MODULE-COMPLIANCE
     STATUS       current
     DESCRIPTION
                  "The basic implementation requirements for the SALIX-DS1-MIB."
     MODULE       -- This module
     MANDATORY-GROUPS { salixDs1Group }
     ::= { salixDs1Compliances 1 }

END
