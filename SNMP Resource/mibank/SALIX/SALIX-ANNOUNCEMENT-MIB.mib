SALIX-ANNOUNCEMENT-MIB DEFINITIONS ::= BEGIN

IMPORTS
   MODULE-IDENTITY, OBJECT-TYPE, IpAddress,
   NOTIFICATION-TYPE                         FROM SNMPv2-SMI

   MODULE-COMPLIANCE, OBJECT-GROUP           FROM SNMPv2-CONF
         
         DisplayString, TruthValue, DateAndTime           FROM SNMPv2-TC
         
         atmfM4TrapAlarmSeverity             FROM ATM-FORUM-M4-MIB
         
         entPhysicalIndex                    FROM ENTITY-MIB      
         
         salixGeneric                        FROM SALIX-MIB;

salixAnnouncementMIB MODULE-IDENTITY
     LAST-UPDATED "9903310000Z"
     ORGANIZATION "SALIX Technologies"
     CONTACT-INFO "904 Wind River Lane
                   Suite 101
                   Gaithersburg, MD  20878
                   (301)-417-0017"
     DESCRIPTION  "The MIB describing objects relating to Announcements, 
                   Tones, and Continuity Tests for SALIX products"
     ::= { salixGeneric 6 }
     
   salixAnnouncementMIBObjects OBJECT IDENTIFIER ::= { salixAnnouncementMIB 1 }
   salixAnnouncementMIBTraps   OBJECT IDENTIFIER ::= { salixAnnouncementMIB 2 }
   salixAnnouncementMIBCompliance OBJECT IDENTIFIER ::= { salixAnnouncementMIB 3 }       
   salixAnnouncementMIBTrapPrefix OBJECT IDENTIFIER ::= { salixAnnouncementMIBTraps 0}

    --  Announcement Table

    -- This table provides a mechanism for installing and viewing announcements 
    -- on the system by initiating a download request 
	 -- to a specific announcement entry (bin) in the  announcement 
    -- download table.  Prior to initiating the announcement request
	 -- a management entity must first set the following fields
	 -- in this table:
    --      salixAnnouncementFilename 
    --      salixAnnouncementIpAddress.
    --
    -- When the above fields are valid, the management entity
	 -- can then start the download by sending a request to the 
	 -- SNMP agent with the salixAnnouncementRequest field set to 
	 -- 'start' in addition to specifing values for the 
	 -- salixAnnouncementUsername and 
	 -- salixAnnouncementPassword fields.

    -- It is the responsibility of the management entity to poll the
    -- salixAnnouncementState to determine when the download completes.
    -- If the command completes with 'success', then the download to the
    -- was successful and the software is installed into the  
    -- system.

    -- The agent will create the salixAnnouncementTable with a fixed 
    -- number of entries when the host is booted.  The management entity
    -- can download to any entry in the salixAnnouncementTable with 
    -- the exception of entry (bin) zero.  Entry (bin) zero is reserved
    -- to indicate any empty software bin.

    -- A download request to an entry (bin) in the salixAnnouncementTable
    -- will overwrite the corresponding entry (bin) in the 
    -- salixAnnouncementTable.  However, a download request to an entry
    -- (bin) in the salixAnnouncementTable will be ignored if a previous
    -- request is still in progress.

  salixAnnouncementTable OBJECT-TYPE
       SYNTAX     SEQUENCE OF    SalixAnnouncementEntry
       MAX-ACCESS not-accessible
       STATUS     current
       DESCRIPTION
            "The  announcement download table.  This table provides a
             mechanism for downloading announcements to the system.  
             Announcements that are successfully downloaded are installed
             on the system and occupy an entry in the salixAnnouncementTable.
             
             An entry in the salixAnnouncementTable exists for each bin on 
             the system."
       ::= { salixAnnouncementMIBObjects 1 }

  salixAnnouncementEntry OBJECT-TYPE
       SYNTAX     SalixAnnouncementEntry
       MAX-ACCESS not-accessible
       STATUS     current
       DESCRIPTION
            "An entry in the salixAnnouncementTable that identifies 
             the parameters necessary to download announcements to the system."
       INDEX { salixAnnouncementIndex }
       ::= { salixAnnouncementTable 1 }

  SalixAnnouncementEntry ::= SEQUENCE {
            salixAnnouncementIndex           INTEGER,
            salixAnnouncementIpAddress       IpAddress,
            salixAnnouncementFilename        DisplayString,
            salixAnnouncementUsername        DisplayString,
            salixAnnouncementPassword        DisplayString,
            salixAnnouncementRequest         INTEGER,
            salixAnnouncementState           INTEGER,
            salixAnnouncementDescription     DisplayString,
            salixAnnouncementInstall         DateAndTime,
            salixAnnouncementFull            TruthValue,
            salixAnnouncementStatusMessage   OCTET STRING
       }
       
  salixAnnouncementIndex OBJECT-TYPE
       SYNTAX         INTEGER (0..20)
       MAX-ACCESS     read-only
       STATUS         current
       DESCRIPTION
            "The unique index (bin) that the announcement is stored in."
       ::= { salixAnnouncementEntry 1 }

  salixAnnouncementIpAddress OBJECT-TYPE
       SYNTAX     IpAddress
       MAX-ACCESS read-write
       STATUS     current
       DESCRIPTION
            "The Ip Address where the salixAnnouncementFilename
             object resides."
       ::= { salixAnnouncementEntry 2 }

  salixAnnouncementFilename OBJECT-TYPE
       SYNTAX     DisplayString (SIZE(0..64))
       MAX-ACCESS read-write
       STATUS     current
       DESCRIPTION
            "The fully qualified filename found at the specified Ip Address
             (salixAnnouncementIpAddress) that is to be downloaded
             to the entry in the Table."
       ::= { salixAnnouncementEntry 3 }

  salixAnnouncementUsername OBJECT-TYPE
       SYNTAX     DisplayString (SIZE(0..64))
       MAX-ACCESS read-write
       STATUS     current
       DESCRIPTION
            "The username to be used when getting a file from the
             computer at the IP address indicated by the 
             salixAnnouncementIpAddress attribute.  For security
             reasons, reading this field will return an empty string."
       ::= { salixAnnouncementEntry 4 }
     
  salixAnnouncementPassword OBJECT-TYPE
       SYNTAX     DisplayString (SIZE(0..64))
       MAX-ACCESS read-write
       STATUS     current
       DESCRIPTION
            "The password to be used when getting a file from the
             computer at the IP address indicated by the 
             salixAnnouncementIpAddress attribute.  For security
             reasons, reading this field will return an empty string."
       ::= { salixAnnouncementEntry 5 }
       
  salixAnnouncementRequest OBJECT-TYPE
       SYNTAX         INTEGER { none(0), 
                                start(1),
                                update(2) }
       MAX-ACCESS     read-write
       STATUS         current
       DESCRIPTION
            "The announcement request for this row.  Writing values to 
             this object has the following side effects (depending on 
             the value written:
             
                  none(0)     - no effect.  Default value for this object.
                  start(1)    - start the FTP download and installation 
                                for the given announcement file.
                  update(2)   - Do not start the FTP download, just update
                                system with the given version of 
                                the announcement that already exists."
       DEFVAL { none }
       ::= { salixAnnouncementEntry 6 }

  salixAnnouncementState OBJECT-TYPE
       SYNTAX     INTEGER { none(1),
                            inProgress(2),
                            success(3),
                            aborted(4),
                            failed(5),
                            locked(6),
                            installInProgress(7)
                          }
       MAX-ACCESS read-only
       STATUS     current
       DESCRIPTION
            "The state of the download software request.

             none(1)       - download not started or not supported
             inProgress(2) - download in progress
             success(3)    - download to the announcement table was
                             successful.
             aborted(4)    - download aborted
             failed(5)     - download to at least one plug-in unit failed
             locked(6)     - the filename in the installed software entry
                             is locked by the management processor software.
             installInProgress(7) - the bin is currently being installed to 
                                    modules in the system and is not available
                                    for download"
       DEFVAL { none }
       ::= { salixAnnouncementEntry 7 }
       
  salixAnnouncementDescription OBJECT-TYPE
       SYNTAX     DisplayString (SIZE(0..80))
       MAX-ACCESS read-write
       STATUS     current
       DESCRIPTION
            "A Description for the announcement.  Should be something
             that uniqely describes this announcement on the system, 
             so that the operator can determine the difference between
             all the installed announcements on the system"
       ::= { salixAnnouncementEntry 8 }
       
  salixAnnouncementInstall OBJECT-TYPE
       SYNTAX     DateAndTime
       MAX-ACCESS read-only
       STATUS     current
       DESCRIPTION
            "The time the announcement was installed on the system.  This time is
             acutally the time that the download completes."
       ::= { salixAnnouncementEntry 9 }
       
  salixAnnouncementFull OBJECT-TYPE
       SYNTAX     TruthValue
       MAX-ACCESS read-only
       STATUS     current
       DESCRIPTION
            "This value indicates whether the announcement bin is full or not.
            
               True:    an announcement file is present in this bin
               False:   no announcement file is present in this bin
            "
       ::= { salixAnnouncementEntry 10 }

  salixAnnouncementStatusMessage OBJECT-TYPE
       SYNTAX     OCTET STRING(SIZE (256))
       MAX-ACCESS read-only
       STATUS     current
       DESCRIPTION
            "Status message that describes the current state of the
             download as indicated by the 'salixAnnouncementState' 
             attribute."
       ::= { salixAnnouncementEntry 11 }
            
                           
  -- Announcement Mapping Table
  
  -- The announcement mapping table maps the salixAnnouncementIndex [bin] to
  -- the enyPhyisicalIndex that the announcement is installed on.
  
  salixAnnouncementMappingTable OBJECT-TYPE
       SYNTAX     SEQUENCE OF    SalixAnnouncementMappingEntry
       MAX-ACCESS not-accessible
       STATUS     current
       DESCRIPTION
            "The announcement mapping table is used to map salixAnnouncementIndex
             [bins] to the entPhysicalIndex that the announcement is installed on.
             When used in conjunction with the salixAnnouncementTable, it can be seen
             which boards in the system contain which announcements.
             
             An entry in this table exists for each announcement on each board
             that the announcement is installed on."
       ::= { salixAnnouncementMIBObjects 2 }

  salixAnnouncementMappingEntry OBJECT-TYPE
       SYNTAX     SalixAnnouncementMappingEntry
       MAX-ACCESS not-accessible
       STATUS     current
       DESCRIPTION
            "An entry in the salixAnnouncementMappingEntry that maps
             an salixAnnouncementIndex to an entPhysicalIndex."
       INDEX { entPhysicalIndex,
               salixAnnouncementIndex }
       ::= { salixAnnouncementMappingTable 1 }

  SalixAnnouncementMappingEntry ::= SEQUENCE {
        salixAnnouncementMappingStatus    INTEGER
       }
         
  salixAnnouncementMappingStatus OBJECT-TYPE
       SYNTAX     INTEGER { ready(1),
                            downloadInProgress(2),
                            error(3)
                           }
       MAX-ACCESS read-only
       STATUS     current
       DESCRIPTION
            "Describes the current state of the announcement on the board 
             in the system.
             
                  ready (1)             - The announcement is installed 
                                          on the board and ready for use
                  downloadInProgress(2) - The announcement is being installed
                                          on the board and is not ready for use"
       ::= { salixAnnouncementMappingEntry 1 }
        
   -- Announcement Traps
   
   salixAnnouncementInstallFailure NOTIFICATION-TYPE
     OBJECTS   { entPhysicalIndex,
                 salixAnnouncementIndex,
                 atmfM4TrapAlarmSeverity }
     STATUS    current
     DESCRIPTION
          "Indicates thats the installation of the announcement
           has failed.  This notification is generated when the
           salixAnnouncementState for this download transitions
           from inProgress to failed.  The default alarm severity 
           for this alarm is 'major'."
     ::= { salixAnnouncementMIBTrapPrefix 1 }   
     
   salixAnnouncementInstallSuccess NOTIFICATION-TYPE
     OBJECTS   { salixAnnouncementIndex,
                 atmfM4TrapAlarmSeverity }
     STATUS    current
     DESCRIPTION
          "Indicates thats the installation of the announcement to
           all the Transcoders have succeeded.  This notification 
           is generated when the salixAnnouncementState for the 
           download transitions from inProgress to success.  The 
           default alarm severity for this alarm is 'minor'."
     ::= { salixAnnouncementMIBTrapPrefix 2 }        
                     
-- Conformance Statements

salixAnnouncementGroups      OBJECT IDENTIFIER  ::= { salixAnnouncementMIBCompliance 1 }
salixAnnouncementCompliances OBJECT IDENTIFIER  ::= { salixAnnouncementMIBCompliance 2 }

   salixAnnouncementGroup OBJECT-GROUP
      OBJECTS {
         salixAnnouncementIpAddress,
         salixAnnouncementFilename,
         salixAnnouncementUsername,
         salixAnnouncementPassword,
         salixAnnouncementRequest,
         salixAnnouncementState,
         salixAnnouncementDescription,
         salixAnnouncementInstall 
      }
      STATUS         current
      DESCRIPTION    "Salix Announcement Objects Group"
      ::= { salixAnnouncementGroups 1}
      
   salixAnnouncementMappingGroup OBJECT-GROUP
      OBJECTS {
         salixAnnouncementMappingStatus
      }
      STATUS         current
      DESCRIPTION    "Salix Announcement Mapping Objects Group"
      ::= { salixAnnouncementGroups 2}

-- Compliance Statements

salixAnnouncementCompliance MODULE-COMPLIANCE
     STATUS       current
     DESCRIPTION
                  "The basic implementation requirements for the SALIX-ANNOUNCEMENT-MIB."
     MODULE       -- This module
     MANDATORY-GROUPS { salixAnnouncementGroup }
     ::= { salixAnnouncementCompliances 1 }

END
