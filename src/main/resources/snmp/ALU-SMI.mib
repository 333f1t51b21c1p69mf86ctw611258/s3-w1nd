--
-- ALU-SMI.mib
-- MIB generated by MG-SOFT Visual MIB Builder Version 6.0  Build 88
-- Tuesday, July 18, 2017 at 16:10:18
--

	ALU-SMI DEFINITIONS ::= BEGIN
 
		IMPORTS
			ifNumber, ifIndex, ifDescr, ifType, ifMtu, 
			ifSpeed, ifPhysAddress, ifAdminStatus, ifOperStatus, ifLastChange, 
			ifInOctets, ifInUcastPkts, ifInNUcastPkts, ifInDiscards, ifInErrors, 
			ifInUnknownProtos, ifOutOctets, ifOutUcastPkts, ifOutNUcastPkts, ifOutDiscards, 
			ifOutErrors, ifOutQLen, ifSpecific, ifName, ifInMulticastPkts, 
			ifInBroadcastPkts, ifOutMulticastPkts, ifOutBroadcastPkts, ifHCInOctets, ifHCInUcastPkts, 
			ifHCInMulticastPkts, ifHCInBroadcastPkts, ifHCOutOctets, ifHCOutUcastPkts, ifHCOutMulticastPkts, 
			ifHCOutBroadcastPkts, ifLinkUpDownTrapEnable, ifHighSpeed, ifPromiscuousMode, ifConnectorPresent, 
			ifAlias, ifCounterDiscontinuityTime, ifStackHigherLayer, ifStackLowerLayer, ifStackStatus, 
			ifTestId, ifTestStatus, ifTestType, ifTestResult, ifTestCode, 
			ifTestOwner, ifRcvAddressAddress, ifRcvAddressStatus, ifRcvAddressType, ifTableLastChange, 
			ifStackLastChange, ifGeneralGroup, ifFixedLengthGroup, ifHCFixedLengthGroup, ifPacketGroup, 
			ifHCPacketGroup, ifVHCPacketGroup, ifRcvAddressGroup, ifTestGroup, ifStackGroup, 
			ifGeneralInformationGroup, ifStackGroup2, ifOldObjectsGroup, ifCounterDiscontinuityGroup, ifCompliance, 
			ifCompliance2, InterfaceIndex			
				FROM IF-MIB			
			enterprises, Integer32, Gauge32, OBJECT-TYPE, MODULE-IDENTITY			
				FROM SNMPv2-SMI			
			TEXTUAL-CONVENTION			
				FROM SNMPv2-TC;
	
	
		alcatel MODULE-IDENTITY 
			LAST-UPDATED "201707131552Z"		-- July 13, 2017 at 15:52 GMT
			ORGANIZATION 
				"Ala-Lucent"
			CONTACT-INFO 
				"Email:    quyenlv@dasanzhone.com"
			DESCRIPTION 
				"This module describles the Alcatel-Lucent private MIB."
			::= { enterprises 637 }

		
	
--
-- Textual conventions
--
	
		AlcatelControlState ::= TEXTUAL-CONVENTION
			STATUS current
			DESCRIPTION 
				"Description."
			SYNTAX INTEGER
				{
				normal(1),
				add(4),
				delete(6)
				}

	
--
-- Node definitions
--
	
		ipDslam OBJECT IDENTIFIER ::= { alcatel 61 }

		
		asam OBJECT IDENTIFIER ::= { ipDslam 1 }

		
		node31 OBJECT IDENTIFIER ::= { asam 31 }

		
		node2 OBJECT IDENTIFIER ::= { node31 2 }

		
		alaBridgeTable OBJECT-TYPE
			SYNTAX SEQUENCE OF AlaBridgeEntry
			MAX-ACCESS not-accessible
			STATUS current
			DESCRIPTION
				"Description."
			::= { node2 5 }

		
		alaBridgeEntry OBJECT-TYPE
			SYNTAX AlaBridgeEntry
			MAX-ACCESS not-accessible
			STATUS current
			DESCRIPTION
				"Description."
			INDEX { alaBridgePortIndex }
			::= { alaBridgeTable 1 }

		
		AlaBridgeEntry ::=
			SEQUENCE { 
				alaBridgeDefaultPriority
					Integer32,
				alaBridgeMaxUnicastMac
					Integer32,
				alaBridgeMacLearnOff
					Integer32,
				alaBridgePrioRegenProf
					Integer32,
				alaBridgeMirrorMode
					INTEGER,
				alaBridgeMirrorVlan
					Integer32,
				alaBridgeMaxCommittedMac
					Gauge32,
				alaBridgePvidTaggingFlag
					INTEGER
			 }

		alaBridgeDefaultPriority OBJECT-TYPE
			SYNTAX Integer32 (0..7)
			MAX-ACCESS read-write
			STATUS current
			DESCRIPTION
				"Priority to be set in upstream frames."
			DEFVAL { 0 }
			::= { alaBridgeEntry 2 }

		
		alaBridgeMaxUnicastMac OBJECT-TYPE
			SYNTAX Integer32 (1..8192)
			MAX-ACCESS read-write
			STATUS current
			DESCRIPTION
				"Max uncommitted unicast mac addresses."
			DEFVAL { 1 }
			::= { alaBridgeEntry 3 }

		
		alaBridgeMacLearnOff OBJECT-TYPE
			SYNTAX Integer32 (1..2)
			MAX-ACCESS read-write
			STATUS current
			DESCRIPTION
				"Disable self learning of mac address."
			::= { alaBridgeEntry 6 }

		
		alaBridgePrioRegenProf OBJECT-TYPE
			SYNTAX Integer32
			MAX-ACCESS read-write
			STATUS current
			DESCRIPTION
				"Priority regeneration profile."
			::= { alaBridgeEntry 10 }

		
		alaBridgeMirrorMode OBJECT-TYPE
			SYNTAX INTEGER
				{
				disable(1),
				overwrite-outer-vlan(4)
				}
			MAX-ACCESS read-write
			STATUS current
			DESCRIPTION
				"Flow mirroring mode of the bridge port."
			DEFVAL { disable }
			::= { alaBridgeEntry 13 }

		
		alaBridgeMirrorVlan OBJECT-TYPE
			SYNTAX Integer32 (0..4093)
			MAX-ACCESS read-write
			STATUS current
			DESCRIPTION
				"Vlan-id to be inserted into mirrored packets. This configuration value has no effect in case mirroring mode of the bridgeport is disabled (mirror-mode)."
			DEFVAL { 0 }
			::= { alaBridgeEntry 14 }

		
		alaBridgeMaxCommittedMac OBJECT-TYPE
			SYNTAX Gauge32 (0..128 | 65535)
			MAX-ACCESS read-write
			STATUS current
			DESCRIPTION
				"Max committed unicast mac addresses. 65535 means the committed value is the same as max-unicast-mac."
			DEFVAL { 65535 }
			::= { alaBridgeEntry 38 }

		
		alaBridgePvidTaggingFlag OBJECT-TYPE
			SYNTAX INTEGER
				{
				onu(1),
				olt(2)
				}
			MAX-ACCESS read-write
			STATUS current
			DESCRIPTION
				"Pvid will be tagged in ONU or in OLT."
			DEFVAL { onu }
			::= { alaBridgeEntry 51 }

		
		alaBridgePortVlanTable OBJECT-TYPE
			SYNTAX SEQUENCE OF AlaBridgePortVlanEntry
			MAX-ACCESS not-accessible
			STATUS current
			DESCRIPTION
				"Description."
			::= { node2 12 }

		
		alaBridgePortVlanEntry OBJECT-TYPE
			SYNTAX AlaBridgePortVlanEntry
			MAX-ACCESS not-accessible
			STATUS current
			DESCRIPTION
				"Description."
			INDEX { alaBridgePortIndex, alaBridgePortVlanID }
			::= { alaBridgePortVlanTable 1 }

		
		AlaBridgePortVlanEntry ::=
			SEQUENCE { 
				alaBridgePortVlanID
					Integer32,
				alaBridgePortVlanTag
					INTEGER,
				alaBridgePortVlanScope
					INTEGER,
				alaBridgePortVlanQosPriority
					Integer32,
				alaBridgePortVlanQosProfile
					Integer32,
				alaBridgePortVlanMaxUnicastMac
					Integer32,
				alaBridgePortVlanMacLearnCtrl
					INTEGER,
				alaBridgePortVlanDsDedicatedQ
					INTEGER
			 }

		alaBridgePortVlanID OBJECT-TYPE
			SYNTAX Integer32 (1..4093 | 4096)
			MAX-ACCESS read-write
			STATUS current
			DESCRIPTION
				"Vlanport on the bridge port."
			::= { alaBridgePortVlanEntry 1 }

		
		alaBridgePortVlanTag OBJECT-TYPE
			SYNTAX INTEGER
				{
				untagged(1),
				single-tagged(2),
				priority-tagged(3)
				}
			MAX-ACCESS read-write
			STATUS current
			DESCRIPTION
				"Tag control for egress port."
			DEFVAL { untagged }
			::= { alaBridgePortVlanEntry 4 }

		
		alaBridgePortVlanScope OBJECT-TYPE
			SYNTAX INTEGER
				{
				network(1),
				local(2)
				}
			MAX-ACCESS read-write
			STATUS current
			DESCRIPTION
				"The vlan scope."
			DEFVAL { network }
			::= { alaBridgePortVlanEntry 7 }

		
		alaBridgePortVlanQosPriority OBJECT-TYPE
			SYNTAX Integer32 (0..7)
			MAX-ACCESS read-write
			STATUS current
			DESCRIPTION
				"QOS fixed priority identify."
			::= { alaBridgePortVlanEntry 11 }

		
		alaBridgePortVlanQosProfile OBJECT-TYPE
			SYNTAX Integer32
			MAX-ACCESS read-write
			STATUS current
			DESCRIPTION
				"QOS regeneration profile identify."
			::= { alaBridgePortVlanEntry 12 }

		
		alaBridgePortVlanMaxUnicastMac OBJECT-TYPE
			SYNTAX Integer32 (0..65535)
			MAX-ACCESS read-write
			STATUS current
			DESCRIPTION
				"Max uncommitted unicast mac addresses."
			DEFVAL { 65535 }
			::= { alaBridgePortVlanEntry 16 }

		
		alaBridgePortVlanMacLearnCtrl OBJECT-TYPE
			SYNTAX INTEGER
				{
				enable(1),
				disable(2),
				inherit(3)
				}
			MAX-ACCESS read-write
			STATUS current
			DESCRIPTION
				"MAC address learned control up(1), down(2), inherit from bridgedPort(3)."
			DEFVAL { inherit }
			::= { alaBridgePortVlanEntry 20 }

		
		alaBridgePortVlanDsDedicatedQ OBJECT-TYPE
			SYNTAX INTEGER
				{
				disable(0),
				enable(1)
				}
			MAX-ACCESS read-write
			STATUS current
			DESCRIPTION
				"Packets use dedicated downstream PON level queue."
			DEFVAL { disable }
			::= { alaBridgePortVlanEntry 21 }

		
		alaBridgePortTable OBJECT-TYPE
			SYNTAX SEQUENCE OF AlaBridgePortEntry
			MAX-ACCESS not-accessible
			STATUS current
			DESCRIPTION
				"Description."
			::= { node2 25 }

		
		alaBridgePortEntry OBJECT-TYPE
			SYNTAX AlaBridgePortEntry
			MAX-ACCESS not-accessible
			STATUS current
			DESCRIPTION
				"Description."
			INDEX { ifIndex }
			::= { alaBridgePortTable 1 }

		
		AlaBridgePortEntry ::=
			SEQUENCE { 
				alaBridgePortIndex
					InterfaceIndex,
				alaBridgePortControlState
					AlcatelControlState
			 }

		alaBridgePortIndex OBJECT-TYPE
			SYNTAX InterfaceIndex
			MAX-ACCESS read-only
			STATUS current
			DESCRIPTION
				"Ont bridge port identifier."
			::= { alaBridgePortEntry 1 }

		
		alaBridgePortControlState OBJECT-TYPE
			SYNTAX AlcatelControlState
			MAX-ACCESS read-write
			STATUS current
			DESCRIPTION
				"Bridge port control state."
			::= { alaBridgePortEntry 2 }

		
		alaEquipment OBJECT IDENTIFIER ::= { asam 35 }

		
		alaOnt OBJECT IDENTIFIER ::= { alaEquipment 10 }

		
		alaOntTable OBJECT-TYPE
			SYNTAX SEQUENCE OF AlaOntEntry
			MAX-ACCESS not-accessible
			STATUS current
			DESCRIPTION
				"Description."
			::= { alaOnt 1 }

		
		alaOntEntry OBJECT-TYPE
			SYNTAX AlaOntEntry
			MAX-ACCESS not-accessible
			STATUS current
			DESCRIPTION
				"Description."
			INDEX { alaOntID }
			::= { alaOntTable 1 }

		
		AlaOntEntry ::=
			SEQUENCE { 
				alaOntID
					Integer32,
				alaOntControlState
					AlcatelControlState,
				alaOntSernum
					OCTET STRING,
				alaOntBatteryBkup
					INTEGER,
				alaOntSwVerPland
					OCTET STRING,
				alaOntBerint
					Integer32,
				alaOntsubslocid
					OCTET STRING,
				alaOntProvversion
					OCTET STRING,
				alaOntDesc1
					OCTET STRING,
				alaOntDesc2
					OCTET STRING,
				alaOntFecUp
					INTEGER,
				alaOntEnable
					INTEGER,
				alaOntSwDnloadVersion
					OCTET STRING,
				alaOntOpticsHist
					INTEGER,
				alaOntPlndVar
					OCTET STRING,
				alaOntRfFilter
					INTEGER,
				alaOntSlidVisibility
					INTEGER,
				alaOntUsPoliceMode
					INTEGER,
				alaOntEnableAes
					INTEGER,
				alaOntLogAuthId
					OCTET STRING,
				alaOntLogAuthPwd
					OCTET STRING,
				alaOntBridgeMapMode
					INTEGER,
				alaOntCvlantransMode
					INTEGER,
				alaOntOltDSCPpbitalign
					INTEGER,
				alaOntSnBundleCtrl0
					Integer32,
				alaOntSnBundleCtrl1
					Integer32
			 }

		alaOntID OBJECT-TYPE
			SYNTAX Integer32 (1..128)
			MAX-ACCESS read-only
			STATUS current
			DESCRIPTION
				"The ONT identifier."
			::= { alaOntEntry 1 }

		
		alaOntControlState OBJECT-TYPE
			SYNTAX AlcatelControlState
			MAX-ACCESS read-write
			STATUS current
			DESCRIPTION
				"Ont table control state."
			::= { alaOntEntry 2 }

		
		alaOntSernum OBJECT-TYPE
			SYNTAX OCTET STRING
			MAX-ACCESS read-write
			STATUS current
			DESCRIPTION
				"Serial Number."
			::= { alaOntEntry 5 }

		
		alaOntBatteryBkup OBJECT-TYPE
			SYNTAX INTEGER
				{
				disable(0),
				enable(1)
				}
			MAX-ACCESS read-write
			STATUS current
			DESCRIPTION
				"Battery backup."
			DEFVAL { disable }
			::= { alaOntEntry 8 }

		
		alaOntSwVerPland OBJECT-TYPE
			SYNTAX OCTET STRING (SIZE (1..14))
			MAX-ACCESS read-write
			STATUS current
			DESCRIPTION
				"Planned ONT software version number. If sw-dnload-version is set to disabled, sw-ver-pland cannot be set to delayactivate.
				"
			::= { alaOntEntry 11 }

		
		alaOntBerint OBJECT-TYPE
			SYNTAX Integer32 (8000..100000)
			MAX-ACCESS read-write
			STATUS current
			DESCRIPTION
				"Accumulation interval (in number of downstream frames) for ONU BER calculation."
			DEFVAL { 8000 }
			::= { alaOntEntry 18 }

		
		alaOntsubslocid OBJECT-TYPE
			SYNTAX OCTET STRING (SIZE (0..12))
			MAX-ACCESS read-write
			STATUS current
			DESCRIPTION
				"Subscriber location id (SLID)."
			::= { alaOntEntry 20 }

		
		alaOntProvversion OBJECT-TYPE
			SYNTAX OCTET STRING (SIZE (0..14))
			MAX-ACCESS read-write
			STATUS current
			DESCRIPTION
				"Provisioned version number."
			DEFVAL { "*" }
			::= { alaOntEntry 21 }

		
		alaOntDesc1 OBJECT-TYPE
			SYNTAX OCTET STRING (SIZE (0..64))
			MAX-ACCESS read-write
			STATUS current
			DESCRIPTION
				"Free-form textual field for user to describe the ONT."
			DEFVAL { "" }
			::= { alaOntEntry 24 }

		
		alaOntDesc2 OBJECT-TYPE
			SYNTAX OCTET STRING (SIZE (0..64))
			MAX-ACCESS read-write
			STATUS current
			DESCRIPTION
				"Free-form textual field for user to describe the ONT."
			DEFVAL { "" }
			::= { alaOntEntry 25 }

		
		alaOntFecUp OBJECT-TYPE
			SYNTAX INTEGER
				{
				enable(1),
				disable(2)
				}
			MAX-ACCESS read-write
			STATUS current
			DESCRIPTION
				"Enable/Disable use of FEC in Upstream direction."
			DEFVAL { disable }
			::= { alaOntEntry 39 }

		
		alaOntEnable OBJECT-TYPE
			SYNTAX INTEGER
				{
				auto(0),
				disable(1),
				enable(2)
				}
			MAX-ACCESS read-write
			STATUS current
			DESCRIPTION
				"ONT disabling decision for rogue ONTs."
			DEFVAL { auto }
			::= { alaOntEntry 57 }

		
		alaOntSwDnloadVersion OBJECT-TYPE
			SYNTAX OCTET STRING (SIZE (1..14))
			MAX-ACCESS read-write
			STATUS current
			DESCRIPTION
				"Standby ONT software version number to be downloaded. If sw-ver-pland is set to delayactivate, sw-dnload-version cannot be set to disabled."
			DEFVAL { "DISABLED" }
			::= { alaOntEntry 60 }

		
		alaOntOpticsHist OBJECT-TYPE
			SYNTAX INTEGER
				{
				enable(1),
				disable(2)
				}
			MAX-ACCESS read-write
			STATUS current
			DESCRIPTION
				"Daily optical supervision measurements collection."
			DEFVAL { disable }
			::= { alaOntEntry 63 }

		
		alaOntPlndVar OBJECT-TYPE
			SYNTAX OCTET STRING (SIZE (0..80))
			MAX-ACCESS read-write
			STATUS current
			DESCRIPTION
				"Planned variant of the ONT hardware version.Use DO for Data-only ONTs,SIP for SIP ONTs,H.248 for MEGACO ONTs."
			DEFVAL { "" }
			::= { alaOntEntry 65 }

		
		alaOntRfFilter OBJECT-TYPE
			SYNTAX INTEGER
				{
				pass-none(0),
				pass-low(1),
				pass-low-high(2),
				pass-low-middle(3)
				}
			MAX-ACCESS read-write
			STATUS current
			DESCRIPTION
				"Filter settings for RF video."
			DEFVAL { pass-low-high }
			::= { alaOntEntry 68 }

		
		alaOntSlidVisibility OBJECT-TYPE
			SYNTAX INTEGER
				{
				disabled(0),
				enable-slid-on(1),
				enable-all(2)
				}
			MAX-ACCESS read-write
			STATUS current
			DESCRIPTION
				"SLID visibility of the interface."
			DEFVAL { disabled }
			::= { alaOntEntry 71 }

		
		alaOntUsPoliceMode OBJECT-TYPE
			SYNTAX INTEGER
				{
				local(0),
				remote(1)
				}
			MAX-ACCESS read-write
			STATUS current
			DESCRIPTION
				"Upstream police mode."
			DEFVAL { local }
			::= { alaOntEntry 74 }

		
		alaOntEnableAes OBJECT-TYPE
			SYNTAX INTEGER
				{
				disable(0),
				enable(1)
				}
			MAX-ACCESS read-write
			STATUS current
			DESCRIPTION
				"AES encryption for all bi-directional GEM port."
			DEFVAL { disable }
			::= { alaOntEntry 75 }

		
		alaOntLogAuthId OBJECT-TYPE
			SYNTAX OCTET STRING (SIZE (0..24))
			MAX-ACCESS read-write
			STATUS current
			DESCRIPTION
				"The logical id for the ont."
			DEFVAL { "" }
			::= { alaOntEntry 82 }

		
		alaOntLogAuthPwd OBJECT-TYPE
			SYNTAX OCTET STRING
			MAX-ACCESS read-write
			STATUS current
			DESCRIPTION
				"The password for the ont"
			::= { alaOntEntry 83 }

		
		alaOntBridgeMapMode OBJECT-TYPE
			SYNTAX INTEGER
				{
				one-mp-bridge-map-filter(5),
				n-mp-bridge-map-filter(7)
				}
			MAX-ACCESS read-write
			STATUS current
			DESCRIPTION
				"Ont bridge map mode."
			DEFVAL { one-mp-bridge-map-filter }
			::= { alaOntEntry 84 }

		
		alaOntCvlantransMode OBJECT-TYPE
			SYNTAX INTEGER
				{
				remote(0),
				local(1)
				}
			MAX-ACCESS read-write
			STATUS current
			DESCRIPTION
				"Description."
			DEFVAL { remote }
			::= { alaOntEntry 85 }

		
		alaOntOltDSCPpbitalign OBJECT-TYPE
			SYNTAX INTEGER
				{
				disable(0),
				enable(1)
				}
			MAX-ACCESS read-write
			STATUS current
			DESCRIPTION
				"If OLT need perform DSCP to Pbit alignment for this ONU, when the DSCP to Pbit alignment is configured on the vlan port."
			DEFVAL { disable }
			::= { alaOntEntry 92 }

		
		alaOntSnBundleCtrl0 OBJECT-TYPE
			SYNTAX Integer32
			MAX-ACCESS read-write
			STATUS current
			DESCRIPTION
				"SN bundling behavior associated with slid/loid."
			::= { alaOntEntry 93 }

		
		alaOntSnBundleCtrl1 OBJECT-TYPE
			SYNTAX Integer32
			MAX-ACCESS read-write
			STATUS current
			DESCRIPTION
				"SN bundling behavior associated with slid/loid."
			::= { alaOntEntry 94 }

		
		alaOntSlotTable OBJECT-TYPE
			SYNTAX SEQUENCE OF AlaOntSlotEntry
			MAX-ACCESS not-accessible
			STATUS current
			DESCRIPTION
				"Description."
			::= { alaOnt 2 }

		
		alaOntSlotEntry OBJECT-TYPE
			SYNTAX AlaOntSlotEntry
			MAX-ACCESS not-accessible
			STATUS current
			DESCRIPTION
				"Description."
			INDEX { alaOntID, alaOntSlotID }
			::= { alaOntSlotTable 1 }

		
		AlaOntSlotEntry ::=
			SEQUENCE { 
				alaOntSlotOntID
					Integer32,
				alaOntSlotID
					Integer32,
				alaOntSlotControlState
					AlcatelControlState,
				alaOntSlotPlannedCardType
					INTEGER,
				alaOntSlotAdminState
					INTEGER,
				alaOntSlotPlndNumDataPorts
					Integer32,
				alaOntSlotPlndNumVoicePorts
					Integer32,
				alaOntSlotPortType
					INTEGER,
				alaOntSlotTranspModeRem
					INTEGER
			 }

		alaOntSlotOntID OBJECT-TYPE
			SYNTAX Integer32 (1..128)
			MAX-ACCESS read-write
			STATUS current
			DESCRIPTION
				"The ONT Identifier."
			::= { alaOntSlotEntry 1 }

		
		alaOntSlotID OBJECT-TYPE
			SYNTAX Integer32 (1..14)
			MAX-ACCESS read-only
			STATUS current
			DESCRIPTION
				"Description."
			::= { alaOntSlotEntry 2 }

		
		alaOntSlotControlState OBJECT-TYPE
			SYNTAX AlcatelControlState
			MAX-ACCESS read-write
			STATUS current
			DESCRIPTION
				"ONT slot control state."
			::= { alaOntSlotEntry 3 }

		
		alaOntSlotPlannedCardType OBJECT-TYPE
			SYNTAX INTEGER
				{
				base10_100(24),
				veip(48)
				}
			MAX-ACCESS read-write
			STATUS current
			DESCRIPTION
				"Planned card type."
			::= { alaOntSlotEntry 4 }

		
		alaOntSlotAdminState OBJECT-TYPE
			SYNTAX INTEGER
				{
				up(0),
				down(1)
				}
			MAX-ACCESS read-write
			STATUS current
			DESCRIPTION
				"Administrative status of the interface."
			DEFVAL { up }
			::= { alaOntSlotEntry 6 }

		
		alaOntSlotPlndNumDataPorts OBJECT-TYPE
			SYNTAX Integer32 (0..16)
			MAX-ACCESS read-write
			STATUS current
			DESCRIPTION
				"Planned no of data ports."
			::= { alaOntSlotEntry 10 }

		
		alaOntSlotPlndNumVoicePorts OBJECT-TYPE
			SYNTAX Integer32 (0..24)
			MAX-ACCESS read-write
			STATUS current
			DESCRIPTION
				"Planned no of voice ports."
			::= { alaOntSlotEntry 11 }

		
		alaOntSlotPortType OBJECT-TYPE
			SYNTAX INTEGER
				{
				uni(1),
				nni(2)
				}
			MAX-ACCESS read-write
			STATUS current
			DESCRIPTION
				"Port type of the line card."
			DEFVAL { uni }
			::= { alaOntSlotEntry 12 }

		
		alaOntSlotTranspModeRem OBJECT-TYPE
			SYNTAX INTEGER
				{
				disable(1),
				enable(2)
				}
			MAX-ACCESS read-write
			STATUS current
			DESCRIPTION
				"Transparent mode of the line card."
			DEFVAL { disable }
			::= { alaOntSlotEntry 13 }

		
		alaQos OBJECT IDENTIFIER ::= { asam 47 }

		
		alaQosInterface OBJECT IDENTIFIER ::= { alaQos 5 }

		
		alaQosUsQueueTable OBJECT-TYPE
			SYNTAX SEQUENCE OF AlaQosUsQueueEntry
			MAX-ACCESS not-accessible
			STATUS current
			DESCRIPTION
				"Description."
			::= { alaQosInterface 2 }

		
		alaQosUsQueueEntry OBJECT-TYPE
			SYNTAX AlaQosUsQueueEntry
			MAX-ACCESS not-accessible
			STATUS current
			DESCRIPTION
				"Description."
			INDEX { ifIndex }
			::= { alaQosUsQueueTable 1 }

		
		AlaQosUsQueueEntry ::=
			SEQUENCE { 
				alaQosUsQueueBwProfile
					Integer32,
				alaQosUsQueueWeight
					Integer32,
				alaQosUsQueuePriority
					Integer32,
				alaQosUsQueueBwSharing
					Integer32,
				alaQosUsQueueProfile
					Integer32
			 }

		alaQosUsQueueBwProfile OBJECT-TYPE
			SYNTAX Integer32
			MAX-ACCESS read-write
			STATUS current
			DESCRIPTION
				"The name of the bandwidth profile. For EPON OLT in downstream, this profile used for DBA on 1G PON bandwidth."
			::= { alaQosUsQueueEntry 3 }

		
		alaQosUsQueueWeight OBJECT-TYPE
			SYNTAX Integer32 (0..127)
			MAX-ACCESS read-write
			STATUS current
			DESCRIPTION
				"Relative weight."
			DEFVAL { 1 }
			::= { alaQosUsQueueEntry 4 }

		
		alaQosUsQueuePriority OBJECT-TYPE
			SYNTAX Integer32 (1..8)
			MAX-ACCESS read-write
			STATUS current
			DESCRIPTION
				"Relative priority."
			DEFVAL { 1 }
			::= { alaQosUsQueueEntry 5 }

		
		alaQosUsQueueBwSharing OBJECT-TYPE
			SYNTAX Integer32 (1..4)
			MAX-ACCESS read-write
			STATUS current
			DESCRIPTION
				"Shaper sharing."
			DEFVAL { 1 }
			::= { alaQosUsQueueEntry 6 }

		
		alaQosUsQueueProfile OBJECT-TYPE
			SYNTAX Integer32
			MAX-ACCESS read-write
			STATUS current
			DESCRIPTION
				"Name of the queue profile."
			::= { alaQosUsQueueEntry 7 }

		
		alaQosDsQueueTable OBJECT-TYPE
			SYNTAX SEQUENCE OF AlaQosDsQueueEntry
			MAX-ACCESS not-accessible
			STATUS current
			DESCRIPTION
				"Description."
			::= { alaQosInterface 3 }

		
		alaQosDsQueueEntry OBJECT-TYPE
			SYNTAX AlaQosDsQueueEntry
			MAX-ACCESS not-accessible
			STATUS current
			DESCRIPTION
				"Description."
			INDEX { ifIndex }
			::= { alaQosDsQueueTable 1 }

		
		AlaQosDsQueueEntry ::=
			SEQUENCE { 
				alaQosDsQueueWeight
					Integer32,
				alaQosDsQueuePriority
					Integer32
			 }

		alaQosDsQueueWeight OBJECT-TYPE
			SYNTAX Integer32 (0..127)
			MAX-ACCESS read-write
			STATUS current
			DESCRIPTION
				"Relative Weight."
			DEFVAL { 10 }
			::= { alaQosDsQueueEntry 3 }

		
		alaQosDsQueuePriority OBJECT-TYPE
			SYNTAX Integer32 (1..8)
			MAX-ACCESS read-write
			STATUS current
			DESCRIPTION
				"Relative priority."
			DEFVAL { 1 }
			::= { alaQosDsQueueEntry 4 }

		
	
	END

--
-- ALU-SMI.mib
--
